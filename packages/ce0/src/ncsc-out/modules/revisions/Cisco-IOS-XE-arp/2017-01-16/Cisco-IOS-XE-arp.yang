module Cisco-IOS-XE-arp {
  // Generated by yanger -t ncs
  tailf:ncs-device-type "netconf";

  namespace "http://cisco.com/ns/yang/Cisco-IOS-XE-arp";
  prefix ios-arp;

  import ietf-inet-types {
    prefix inet;
  }
  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Access Point (AP) Group Yang model.
     Copyright (c) 2016 by Cisco Systems, Inc.
     All rights reserved.";

  revision 2017-01-16 {
    description
      "Initial Revision";
  }

  grouping ncs_template_config-arp-grouping {
    container arp {
      description
        "Set a static ARP entry";
      list arp-entry {
        // NCS patched for predictable order
        ordered-by user;
        description
          "Configure an arp entry";
        key "ip";
        leaf ip {
          description
            "IP address of ARP entry";
          type string;
        }
        leaf hardware-address {
          description
            "48-bit hardware address of ARP entry";
          type string;
        }
        leaf arp-type {
          type string;
        }
      }
    }
  }

  grouping ncs_rpc_notif_config-arp-grouping {
    container arp {
      description
        "Set a static ARP entry";
      list arp-entry {
        description
          "Configure an arp entry";
        key "ip";
        leaf ip {
          description
            "IP address of ARP entry";
          type inet:ip-address;
        }
        leaf hardware-address {
          description
            "48-bit hardware address of ARP entry";
          type string;
        }
        leaf arp-type {
          type enumeration {
            enum "ARPA";
            enum "SAP";
            enum "SMDS";
            enum "SNAP";
            enum "SRP-A";
            enum "SRP-B";
          }
        }
      }
    }
  }

  grouping live_ncs_config-arp-grouping {
    container arp {
      description
        "Set a static ARP entry";
      list arp-entry {
        description
          "Configure an arp entry";
        key "ip";
        leaf ip {
          description
            "IP address of ARP entry";
          type inet:ip-address;
        }
        leaf hardware-address {
          description
            "48-bit hardware address of ARP entry";
          type string;
        }
        leaf arp-type {
          type enumeration {
            enum "ARPA";
            enum "SAP";
            enum "SMDS";
            enum "SNAP";
            enum "SRP-A";
            enum "SRP-B";
          }
        }
      }
    }
  }

  grouping config-arp-grouping {
    container arp {
      description
        "Set a static ARP entry";
      list arp-entry {
        description
          "Configure an arp entry";
        key "ip";
        leaf ip {
          description
            "IP address of ARP entry";
          type inet:ip-address;
        }
        leaf hardware-address {
          description
            "48-bit hardware address of ARP entry";
          type string;
        }
        leaf arp-type {
          type enumeration {
            enum "ARPA";
            enum "SAP";
            enum "SMDS";
            enum "SNAP";
            enum "SRP-A";
            enum "SRP-B";
          }
        }
      }
    }
  }

  augment "/ncs:devices/ncs:template/ncs:config/ios:native" {
    uses ncs_template_config-arp-grouping;
  }
  augment "/ncs:devices/ncs:device/ncs:live-status/ios:native" {
    uses live_ncs_config-arp-grouping {
      refine arp {
        tailf:ncs-device-type "netconf";
        tailf:display-when "not(../../../ncs:module) or ../../../ncs:module[ncs:name='Cisco-IOS-XE-arp'] or (../../../ncs:live-status-protocol[not(ncs:capability)]) or (../../../ncs:live-status-protocol/ncs:capability/ncs:module[.='Cisco-IOS-XE-arp'])";
      }
    }
  }
  augment "/ncs:devices/ncs:device/ncs:config/ios:native" {
    uses config-arp-grouping {
      refine arp {
        tailf:ncs-device-type "netconf";
        tailf:display-when "not(../../../ncs:module) or ../../../ncs:module[ncs:name='Cisco-IOS-XE-arp']";
      }
    }
  }
}
