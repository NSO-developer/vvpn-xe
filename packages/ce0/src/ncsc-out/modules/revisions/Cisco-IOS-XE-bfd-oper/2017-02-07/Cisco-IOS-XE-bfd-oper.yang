module Cisco-IOS-XE-bfd-oper {
  // Generated by yanger -t ncs
  tailf:ncs-device-type "netconf";

  yang-version "1";
  namespace "http://cisco.com/ns/yang/Cisco-IOS-XE-bfd-oper";
  prefix bfd-ios-xe-oper;

  import ietf-inet-types {
    prefix inet;
  }
  import tailf-ncs {
    prefix ncs;
  }
  import tailf-common {
    prefix tailf;
  }

  organization "Cisco Systems, Inc.";
  contact
    "Cisco Systems, Inc. Customer Service Postal: 170 W Tasman Drive
     San Jose, CA 95134 Tel: +1 1800 553-NETS E-mail: cs-yang@cisco.com";
  description
    "This module contains a collection of YANG definitions for
     monitoring BFD neighbours.Copyright (c) 2016-2017 by Cisco Systems, Inc.All rights reserved.";

  revision 2017-02-07 {
    description
      "Initial revision";
  }

  typedef bfd-lsp-type {
    description
      "BFD lsp type";
    type enumeration {
      enum "working";
      enum "protect";
      enum "unknown";
    }
  }

  typedef bfd-state-type {
    description
      "BFD state type";
    type enumeration {
      enum "admindown";
      enum "down";
      enum "fail";
      enum "init";
      enum "up";
      enum "invalid";
    }
  }

  typedef bfd-remote-state-type {
    description
      "BFD remote state type";
    type enumeration {
      enum "up";
      enum "down";
      enum "init";
      enum "admindown";
      enum "invalid";
    }
  }

  typedef bfd-oper-session-type {
    description
      "BFD session type";
    type enumeration {
      enum "ipv4";
      enum "ipv6";
      enum "vccv";
      enum "mpls-tp";
      enum "ipv4-multihop";
      enum "ipv6-multihop";
    }
  }

  grouping ncs_template_bfd-neighbor-params {
    description
      "BFD neighbour parameters";
    leaf ld {
      type string;
      description
        "local-discriminator";
    }
    leaf rd {
      type string;
      description
        "remote-discriminator";
    }
    leaf remote-state {
      type string;
      description
        " Remote Heard. RH state of BFD version '0'
          is also mapped to up/down. ";
    }
    leaf state {
      type string;
      description
        "BFD state";
    }
  }

  grouping ncs_template_bfd-tunnel-path-key {
    description
      "BFD tunnel Path Key";
    leaf interface {
      type string;
    }
    leaf lsp-type {
      type string;
    }
  }

  grouping ncs_template_bfd-circuit-key {
    description
      "BFD circuit key";
    leaf interface {
      type string;
    }
    leaf vcid {
      type string;
    }
  }

  grouping ncs_template_bfd-nbr-key {
    description
      "BFD Neighbor key";
    leaf ip {
      type string;
    }
    leaf interface {
      type string;
    }
  }

  grouping ncs_template_mhop-nbr-key {
    description
      "BHD MHOP Neighbor key";
    leaf ip {
      type string;
    }
  }

  grouping ncs_template_mhop-vrf-nbr-key {
    description
      "BHD MHOP VRF Neighbor key";
    leaf ip {
      type string;
    }
    leaf vrf {
      type string;
    }
  }

  grouping ncs_template_bfd-session {
    description
      "BHD session data";
    leaf type {
      description
        "Session type";
      type string;
    }
    container bfd-tunnel-paths {
      list bfd-tunnel-path {
        // NCS patched for predictable order
        ordered-by user;
        // NCS drop when statement
        key "interface lsp-type";
        description
          "Tunnel Path";
        uses bfd-ios-xe-oper:ncs_template_bfd-tunnel-path-key;
        uses bfd-ios-xe-oper:ncs_template_bfd-neighbor-params;
      }
    }
    container bfd-circuits {
      list bfd-circuit {
        // NCS patched for predictable order
        ordered-by user;
        // NCS drop when statement
        key "interface vcid";
        description
          "BFD circuit";
        uses bfd-ios-xe-oper:ncs_template_bfd-circuit-key;
        uses bfd-ios-xe-oper:ncs_template_bfd-neighbor-params;
      }
    }
    container bfd-nbrs {
      list bfd-nbr {
        // NCS patched for predictable order
        ordered-by user;
        // NCS drop when statement
        key "ip interface";
        description
          "This is for directly connected neighbor case";
        uses bfd-ios-xe-oper:ncs_template_bfd-nbr-key;
        uses bfd-ios-xe-oper:ncs_template_bfd-neighbor-params;
      }
    }
    container bfd-mhop-nbrs {
      list bfd-mhop-nbr {
        // NCS patched for predictable order
        ordered-by user;
        // NCS drop when statement
        key "ip";
        description
          "This is for multi hop neighbor scenario
           for global VRF (no VRF).";
        uses bfd-ios-xe-oper:ncs_template_mhop-nbr-key;
        uses bfd-ios-xe-oper:ncs_template_bfd-neighbor-params;
      }
    }
    container bfd-mhop-vrf-nbrs {
      list bfd-mhop-vrf-nbr {
        // NCS patched for predictable order
        ordered-by user;
        // NCS drop when statement
        key "ip vrf";
        description
          "This is for multi hop neighbor scenario
           for non-global VRF.";
        uses bfd-ios-xe-oper:ncs_template_mhop-vrf-nbr-key;
        uses bfd-ios-xe-oper:ncs_template_bfd-neighbor-params;
      }
    }
  }

  grouping ncs_rpc_notif_bfd-neighbor-params {
    description
      "BFD neighbour parameters";
    leaf ld {
      type uint32;
      description
        "local-discriminator";
    }
    leaf rd {
      type uint32;
      description
        "remote-discriminator";
    }
    leaf remote-state {
      type bfd-ios-xe-oper:bfd-remote-state-type;
      description
        " Remote Heard. RH state of BFD version '0'
          is also mapped to up/down. ";
    }
    leaf state {
      type bfd-ios-xe-oper:bfd-state-type;
      description
        "BFD state";
    }
  }

  grouping ncs_rpc_notif_bfd-tunnel-path-key {
    description
      "BFD tunnel Path Key";
    leaf interface {
      type string;
    }
    leaf lsp-type {
      type bfd-ios-xe-oper:bfd-lsp-type;
    }
  }

  grouping ncs_rpc_notif_bfd-circuit-key {
    description
      "BFD circuit key";
    leaf interface {
      type string;
    }
    leaf vcid {
      type uint32;
    }
  }

  grouping ncs_rpc_notif_bfd-nbr-key {
    description
      "BFD Neighbor key";
    leaf ip {
      type inet:ip-address;
    }
    leaf interface {
      type string;
    }
  }

  grouping ncs_rpc_notif_mhop-nbr-key {
    description
      "BHD MHOP Neighbor key";
    leaf ip {
      type inet:ip-address;
    }
  }

  grouping ncs_rpc_notif_mhop-vrf-nbr-key {
    description
      "BHD MHOP VRF Neighbor key";
    leaf ip {
      type inet:ip-address;
    }
    leaf vrf {
      type string;
    }
  }

  grouping ncs_rpc_notif_bfd-session {
    description
      "BHD session data";
    leaf type {
      description
        "Session type";
      type bfd-ios-xe-oper:bfd-oper-session-type;
    }
    container bfd-tunnel-paths {
      list bfd-tunnel-path {
        when "../../type='mpls-tp'" {
          tailf:xpath-root 3;
        }
        key "interface lsp-type";
        description
          "Tunnel Path";
        uses bfd-ios-xe-oper:ncs_rpc_notif_bfd-tunnel-path-key;
        uses bfd-ios-xe-oper:ncs_rpc_notif_bfd-neighbor-params;
      }
    }
    container bfd-circuits {
      list bfd-circuit {
        when "../../type='vccv'" {
          tailf:xpath-root 3;
        }
        key "interface vcid";
        description
          "BFD circuit";
        uses bfd-ios-xe-oper:ncs_rpc_notif_bfd-circuit-key;
        uses bfd-ios-xe-oper:ncs_rpc_notif_bfd-neighbor-params;
      }
    }
    container bfd-nbrs {
      list bfd-nbr {
        when "../../type!='mpls-tp' and ../../type!='vccv'" {
          tailf:xpath-root 3;
        }
        key "ip interface";
        description
          "This is for directly connected neighbor case";
        uses bfd-ios-xe-oper:ncs_rpc_notif_bfd-nbr-key;
        uses bfd-ios-xe-oper:ncs_rpc_notif_bfd-neighbor-params;
      }
    }
    container bfd-mhop-nbrs {
      list bfd-mhop-nbr {
        when "../../type='ipv4-multihop' or ../../type='ipv6-multihop'" {
          tailf:xpath-root 3;
        }
        key "ip";
        description
          "This is for multi hop neighbor scenario
           for global VRF (no VRF).";
        uses bfd-ios-xe-oper:ncs_rpc_notif_mhop-nbr-key;
        uses bfd-ios-xe-oper:ncs_rpc_notif_bfd-neighbor-params;
      }
    }
    container bfd-mhop-vrf-nbrs {
      list bfd-mhop-vrf-nbr {
        when "../../type='ipv4-multihop' or ../../type='ipv6-multihop'" {
          tailf:xpath-root 3;
        }
        key "ip vrf";
        description
          "This is for multi hop neighbor scenario
           for non-global VRF.";
        uses bfd-ios-xe-oper:ncs_rpc_notif_mhop-vrf-nbr-key;
        uses bfd-ios-xe-oper:ncs_rpc_notif_bfd-neighbor-params;
      }
    }
  }

  grouping live_ncs_bfd-neighbor-params {
    description
      "BFD neighbour parameters";
    leaf ld {
      type uint32;
      description
        "local-discriminator";
    }
    leaf rd {
      type uint32;
      description
        "remote-discriminator";
    }
    leaf remote-state {
      type bfd-ios-xe-oper:bfd-remote-state-type;
      description
        " Remote Heard. RH state of BFD version '0'
          is also mapped to up/down. ";
    }
    leaf state {
      type bfd-ios-xe-oper:bfd-state-type;
      description
        "BFD state";
    }
  }

  grouping live_ncs_bfd-tunnel-path-key {
    description
      "BFD tunnel Path Key";
    leaf interface {
      type string;
    }
    leaf lsp-type {
      type bfd-ios-xe-oper:bfd-lsp-type;
    }
  }

  grouping live_ncs_bfd-circuit-key {
    description
      "BFD circuit key";
    leaf interface {
      type string;
    }
    leaf vcid {
      type uint32;
    }
  }

  grouping live_ncs_bfd-nbr-key {
    description
      "BFD Neighbor key";
    leaf ip {
      type inet:ip-address;
    }
    leaf interface {
      type string;
    }
  }

  grouping live_ncs_mhop-nbr-key {
    description
      "BHD MHOP Neighbor key";
    leaf ip {
      type inet:ip-address;
    }
  }

  grouping live_ncs_mhop-vrf-nbr-key {
    description
      "BHD MHOP VRF Neighbor key";
    leaf ip {
      type inet:ip-address;
    }
    leaf vrf {
      type string;
    }
  }

  grouping live_ncs_bfd-session {
    description
      "BHD session data";
    leaf type {
      description
        "Session type";
      type bfd-ios-xe-oper:bfd-oper-session-type;
    }
    container bfd-tunnel-paths {
      list bfd-tunnel-path {
        // NCS drop when statement
        key "interface lsp-type";
        description
          "Tunnel Path";
        uses bfd-ios-xe-oper:live_ncs_bfd-tunnel-path-key;
        uses bfd-ios-xe-oper:live_ncs_bfd-neighbor-params;
      }
    }
    container bfd-circuits {
      list bfd-circuit {
        // NCS drop when statement
        key "interface vcid";
        description
          "BFD circuit";
        uses bfd-ios-xe-oper:live_ncs_bfd-circuit-key;
        uses bfd-ios-xe-oper:live_ncs_bfd-neighbor-params;
      }
    }
    container bfd-nbrs {
      list bfd-nbr {
        // NCS drop when statement
        key "ip interface";
        description
          "This is for directly connected neighbor case";
        uses bfd-ios-xe-oper:live_ncs_bfd-nbr-key;
        uses bfd-ios-xe-oper:live_ncs_bfd-neighbor-params;
      }
    }
    container bfd-mhop-nbrs {
      list bfd-mhop-nbr {
        // NCS drop when statement
        key "ip";
        description
          "This is for multi hop neighbor scenario
           for global VRF (no VRF).";
        uses bfd-ios-xe-oper:live_ncs_mhop-nbr-key;
        uses bfd-ios-xe-oper:live_ncs_bfd-neighbor-params;
      }
    }
    container bfd-mhop-vrf-nbrs {
      list bfd-mhop-vrf-nbr {
        // NCS drop when statement
        key "ip vrf";
        description
          "This is for multi hop neighbor scenario
           for non-global VRF.";
        uses bfd-ios-xe-oper:live_ncs_mhop-vrf-nbr-key;
        uses bfd-ios-xe-oper:live_ncs_bfd-neighbor-params;
      }
    }
  }

  grouping bfd-neighbor-params {
    description
      "BFD neighbour parameters";
    leaf ld {
      type uint32;
      description
        "local-discriminator";
    }
    leaf rd {
      type uint32;
      description
        "remote-discriminator";
    }
    leaf remote-state {
      type bfd-ios-xe-oper:bfd-remote-state-type;
      description
        " Remote Heard. RH state of BFD version '0'
          is also mapped to up/down. ";
    }
    leaf state {
      type bfd-ios-xe-oper:bfd-state-type;
      description
        "BFD state";
    }
  }

  grouping bfd-tunnel-path-key {
    description
      "BFD tunnel Path Key";
    leaf interface {
      type string;
    }
    leaf lsp-type {
      type bfd-ios-xe-oper:bfd-lsp-type;
    }
  }

  grouping bfd-circuit-key {
    description
      "BFD circuit key";
    leaf interface {
      type string;
    }
    leaf vcid {
      type uint32;
    }
  }

  grouping bfd-nbr-key {
    description
      "BFD Neighbor key";
    leaf ip {
      type inet:ip-address;
    }
    leaf interface {
      type string;
    }
  }

  grouping mhop-nbr-key {
    description
      "BHD MHOP Neighbor key";
    leaf ip {
      type inet:ip-address;
    }
  }

  grouping mhop-vrf-nbr-key {
    description
      "BHD MHOP VRF Neighbor key";
    leaf ip {
      type inet:ip-address;
    }
    leaf vrf {
      type string;
    }
  }

  grouping bfd-session {
    description
      "BHD session data";
    leaf type {
      description
        "Session type";
      type bfd-ios-xe-oper:bfd-oper-session-type;
    }
    container bfd-tunnel-paths {
      list bfd-tunnel-path {
        when "../../type='mpls-tp'" {
          tailf:xpath-root 3;
        }
        key "interface lsp-type";
        description
          "Tunnel Path";
        uses bfd-ios-xe-oper:bfd-tunnel-path-key;
        uses bfd-ios-xe-oper:bfd-neighbor-params;
      }
    }
    container bfd-circuits {
      list bfd-circuit {
        when "../../type='vccv'" {
          tailf:xpath-root 3;
        }
        key "interface vcid";
        description
          "BFD circuit";
        uses bfd-ios-xe-oper:bfd-circuit-key;
        uses bfd-ios-xe-oper:bfd-neighbor-params;
      }
    }
    container bfd-nbrs {
      list bfd-nbr {
        when "../../type!='mpls-tp' and ../../type!='vccv'" {
          tailf:xpath-root 3;
        }
        key "ip interface";
        description
          "This is for directly connected neighbor case";
        uses bfd-ios-xe-oper:bfd-nbr-key;
        uses bfd-ios-xe-oper:bfd-neighbor-params;
      }
    }
    container bfd-mhop-nbrs {
      list bfd-mhop-nbr {
        when "../../type='ipv4-multihop' or ../../type='ipv6-multihop'" {
          tailf:xpath-root 3;
        }
        key "ip";
        description
          "This is for multi hop neighbor scenario
           for global VRF (no VRF).";
        uses bfd-ios-xe-oper:mhop-nbr-key;
        uses bfd-ios-xe-oper:bfd-neighbor-params;
      }
    }
    container bfd-mhop-vrf-nbrs {
      list bfd-mhop-vrf-nbr {
        when "../../type='ipv4-multihop' or ../../type='ipv6-multihop'" {
          tailf:xpath-root 3;
        }
        key "ip vrf";
        description
          "This is for multi hop neighbor scenario
           for non-global VRF.";
        uses bfd-ios-xe-oper:mhop-vrf-nbr-key;
        uses bfd-ios-xe-oper:bfd-neighbor-params;
      }
    }
  }

  augment "/ncs:devices/ncs:device/ncs:config" {
    // NCS drop config false container 'bfd-state'
  }
  augment "/ncs:devices/ncs:device/ncs:live-status" {
    container bfd-state {
      tailf:ncs-device-type "netconf";
      tailf:display-when "not(../../ncs:module) or ../../ncs:module[ncs:name='Cisco-IOS-XE-bfd-oper'] or (../../ncs:live-status-protocol[not(ncs:capability)]) or (../../ncs:live-status-protocol/ncs:capability/ncs:module[.='Cisco-IOS-XE-bfd-oper'])";
      description
        "Data nodes for BFD neighbors.";
      container sessions {
        list session {
          key "type";
          uses bfd-ios-xe-oper:live_ncs_bfd-session;
        }
      }
    }
  }
  augment "/ncs:devices/ncs:template/ncs:config" {
    // NCS drop config false container 'bfd-state'
  }
}
