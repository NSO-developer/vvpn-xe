module Cisco-IOS-XE-call-home {
  // Generated by yanger -t ncs
  tailf:ncs-device-type "netconf";

  namespace "http://cisco.com/ns/yang/Cisco-IOS-XE-call-home";
  prefix ios-ch;

  import Cisco-IOS-XE-native {
    prefix ios;
  }
  import Cisco-IOS-XE-types {
    prefix ios-types;
  }
  import Cisco-IOS-XE-interface-common {
    prefix ios-ifc;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Call Home Yang Model.
     Copyright (c) 2016 by Cisco Systems, Inc.
     All rights reserved.";

  revision 2017-02-07 {
    description
      "Initial revision";
  }

  grouping ncs_template_call-home-profile-periodic-grouping {
    container periodic {
      choice periodic-choice {
        description
          "Periodic call-home message";
        container daily {
          description
            "Daily call-home message";
          leaf begin-time {
            description
              "Begin time";
            type string;
          }
        }
        container monthly {
          description
            "Monthly call-home message";
          leaf date {
            description
              "Day of month";
            type string;
          }
          leaf begin-time {
            description
              "Begin time";
            type string;
          }
        }
        container weekly {
          description
            "Weekly call-home message";
          leaf day {
            description
              "Day of the week";
            type string;
          }
          leaf begin-time {
            description
              "Begin time";
            type string;
          }
        }
      }
    }
  }

  grouping ncs_template_cfg-call-home-profile-grouping {
    leaf active {
      description
        "Activate the current profile";
      type string;
    }
    container destination {
      description
        "Message destination related configuration";
      leaf transport-method {
        description
          "To specify transport method for this profile";
        type string;
      }
      container address {
        description
          "To add destination address to this profile";
        leaf email {
          description
            "Use email address";
          type string;
        }
        leaf http {
          description
            "To add http address to this profile";
          type string;
        }
      }
    }
    container subscribe-to-alert-group {
      description
        "Subscribe to alert-group";
      container diagnostic {
        description
          "diagnostic info";
        presence "true";
        leaf severity {
          description
            "Severity";
          type string;
        }
      }
      container environment {
        description
          "environmental info";
        presence "true";
        leaf severity {
          description
            "Severity";
          type string;
        }
      }
      container inventory {
        description
          "inventory info";
        presence "true";
        uses ncs_template_call-home-profile-periodic-grouping;
      }
      container syslog {
        description
          "syslog info";
        presence "true";
        list severity {
          // NCS patched for predictable order
          ordered-by user;
          description
            "severity";
          key "value";
          leaf value {
            type string;
          }
          leaf pattern {
            description
              "Syslog message pattern";
            type string;
          }
        }
      }
      container configuration {
        description
          "configuration info";
        presence "true";
        uses ncs_template_call-home-profile-periodic-grouping;
      }
    }
  }

  grouping ncs_template_config-call-home-grouping {
    leaf contact-email-addr {
      description
        "Use email address";
      type string;
    }
    container source-interface {
      description
        "Source interface name to send call-home messages using email";
      uses ios-ifc:ncs_template_interface-grouping;
    }
    container http-proxy {
      description
        "Specify proxy server for http request";
      list proxy-servers {
        // NCS patched for predictable order
        ordered-by user;
        key "proxy-server";
        leaf proxy-server {
          description
            "Http proxy server";
          type string;
        }
        leaf port {
          description
            "http proxy server port number";
          type string;
        }
      }
    }
    list profile {
      // NCS patched for predictable order
      ordered-by user;
      description
        "Enter call-home profile configuration mode";
      key "profile-name";
      leaf profile-name {
        type string;
      }
      uses ncs_template_cfg-call-home-profile-grouping;
    }
  }

  grouping ncs_rpc_notif_call-home-profile-periodic-grouping {
    container periodic {
      choice periodic-choice {
        description
          "Periodic call-home message";
        container daily {
          description
            "Daily call-home message";
          leaf begin-time {
            description
              "Begin time";
            type ios-types:hhmm-type;
          }
        }
        container monthly {
          description
            "Monthly call-home message";
          leaf date {
            description
              "Day of month";
            type uint8 {
              range "1..31";
            }
          }
          leaf begin-time {
            description
              "Begin time";
            type ios-types:hhmm-type;
          }
        }
        container weekly {
          description
            "Weekly call-home message";
          leaf day {
            description
              "Day of the week";
            type ios-types:weekday-type;
          }
          leaf begin-time {
            description
              "Begin time";
            type ios-types:hhmm-type;
          }
        }
      }
    }
  }

  grouping ncs_rpc_notif_cfg-call-home-profile-grouping {
    leaf active {
      description
        "Activate the current profile";
      type boolean;
    }
    container destination {
      description
        "Message destination related configuration";
      leaf transport-method {
        description
          "To specify transport method for this profile";
        type enumeration {
          enum "http";
          enum "email";
        }
      }
      container address {
        description
          "To add destination address to this profile";
        leaf email {
          description
            "Use email address";
          type string;
        }
        leaf http {
          description
            "To add http address to this profile";
          type string;
        }
      }
    }
    container subscribe-to-alert-group {
      description
        "Subscribe to alert-group";
      container diagnostic {
        description
          "diagnostic info";
        presence "true";
        leaf severity {
          description
            "Severity";
          type enumeration {
            enum "catastrophic";
            enum "critical";
            enum "debugging";
            enum "disaster";
            enum "fatal";
            enum "major";
            enum "minor";
            enum "normal";
            enum "notification";
            enum "warning";
          }
        }
      }
      container environment {
        description
          "environmental info";
        presence "true";
        leaf severity {
          description
            "Severity";
          type enumeration {
            enum "catastrophic";
            enum "critical";
            enum "debugging";
            enum "disaster";
            enum "fatal";
            enum "major";
            enum "minor";
            enum "normal";
            enum "notification";
            enum "warning";
          }
        }
      }
      container inventory {
        description
          "inventory info";
        presence "true";
        uses ncs_rpc_notif_call-home-profile-periodic-grouping;
      }
      container syslog {
        description
          "syslog info";
        presence "true";
        list severity {
          description
            "severity";
          key "value";
          leaf value {
            type enumeration {
              enum "catastrophic";
              enum "critical";
              enum "debugging";
              enum "disaster";
              enum "fatal";
              enum "major";
              enum "minor";
              enum "normal";
              enum "notification";
              enum "warning";
            }
          }
          leaf pattern {
            description
              "Syslog message pattern";
            type string;
          }
        }
      }
      container configuration {
        description
          "configuration info";
        presence "true";
        uses ncs_rpc_notif_call-home-profile-periodic-grouping;
      }
    }
  }

  grouping ncs_rpc_notif_config-call-home-grouping {
    leaf contact-email-addr {
      description
        "Use email address";
      type string;
    }
    container source-interface {
      description
        "Source interface name to send call-home messages using email";
      uses ios-ifc:ncs_rpc_notif_interface-grouping;
    }
    container http-proxy {
      description
        "Specify proxy server for http request";
      list proxy-servers {
        key "proxy-server";
        leaf proxy-server {
          description
            "Http proxy server";
          type string;
        }
        leaf port {
          description
            "http proxy server port number";
          type uint16 {
            range "1..65535";
          }
        }
      }
    }
    list profile {
      description
        "Enter call-home profile configuration mode";
      key "profile-name";
      leaf profile-name {
        type string;
      }
      uses ncs_rpc_notif_cfg-call-home-profile-grouping;
    }
  }

  grouping live_ncs_call-home-profile-periodic-grouping {
    container periodic {
      choice periodic-choice {
        description
          "Periodic call-home message";
        container daily {
          description
            "Daily call-home message";
          leaf begin-time {
            description
              "Begin time";
            type ios-types:hhmm-type;
          }
        }
        container monthly {
          description
            "Monthly call-home message";
          leaf date {
            description
              "Day of month";
            type uint8 {
              range "1..31";
            }
          }
          leaf begin-time {
            description
              "Begin time";
            type ios-types:hhmm-type;
          }
        }
        container weekly {
          description
            "Weekly call-home message";
          leaf day {
            description
              "Day of the week";
            type ios-types:weekday-type;
          }
          leaf begin-time {
            description
              "Begin time";
            type ios-types:hhmm-type;
          }
        }
      }
    }
  }

  grouping live_ncs_cfg-call-home-profile-grouping {
    leaf active {
      description
        "Activate the current profile";
      type boolean;
    }
    container destination {
      description
        "Message destination related configuration";
      leaf transport-method {
        description
          "To specify transport method for this profile";
        type enumeration {
          enum "http";
          enum "email";
        }
      }
      container address {
        description
          "To add destination address to this profile";
        leaf email {
          description
            "Use email address";
          type string;
        }
        leaf http {
          description
            "To add http address to this profile";
          type string;
        }
      }
    }
    container subscribe-to-alert-group {
      description
        "Subscribe to alert-group";
      container diagnostic {
        description
          "diagnostic info";
        presence "true";
        leaf severity {
          description
            "Severity";
          type enumeration {
            enum "catastrophic";
            enum "critical";
            enum "debugging";
            enum "disaster";
            enum "fatal";
            enum "major";
            enum "minor";
            enum "normal";
            enum "notification";
            enum "warning";
          }
        }
      }
      container environment {
        description
          "environmental info";
        presence "true";
        leaf severity {
          description
            "Severity";
          type enumeration {
            enum "catastrophic";
            enum "critical";
            enum "debugging";
            enum "disaster";
            enum "fatal";
            enum "major";
            enum "minor";
            enum "normal";
            enum "notification";
            enum "warning";
          }
        }
      }
      container inventory {
        description
          "inventory info";
        presence "true";
        uses live_ncs_call-home-profile-periodic-grouping;
      }
      container syslog {
        description
          "syslog info";
        presence "true";
        list severity {
          description
            "severity";
          key "value";
          leaf value {
            type enumeration {
              enum "catastrophic";
              enum "critical";
              enum "debugging";
              enum "disaster";
              enum "fatal";
              enum "major";
              enum "minor";
              enum "normal";
              enum "notification";
              enum "warning";
            }
          }
          leaf pattern {
            description
              "Syslog message pattern";
            type string;
          }
        }
      }
      container configuration {
        description
          "configuration info";
        presence "true";
        uses live_ncs_call-home-profile-periodic-grouping;
      }
    }
  }

  grouping live_ncs_config-call-home-grouping {
    leaf contact-email-addr {
      description
        "Use email address";
      type string;
    }
    container source-interface {
      description
        "Source interface name to send call-home messages using email";
      uses ios-ifc:live_ncs_interface-grouping;
    }
    container http-proxy {
      description
        "Specify proxy server for http request";
      list proxy-servers {
        key "proxy-server";
        leaf proxy-server {
          description
            "Http proxy server";
          type string;
        }
        leaf port {
          description
            "http proxy server port number";
          type uint16 {
            range "1..65535";
          }
        }
      }
    }
    list profile {
      description
        "Enter call-home profile configuration mode";
      key "profile-name";
      leaf profile-name {
        type string;
      }
      uses live_ncs_cfg-call-home-profile-grouping;
    }
  }

  grouping call-home-profile-periodic-grouping {
    container periodic {
      choice periodic-choice {
        description
          "Periodic call-home message";
        container daily {
          description
            "Daily call-home message";
          leaf begin-time {
            description
              "Begin time";
            type ios-types:hhmm-type;
          }
        }
        container monthly {
          description
            "Monthly call-home message";
          leaf date {
            description
              "Day of month";
            type uint8 {
              range "1..31";
            }
          }
          leaf begin-time {
            description
              "Begin time";
            type ios-types:hhmm-type;
          }
        }
        container weekly {
          description
            "Weekly call-home message";
          leaf day {
            description
              "Day of the week";
            type ios-types:weekday-type;
          }
          leaf begin-time {
            description
              "Begin time";
            type ios-types:hhmm-type;
          }
        }
      }
    }
  }

  grouping cfg-call-home-profile-grouping {
    leaf active {
      description
        "Activate the current profile";
      type boolean;
    }
    container destination {
      description
        "Message destination related configuration";
      leaf transport-method {
        description
          "To specify transport method for this profile";
        type enumeration {
          enum "http";
          enum "email";
        }
      }
      container address {
        description
          "To add destination address to this profile";
        leaf email {
          description
            "Use email address";
          type string;
        }
        leaf http {
          description
            "To add http address to this profile";
          type string;
        }
      }
    }
    container subscribe-to-alert-group {
      description
        "Subscribe to alert-group";
      container diagnostic {
        description
          "diagnostic info";
        presence "true";
        leaf severity {
          description
            "Severity";
          type enumeration {
            enum "catastrophic";
            enum "critical";
            enum "debugging";
            enum "disaster";
            enum "fatal";
            enum "major";
            enum "minor";
            enum "normal";
            enum "notification";
            enum "warning";
          }
        }
      }
      container environment {
        description
          "environmental info";
        presence "true";
        leaf severity {
          description
            "Severity";
          type enumeration {
            enum "catastrophic";
            enum "critical";
            enum "debugging";
            enum "disaster";
            enum "fatal";
            enum "major";
            enum "minor";
            enum "normal";
            enum "notification";
            enum "warning";
          }
        }
      }
      container inventory {
        description
          "inventory info";
        presence "true";
        uses call-home-profile-periodic-grouping;
      }
      container syslog {
        description
          "syslog info";
        presence "true";
        list severity {
          description
            "severity";
          key "value";
          leaf value {
            type enumeration {
              enum "catastrophic";
              enum "critical";
              enum "debugging";
              enum "disaster";
              enum "fatal";
              enum "major";
              enum "minor";
              enum "normal";
              enum "notification";
              enum "warning";
            }
          }
          leaf pattern {
            description
              "Syslog message pattern";
            type string;
          }
        }
      }
      container configuration {
        description
          "configuration info";
        presence "true";
        uses call-home-profile-periodic-grouping;
      }
    }
  }

  grouping config-call-home-grouping {
    leaf contact-email-addr {
      description
        "Use email address";
      type string;
    }
    container source-interface {
      description
        "Source interface name to send call-home messages using email";
      uses ios-ifc:interface-grouping;
    }
    container http-proxy {
      description
        "Specify proxy server for http request";
      list proxy-servers {
        key "proxy-server";
        leaf proxy-server {
          description
            "Http proxy server";
          type string;
        }
        leaf port {
          description
            "http proxy server port number";
          type uint16 {
            range "1..65535";
          }
        }
      }
    }
    list profile {
      description
        "Enter call-home profile configuration mode";
      key "profile-name";
      leaf profile-name {
        type string;
      }
      uses cfg-call-home-profile-grouping;
    }
  }

  augment "/ncs:devices/ncs:template/ncs:config/ios:native/ios:call-home" {
    uses ncs_template_config-call-home-grouping;
  }
  augment "/ncs:devices/ncs:device/ncs:live-status/ios:native/ios:call-home" {
    uses live_ncs_config-call-home-grouping {
      refine profile {
        tailf:ncs-device-type "netconf";
        tailf:display-when "not(../../../ncs:module) or ../../../ncs:module[ncs:name='Cisco-IOS-XE-call-home'] or (../../../ncs:live-status-protocol[not(ncs:capability)]) or (../../../ncs:live-status-protocol/ncs:capability/ncs:module[.='Cisco-IOS-XE-call-home'])";
      }
      refine http-proxy {
        tailf:ncs-device-type "netconf";
        tailf:display-when "not(../../../../ncs:module) or ../../../../ncs:module[ncs:name='Cisco-IOS-XE-call-home'] or (../../../../ncs:live-status-protocol[not(ncs:capability)]) or (../../../../ncs:live-status-protocol/ncs:capability/ncs:module[.='Cisco-IOS-XE-call-home'])";
      }
      refine source-interface {
        tailf:ncs-device-type "netconf";
        tailf:display-when "not(../../../../ncs:module) or ../../../../ncs:module[ncs:name='Cisco-IOS-XE-call-home'] or (../../../../ncs:live-status-protocol[not(ncs:capability)]) or (../../../../ncs:live-status-protocol/ncs:capability/ncs:module[.='Cisco-IOS-XE-call-home'])";
      }
      refine contact-email-addr {
        tailf:ncs-device-type "netconf";
        tailf:display-when "not(../../../../ncs:module) or ../../../../ncs:module[ncs:name='Cisco-IOS-XE-call-home'] or (../../../../ncs:live-status-protocol[not(ncs:capability)]) or (../../../../ncs:live-status-protocol/ncs:capability/ncs:module[.='Cisco-IOS-XE-call-home'])";
      }
    }
  }
  augment "/ncs:devices/ncs:device/ncs:config/ios:native/ios:call-home" {
    uses config-call-home-grouping {
      refine profile {
        tailf:ncs-device-type "netconf";
        tailf:display-when "not(../../../ncs:module) or ../../../ncs:module[ncs:name='Cisco-IOS-XE-call-home']";
      }
      refine http-proxy {
        tailf:ncs-device-type "netconf";
        tailf:display-when "not(../../../../ncs:module) or ../../../../ncs:module[ncs:name='Cisco-IOS-XE-call-home']";
      }
      refine source-interface {
        tailf:ncs-device-type "netconf";
        tailf:display-when "not(../../../../ncs:module) or ../../../../ncs:module[ncs:name='Cisco-IOS-XE-call-home']";
      }
      refine contact-email-addr {
        tailf:ncs-device-type "netconf";
        tailf:display-when "not(../../../../ncs:module) or ../../../../ncs:module[ncs:name='Cisco-IOS-XE-call-home']";
      }
    }
  }
}
