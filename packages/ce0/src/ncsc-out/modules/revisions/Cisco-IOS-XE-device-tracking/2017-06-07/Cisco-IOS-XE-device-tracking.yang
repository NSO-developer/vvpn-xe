module Cisco-IOS-XE-device-tracking {
  // Generated by yanger -t ncs
  tailf:ncs-device-type "netconf";

  namespace "http://cisco.com/ns/yang/Cisco-IOS-XE-device-tracking";
  prefix ios-dt;

  import Cisco-IOS-XE-types {
    prefix ios-types;
  }
  import Cisco-IOS-XE-native {
    prefix ios;
  }
  import ietf-inet-types {
    prefix inet;
  }
  import Cisco-IOS-XE-features {
    prefix ios-features;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Device Tracking Yang model.
     Copyright (c) 2016 by Cisco Systems, Inc.
     All rights reserved.";

  revision 2017-06-07 {
    description
      "Add device-tracking tracking support";
  }
  revision 2017-02-07 {
    description
      "Initial revision";
  }

  grouping ncs_template_config-interface-device-tracking-grouping {
    container device-tracking {
      description
        "Configure device-tracking on the interface";
      leaf attach-policy {
        description
          "Apply a policy for feature device-tracking";
        type string;
      }
    }
  }

  grouping ncs_template_config-device-tracking-grouping {
    list policy {
      // NCS patched for predictable order
      ordered-by user;
      description
        "Configure a policy for feature device-tracking";
      key "word";
      leaf word {
        type string;
      }
      container device-role {
        description
          "Sets the role of the device attached to the port";
        choice device-role-choice {
          case node {
            leaf node {
              type string;
              // NCS drop default statement
            }
          }
          case switch {
            leaf switch {
              type empty;
            }
          }
        }
      }
      container protocol {
        description
          "Set the protocol to glean (default all)";
        leaf udp {
          type string;
        }
        leaf arp {
          description
            "Glean addresses in ARP packets";
          type string;
        }
        leaf dhcp4 {
          description
            "Glean addresses in DHCPv4 packets";
          type string;
        }
        leaf dhcp6 {
          description
            "Glean addresses in DHCPv6 packets";
          type string;
        }
        leaf ndp {
          description
            "Glean addresses in NDP packets";
          type string;
        }
      }
      container tracking {
        description
          "Override default tracking behavior";
        leaf tracking-on-off {
          description
            "Tracking on or off";
          type string;
        }
      }
      container limit {
        description
          "Specifies a limit";
        leaf address-count {
          description
            "Configure maximum address per port";
          type string;
        }
      }
      container security-level {
        description
          "setup security level";
        leaf glean {
          description
            "glean addresses passively";
          type empty;
        }
      }
    }
    container tracking {
      presence "true";
      container auto-source {
        presence "true";
        container fallback {
          description
            "Specify IP and MASK to use as last resort";
          choice ip-subnet-choice {
            case ip-addr-and-mask {
              description
                "IPv4 and MASK of fallback source";
              container ipv4-subnet-type1 {
                leaf ipv4 {
                  description
                    "IPv4 address";
                  type string;
                }
                leaf mask {
                  description
                    "IP prefix mask";
                  type string;
                }
                leaf override {
                  description
                    "Do not select source address from device track table";
                  type empty;
                }
              }
            }
            case ip-addr-and-prefix-len {
              description
                "IPv4 and MASK of fallback source";
              container ipv4-subnet-type2 {
                leaf ipv4-prefix-name {
                  description
                    "ip address/length <network>/<length>, e.g., 192.168.0.0/16";
                  type string;
                }
                leaf override {
                  description
                    "Do not select source address from device track table";
                  type empty;
                }
              }
            }
          }
        }
        leaf override {
          description
            "Do not select source address from device track table";
          type empty;
        }
      }
      leaf retry-interval {
        description
          "Interval time  between two probing";
        type string;
      }
    }
  }

  grouping ncs_template_config-ip-device-grouping {
    container tracking {
      description
        "Device tracking";
      presence "true";
      container probe {
        description
          "Probe";
        container auto-source {
          description
            "Probe source selection algorithm";
          presence "true";
          container fallback {
            description
              "Specify IP and MASK to use as last resort";
            leaf src-ip {
              description
                "IP and MASK of fallback source";
              type string;
            }
            leaf mask {
              description
                "IP prefix mask";
              type string;
            }
          }
          leaf override {
            description
              "Do not select source address from device track table";
            type empty;
          }
        }
        leaf count {
          description
            "Probe count";
          type string;
        }
        leaf delay {
          description
            "Probe delay";
          type string;
        }
        leaf interval {
          description
            "Probe interval";
          type string;
        }
      }
      leaf trace-buffer {
        description
          "Enable Tracing Support";
        type empty;
      }
    }
  }

  grouping ncs_rpc_notif_config-interface-device-tracking-grouping {
    container device-tracking {
      description
        "Configure device-tracking on the interface";
      leaf attach-policy {
        description
          "Apply a policy for feature device-tracking";
        type string;
      }
    }
  }

  grouping ncs_rpc_notif_config-device-tracking-grouping {
    list policy {
      description
        "Configure a policy for feature device-tracking";
      key "word";
      leaf word {
        type string;
      }
      container device-role {
        description
          "Sets the role of the device attached to the port";
        choice device-role-choice {
          case node {
            leaf node {
              type boolean;
              default "true";
            }
          }
          case switch {
            leaf switch {
              type empty;
            }
          }
        }
      }
      container protocol {
        description
          "Set the protocol to glean (default all)";
        leaf udp {
          type boolean;
        }
        leaf arp {
          description
            "Glean addresses in ARP packets";
          type boolean;
        }
        leaf dhcp4 {
          description
            "Glean addresses in DHCPv4 packets";
          type boolean;
        }
        leaf dhcp6 {
          description
            "Glean addresses in DHCPv6 packets";
          type boolean;
        }
        leaf ndp {
          description
            "Glean addresses in NDP packets";
          type boolean;
        }
      }
      container tracking {
        description
          "Override default tracking behavior";
        leaf tracking-on-off {
          description
            "Tracking on or off";
          type enumeration {
            enum "enable";
            enum "disable";
          }
        }
      }
      container limit {
        description
          "Specifies a limit";
        leaf address-count {
          description
            "Configure maximum address per port";
          type uint16 {
            range "1..32000";
          }
        }
      }
      container security-level {
        description
          "setup security level";
        leaf glean {
          description
            "glean addresses passively";
          type empty;
        }
      }
    }
    container tracking {
      presence "true";
      container auto-source {
        presence "true";
        container fallback {
          description
            "Specify IP and MASK to use as last resort";
          choice ip-subnet-choice {
            case ip-addr-and-mask {
              description
                "IPv4 and MASK of fallback source";
              container ipv4-subnet-type1 {
                leaf ipv4 {
                  description
                    "IPv4 address";
                  type inet:ipv4-address;
                }
                leaf mask {
                  description
                    "IP prefix mask";
                  type inet:ipv4-address;
                }
                leaf override {
                  description
                    "Do not select source address from device track table";
                  type empty;
                }
              }
            }
            case ip-addr-and-prefix-len {
              description
                "IPv4 and MASK of fallback source";
              container ipv4-subnet-type2 {
                leaf ipv4-prefix-name {
                  description
                    "ip address/length <network>/<length>, e.g., 192.168.0.0/16";
                  type ios-types:ipv4-address-slush-prefix-len;
                }
                leaf override {
                  description
                    "Do not select source address from device track table";
                  type empty;
                }
              }
            }
          }
        }
        leaf override {
          description
            "Do not select source address from device track table";
          type empty;
        }
      }
      leaf retry-interval {
        description
          "Interval time  between two probing";
        type uint16 {
          range "1..3600";
        }
      }
    }
  }

  grouping ncs_rpc_notif_config-ip-device-grouping {
    container tracking {
      description
        "Device tracking";
      presence "true";
      container probe {
        description
          "Probe";
        container auto-source {
          description
            "Probe source selection algorithm";
          presence "true";
          container fallback {
            description
              "Specify IP and MASK to use as last resort";
            leaf src-ip {
              description
                "IP and MASK of fallback source";
              type inet:ipv4-address;
            }
            leaf mask {
              description
                "IP prefix mask";
              type inet:ipv4-address;
            }
          }
          leaf override {
            description
              "Do not select source address from device track table";
            type empty;
          }
        }
        leaf count {
          description
            "Probe count";
          type uint8;
        }
        leaf delay {
          description
            "Probe delay";
          type uint8 {
            range "1..120";
          }
        }
        leaf interval {
          description
            "Probe interval";
          type uint32 {
            range "30..1814400";
          }
        }
      }
      leaf trace-buffer {
        description
          "Enable Tracing Support";
        type empty;
      }
    }
  }

  grouping live_ncs_config-interface-device-tracking-grouping {
    container device-tracking {
      description
        "Configure device-tracking on the interface";
      leaf attach-policy {
        description
          "Apply a policy for feature device-tracking";
        type string;
      }
    }
  }

  grouping live_ncs_config-device-tracking-grouping {
    list policy {
      description
        "Configure a policy for feature device-tracking";
      key "word";
      leaf word {
        type string;
      }
      container device-role {
        description
          "Sets the role of the device attached to the port";
        choice device-role-choice {
          case node {
            leaf node {
              type boolean;
              // NCS drop default statement
            }
          }
          case switch {
            leaf switch {
              type empty;
            }
          }
        }
      }
      container protocol {
        description
          "Set the protocol to glean (default all)";
        leaf udp {
          type boolean;
        }
        leaf arp {
          description
            "Glean addresses in ARP packets";
          type boolean;
        }
        leaf dhcp4 {
          description
            "Glean addresses in DHCPv4 packets";
          type boolean;
        }
        leaf dhcp6 {
          description
            "Glean addresses in DHCPv6 packets";
          type boolean;
        }
        leaf ndp {
          description
            "Glean addresses in NDP packets";
          type boolean;
        }
      }
      container tracking {
        description
          "Override default tracking behavior";
        leaf tracking-on-off {
          description
            "Tracking on or off";
          type enumeration {
            enum "enable";
            enum "disable";
          }
        }
      }
      container limit {
        description
          "Specifies a limit";
        leaf address-count {
          description
            "Configure maximum address per port";
          type uint16 {
            range "1..32000";
          }
        }
      }
      container security-level {
        description
          "setup security level";
        leaf glean {
          description
            "glean addresses passively";
          type empty;
        }
      }
    }
    container tracking {
      presence "true";
      container auto-source {
        presence "true";
        container fallback {
          description
            "Specify IP and MASK to use as last resort";
          choice ip-subnet-choice {
            case ip-addr-and-mask {
              description
                "IPv4 and MASK of fallback source";
              container ipv4-subnet-type1 {
                leaf ipv4 {
                  description
                    "IPv4 address";
                  type inet:ipv4-address;
                }
                leaf mask {
                  description
                    "IP prefix mask";
                  type inet:ipv4-address;
                }
                leaf override {
                  description
                    "Do not select source address from device track table";
                  type empty;
                }
              }
            }
            case ip-addr-and-prefix-len {
              description
                "IPv4 and MASK of fallback source";
              container ipv4-subnet-type2 {
                leaf ipv4-prefix-name {
                  description
                    "ip address/length <network>/<length>, e.g., 192.168.0.0/16";
                  type ios-types:ipv4-address-slush-prefix-len;
                }
                leaf override {
                  description
                    "Do not select source address from device track table";
                  type empty;
                }
              }
            }
          }
        }
        leaf override {
          description
            "Do not select source address from device track table";
          type empty;
        }
      }
      leaf retry-interval {
        description
          "Interval time  between two probing";
        type uint16 {
          range "1..3600";
        }
      }
    }
  }

  grouping live_ncs_config-ip-device-grouping {
    container tracking {
      description
        "Device tracking";
      presence "true";
      container probe {
        description
          "Probe";
        container auto-source {
          description
            "Probe source selection algorithm";
          presence "true";
          container fallback {
            description
              "Specify IP and MASK to use as last resort";
            leaf src-ip {
              description
                "IP and MASK of fallback source";
              type inet:ipv4-address;
            }
            leaf mask {
              description
                "IP prefix mask";
              type inet:ipv4-address;
            }
          }
          leaf override {
            description
              "Do not select source address from device track table";
            type empty;
          }
        }
        leaf count {
          description
            "Probe count";
          type uint8;
        }
        leaf delay {
          description
            "Probe delay";
          type uint8 {
            range "1..120";
          }
        }
        leaf interval {
          description
            "Probe interval";
          type uint32 {
            range "30..1814400";
          }
        }
      }
      leaf trace-buffer {
        description
          "Enable Tracing Support";
        type empty;
      }
    }
  }

  grouping config-interface-device-tracking-grouping {
    container device-tracking {
      description
        "Configure device-tracking on the interface";
      leaf attach-policy {
        description
          "Apply a policy for feature device-tracking";
        type string;
      }
    }
  }

  grouping config-device-tracking-grouping {
    list policy {
      description
        "Configure a policy for feature device-tracking";
      key "word";
      leaf word {
        type string;
      }
      container device-role {
        description
          "Sets the role of the device attached to the port";
        choice device-role-choice {
          case node {
            leaf node {
              type boolean;
              default "true";
            }
          }
          case switch {
            leaf switch {
              type empty;
            }
          }
        }
      }
      container protocol {
        description
          "Set the protocol to glean (default all)";
        leaf udp {
          type boolean;
        }
        leaf arp {
          description
            "Glean addresses in ARP packets";
          type boolean;
        }
        leaf dhcp4 {
          description
            "Glean addresses in DHCPv4 packets";
          type boolean;
        }
        leaf dhcp6 {
          description
            "Glean addresses in DHCPv6 packets";
          type boolean;
        }
        leaf ndp {
          description
            "Glean addresses in NDP packets";
          type boolean;
        }
      }
      container tracking {
        description
          "Override default tracking behavior";
        leaf tracking-on-off {
          description
            "Tracking on or off";
          type enumeration {
            enum "enable";
            enum "disable";
          }
        }
      }
      container limit {
        description
          "Specifies a limit";
        leaf address-count {
          description
            "Configure maximum address per port";
          type uint16 {
            range "1..32000";
          }
        }
      }
      container security-level {
        description
          "setup security level";
        leaf glean {
          description
            "glean addresses passively";
          type empty;
        }
      }
    }
    container tracking {
      presence "true";
      container auto-source {
        presence "true";
        container fallback {
          description
            "Specify IP and MASK to use as last resort";
          choice ip-subnet-choice {
            case ip-addr-and-mask {
              description
                "IPv4 and MASK of fallback source";
              container ipv4-subnet-type1 {
                leaf ipv4 {
                  description
                    "IPv4 address";
                  type inet:ipv4-address;
                }
                leaf mask {
                  description
                    "IP prefix mask";
                  type inet:ipv4-address;
                }
                leaf override {
                  description
                    "Do not select source address from device track table";
                  type empty;
                }
              }
            }
            case ip-addr-and-prefix-len {
              description
                "IPv4 and MASK of fallback source";
              container ipv4-subnet-type2 {
                leaf ipv4-prefix-name {
                  description
                    "ip address/length <network>/<length>, e.g., 192.168.0.0/16";
                  type ios-types:ipv4-address-slush-prefix-len;
                }
                leaf override {
                  description
                    "Do not select source address from device track table";
                  type empty;
                }
              }
            }
          }
        }
        leaf override {
          description
            "Do not select source address from device track table";
          type empty;
        }
      }
      leaf retry-interval {
        description
          "Interval time  between two probing";
        type uint16 {
          range "1..3600";
        }
      }
    }
  }

  grouping config-ip-device-grouping {
    container tracking {
      description
        "Device tracking";
      presence "true";
      container probe {
        description
          "Probe";
        container auto-source {
          description
            "Probe source selection algorithm";
          presence "true";
          container fallback {
            description
              "Specify IP and MASK to use as last resort";
            leaf src-ip {
              description
                "IP and MASK of fallback source";
              type inet:ipv4-address;
            }
            leaf mask {
              description
                "IP prefix mask";
              type inet:ipv4-address;
            }
          }
          leaf override {
            description
              "Do not select source address from device track table";
            type empty;
          }
        }
        leaf count {
          description
            "Probe count";
          type uint8;
        }
        leaf delay {
          description
            "Probe delay";
          type uint8 {
            range "1..120";
          }
        }
        leaf interval {
          description
            "Probe interval";
          type uint32 {
            range "30..1814400";
          }
        }
      }
      leaf trace-buffer {
        description
          "Enable Tracing Support";
        type empty;
      }
    }
  }

  augment "/ncs:devices/ncs:template/ncs:config/ios:native/ios:device-tracking" {
    uses ncs_template_config-device-tracking-grouping;
  }
  augment "/ncs:devices/ncs:device/ncs:live-status/ios:native/ios:device-tracking" {
    uses live_ncs_config-device-tracking-grouping {
      refine tracking {
        tailf:ncs-device-type "netconf";
        tailf:display-when "not(../../../../ncs:module) or ../../../../ncs:module[ncs:name='Cisco-IOS-XE-device-tracking'] or (../../../../ncs:live-status-protocol[not(ncs:capability)]) or (../../../../ncs:live-status-protocol/ncs:capability/ncs:module[.='Cisco-IOS-XE-device-tracking'])";
      }
      refine policy {
        tailf:ncs-device-type "netconf";
        tailf:display-when "not(../../../ncs:module) or ../../../ncs:module[ncs:name='Cisco-IOS-XE-device-tracking'] or (../../../ncs:live-status-protocol[not(ncs:capability)]) or (../../../ncs:live-status-protocol/ncs:capability/ncs:module[.='Cisco-IOS-XE-device-tracking'])";
      }
    }
  }
  augment "/ncs:devices/ncs:device/ncs:config/ios:native/ios:device-tracking" {
    uses config-device-tracking-grouping {
      refine tracking {
        tailf:ncs-device-type "netconf";
        tailf:display-when "not(../../../../ncs:module) or ../../../../ncs:module[ncs:name='Cisco-IOS-XE-device-tracking']";
      }
      refine policy {
        tailf:ncs-device-type "netconf";
        tailf:display-when "not(../../../ncs:module) or ../../../ncs:module[ncs:name='Cisco-IOS-XE-device-tracking']";
      }
    }
  }
  augment "/ncs:devices/ncs:template/ncs:config/ios:native/ios:ip/ios:device" {
    uses ncs_template_config-ip-device-grouping {
      // NCS drop if-feature statement
    }
  }
  augment "/ncs:devices/ncs:device/ncs:live-status/ios:native/ios:ip/ios:device" {
    uses live_ncs_config-ip-device-grouping {
      refine tracking {
        tailf:ncs-device-type "netconf";
        tailf:display-when "not(../../../../../ncs:module) or ../../../../../ncs:module[ncs:name='Cisco-IOS-XE-device-tracking'] or (../../../../../ncs:live-status-protocol[not(ncs:capability)]) or (../../../../../ncs:live-status-protocol/ncs:capability/ncs:module[.='Cisco-IOS-XE-device-tracking'])";
      }
      // NCS drop if-feature statement
    }
  }
  augment "/ncs:devices/ncs:device/ncs:config/ios:native/ios:ip/ios:device" {
    uses config-ip-device-grouping {
      refine tracking {
        tailf:ncs-device-type "netconf";
        tailf:display-when "not(../../../../../ncs:module) or ../../../../../ncs:module[ncs:name='Cisco-IOS-XE-device-tracking']";
      }
      // NCS drop if-feature statement
    }
  }
}
