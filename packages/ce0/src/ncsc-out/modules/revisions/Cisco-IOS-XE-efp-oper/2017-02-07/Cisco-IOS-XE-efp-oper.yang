module Cisco-IOS-XE-efp-oper {
  // Generated by yanger -t ncs
  tailf:ncs-device-type "netconf";

  yang-version "1";
  namespace "http://cisco.com/ns/yang/Cisco-IOS-XE-efp-oper";
  prefix efp-stats-ios-xe-oper;

  import ietf-yang-types {
    prefix yang;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for service instance (efp) stats.
     Copyright (c) 2016-2017 by Cisco Systems, Inc.
     All rights reserved.";

  revision 2017-02-07 {
    description
      "Initial revision";
    reference "1.0.0";
  }

  grouping ncs_template_efp-key {
    description
      "Each efp record is uniquely identified by interface and id";
    leaf id {
      type string;
      description
        "EFP id";
    }
    leaf interface {
      type string;
      description
        "Interface name";
    }
  }

  grouping ncs_template_efp-params {
    description
      "EFP parameters";
    leaf in-pkts {
      type string;
      description
        "Incoming packets";
    }
    leaf in-bytes {
      type string;
      description
        "Incoming bytes";
    }
    leaf out-pkts {
      type string;
      description
        "Outgoing packets";
    }
    leaf out-bytes {
      type string;
      description
        "Outgoing bytes";
    }
  }

  grouping ncs_rpc_notif_efp-key {
    description
      "Each efp record is uniquely identified by interface and id";
    leaf id {
      type uint32;
      description
        "EFP id";
    }
    leaf interface {
      type string;
      description
        "Interface name";
    }
  }

  grouping ncs_rpc_notif_efp-params {
    description
      "EFP parameters";
    leaf in-pkts {
      type yang:counter64;
      description
        "Incoming packets";
    }
    leaf in-bytes {
      type yang:counter64;
      description
        "Incoming bytes";
    }
    leaf out-pkts {
      type yang:counter64;
      description
        "Outgoing packets";
    }
    leaf out-bytes {
      type yang:counter64;
      description
        "Outgoing bytes";
    }
  }

  grouping live_ncs_efp-key {
    description
      "Each efp record is uniquely identified by interface and id";
    leaf id {
      type uint32;
      description
        "EFP id";
    }
    leaf interface {
      type string;
      description
        "Interface name";
    }
  }

  grouping live_ncs_efp-params {
    description
      "EFP parameters";
    leaf in-pkts {
      type yang:counter64;
      description
        "Incoming packets";
    }
    leaf in-bytes {
      type yang:counter64;
      description
        "Incoming bytes";
    }
    leaf out-pkts {
      type yang:counter64;
      description
        "Outgoing packets";
    }
    leaf out-bytes {
      type yang:counter64;
      description
        "Outgoing bytes";
    }
  }

  grouping efp-key {
    description
      "Each efp record is uniquely identified by interface and id";
    leaf id {
      type uint32;
      description
        "EFP id";
    }
    leaf interface {
      type string;
      description
        "Interface name";
    }
  }

  grouping efp-params {
    description
      "EFP parameters";
    leaf in-pkts {
      type yang:counter64;
      description
        "Incoming packets";
    }
    leaf in-bytes {
      type yang:counter64;
      description
        "Incoming bytes";
    }
    leaf out-pkts {
      type yang:counter64;
      description
        "Outgoing packets";
    }
    leaf out-bytes {
      type yang:counter64;
      description
        "Outgoing bytes";
    }
  }

  augment "/ncs:devices/ncs:device/ncs:config" {
    // NCS drop config false container 'efp-stats'
  }
  augment "/ncs:devices/ncs:device/ncs:live-status" {
    container efp-stats {
      tailf:ncs-device-type "netconf";
      tailf:display-when "not(../../ncs:module) or ../../ncs:module[ncs:name='Cisco-IOS-XE-efp-oper'] or (../../ncs:live-status-protocol[not(ncs:capability)]) or (../../ncs:live-status-protocol/ncs:capability/ncs:module[.='Cisco-IOS-XE-efp-oper'])";
      description
        "Service instance stats";
      list efp-stat {
        key "id interface";
        description
          "List of service instance stats";
        uses efp-stats-ios-xe-oper:live_ncs_efp-key;
        uses efp-stats-ios-xe-oper:live_ncs_efp-params;
      }
    }
  }
  augment "/ncs:devices/ncs:template/ncs:config" {
    // NCS drop config false container 'efp-stats'
  }
}
