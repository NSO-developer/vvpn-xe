module Cisco-IOS-XE-features {
  // Generated by yanger -t ncs
  tailf:ncs-device-type "netconf";

  namespace "http://cisco.com/ns/yang/Cisco-IOS-XE-features";
  prefix ios-features;

  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE feature Definitions
     Copyright (c) 2016-2017 by Cisco Systems, Inc.
     All rights reserved.";

  revision 2017-02-07 {
    description
      "Initial revision";
  }

  feature vlan {
    description
      "Vlan feature";
  }

  feature virtual-template {
    description
      "Virtual-template commands";
  }

  feature transceiver {
    description
      "Transceiver commands";
  }

  feature tod-clock {
    description
      "Time of Day clock feature";
  }

  feature table-map {
    description
      "table-map feature";
  }

  feature switch-virtual {
    description
      "Switch-virtual feature";
  }

  feature setup {
    description
      "Express setup feature";
  }

  feature qos-qsm {
    description
      "QoS queue softmax multiplier";
  }

  feature punt-num {
    description
      "Police punt feature";
  }

  feature private-vlan {
    description
      "Private-vlan feature";
  }

  feature parameter-map {
    description
      "Parameter Map feature";
  }

  feature mls {
    description
      "Multilayer Switching feature";
  }

  feature multilink {
    description
      "PPP multilink global configuration";
  }

  feature module {
    description
      "Device module feature";
  }

  feature mem-size {
    description
      "Memory size commands";
  }

  feature l2vpn {
    description
      "Layer2 VPN feature";
  }

  feature l2 {
    description
      "Layer2 VPN feature";
  }

  feature ezpm {
    description
      "Easy Performance Monitor feature";
  }

  feature eth-evc {
    description
      "Ethernet Virtual Circuit (EVC) feature";
  }

  feature esmc {
    description
      "Ethernet Synchronization Messaging Channel (esmc) feature";
  }

  feature efp {
    description
      "Ethernet Flow Point (efp) feature";
  }

  feature dot1x {
    description
      "dot1x feature";
  }

  feature device-tracking {
    description
      "device-tracking feature";
  }

  feature crypto {
    description
      "crypto feature";
  }

  feature switching-platform {
    description
      "switching platform specific features";
  }
}
