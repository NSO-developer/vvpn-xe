module Cisco-IOS-XE-icmp {
  // Generated by yanger -t ncs
  tailf:ncs-device-type "netconf";

  namespace "http://cisco.com/ns/yang/Cisco-IOS-XE-icmp";
  prefix ios-icmp;

  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Internet Control Message Protocol (ICMP) Yang model.
     Copyright (c) 2016 by Cisco Systems, Inc.
     All rights reserved.";

  revision 2017-02-07 {
    description
      "Initial revision";
  }

  grouping ncs_template_config-icmp-grouping {
    container icmp {
      description
        "ICMP options";
      container rate-limit {
        description
          "rate limit ICMP messages generated";
        container unreachable {
          description
            "ICMP type 3, Destination Unreachable";
          leaf time {
            description
              "Once per milliseconds";
            type string;
          }
          container DF {
            description
              "code 4, fragmentation needed and DF set";
            leaf time {
              description
                "Once per milliseconds";
              type string;
            }
          }
          container log {
            description
              "log message if rate limiting is excessive";
            presence "true";
            leaf number-unreachables {
              description
                "number of unreachables within interval to trigger a message";
              type string;
            }
            leaf log-message {
              description
                "log message once per milliseconds";
              type string;
            }
          }
        }
        leaf redirect {
          description
            "description";
          type string;
        }
      }
    }
  }

  grouping ncs_template_config-interface-ip-icmp-grouping {
    leaf unreachables {
      description
        "Enable sending ICMP Unreachable messages";
      type string;
    }
  }

  grouping ncs_rpc_notif_config-icmp-grouping {
    container icmp {
      description
        "ICMP options";
      container rate-limit {
        description
          "rate limit ICMP messages generated";
        container unreachable {
          description
            "ICMP type 3, Destination Unreachable";
          leaf time {
            description
              "Once per milliseconds";
            type uint32;
          }
          container DF {
            description
              "code 4, fragmentation needed and DF set";
            leaf time {
              description
                "Once per milliseconds";
              type uint32;
            }
          }
          container log {
            description
              "log message if rate limiting is excessive";
            presence "true";
            leaf number-unreachables {
              description
                "number of unreachables within interval to trigger a message";
              type uint32;
            }
            leaf log-message {
              description
                "log message once per milliseconds";
              type uint32 {
                range "10000..4294967295";
              }
            }
          }
        }
        leaf redirect {
          description
            "description";
          type enumeration {
            enum "host";
            enum "subnet";
          }
        }
      }
    }
  }

  grouping ncs_rpc_notif_config-interface-ip-icmp-grouping {
    leaf unreachables {
      description
        "Enable sending ICMP Unreachable messages";
      type boolean;
    }
  }

  grouping live_ncs_config-icmp-grouping {
    container icmp {
      description
        "ICMP options";
      container rate-limit {
        description
          "rate limit ICMP messages generated";
        container unreachable {
          description
            "ICMP type 3, Destination Unreachable";
          leaf time {
            description
              "Once per milliseconds";
            type uint32;
          }
          container DF {
            description
              "code 4, fragmentation needed and DF set";
            leaf time {
              description
                "Once per milliseconds";
              type uint32;
            }
          }
          container log {
            description
              "log message if rate limiting is excessive";
            presence "true";
            leaf number-unreachables {
              description
                "number of unreachables within interval to trigger a message";
              type uint32;
            }
            leaf log-message {
              description
                "log message once per milliseconds";
              type uint32 {
                range "10000..4294967295";
              }
            }
          }
        }
        leaf redirect {
          description
            "description";
          type enumeration {
            enum "host";
            enum "subnet";
          }
        }
      }
    }
  }

  grouping live_ncs_config-interface-ip-icmp-grouping {
    leaf unreachables {
      description
        "Enable sending ICMP Unreachable messages";
      type boolean;
    }
  }

  grouping config-icmp-grouping {
    container icmp {
      description
        "ICMP options";
      container rate-limit {
        description
          "rate limit ICMP messages generated";
        container unreachable {
          description
            "ICMP type 3, Destination Unreachable";
          leaf time {
            description
              "Once per milliseconds";
            type uint32;
          }
          container DF {
            description
              "code 4, fragmentation needed and DF set";
            leaf time {
              description
                "Once per milliseconds";
              type uint32;
            }
          }
          container log {
            description
              "log message if rate limiting is excessive";
            presence "true";
            leaf number-unreachables {
              description
                "number of unreachables within interval to trigger a message";
              type uint32;
            }
            leaf log-message {
              description
                "log message once per milliseconds";
              type uint32 {
                range "10000..4294967295";
              }
            }
          }
        }
        leaf redirect {
          description
            "description";
          type enumeration {
            enum "host";
            enum "subnet";
          }
        }
      }
    }
  }

  grouping config-interface-ip-icmp-grouping {
    leaf unreachables {
      description
        "Enable sending ICMP Unreachable messages";
      type boolean;
    }
  }

  augment "/ncs:devices/ncs:template/ncs:config/ios:native/ios:ip" {
    uses ncs_template_config-icmp-grouping;
  }
  augment "/ncs:devices/ncs:device/ncs:live-status/ios:native/ios:ip" {
    uses live_ncs_config-icmp-grouping {
      refine icmp {
        tailf:ncs-device-type "netconf";
        tailf:display-when "not(../../../../ncs:module) or ../../../../ncs:module[ncs:name='Cisco-IOS-XE-icmp'] or (../../../../ncs:live-status-protocol[not(ncs:capability)]) or (../../../../ncs:live-status-protocol/ncs:capability/ncs:module[.='Cisco-IOS-XE-icmp'])";
      }
    }
  }
  augment "/ncs:devices/ncs:device/ncs:config/ios:native/ios:ip" {
    uses config-icmp-grouping {
      refine icmp {
        tailf:ncs-device-type "netconf";
        tailf:display-when "not(../../../../ncs:module) or ../../../../ncs:module[ncs:name='Cisco-IOS-XE-icmp']";
      }
    }
  }
  augment "/ncs:devices/ncs:template/ncs:config/ios:native/ios:interface/ios:FastEthernet/ios:ip" {
    uses ncs_template_config-interface-ip-icmp-grouping;
  }
  augment "/ncs:devices/ncs:device/ncs:live-status/ios:native/ios:interface/ios:FastEthernet/ios:ip" {
    uses live_ncs_config-interface-ip-icmp-grouping {
      refine unreachables {
        tailf:ncs-device-type "netconf";
        tailf:display-when "not(../../../../../../ncs:module) or ../../../../../../ncs:module[ncs:name='Cisco-IOS-XE-icmp'] or (../../../../../../ncs:live-status-protocol[not(ncs:capability)]) or (../../../../../../ncs:live-status-protocol/ncs:capability/ncs:module[.='Cisco-IOS-XE-icmp'])";
      }
    }
  }
  augment "/ncs:devices/ncs:device/ncs:config/ios:native/ios:interface/ios:FastEthernet/ios:ip" {
    uses config-interface-ip-icmp-grouping {
      refine unreachables {
        tailf:ncs-device-type "netconf";
        tailf:display-when "not(../../../../../../ncs:module) or ../../../../../../ncs:module[ncs:name='Cisco-IOS-XE-icmp']";
      }
    }
  }
  augment "/ncs:devices/ncs:template/ncs:config/ios:native/ios:interface/ios:GigabitEthernet/ios:ip" {
    uses ncs_template_config-interface-ip-icmp-grouping;
  }
  augment "/ncs:devices/ncs:device/ncs:live-status/ios:native/ios:interface/ios:GigabitEthernet/ios:ip" {
    uses live_ncs_config-interface-ip-icmp-grouping {
      refine unreachables {
        tailf:ncs-device-type "netconf";
        tailf:display-when "not(../../../../../../ncs:module) or ../../../../../../ncs:module[ncs:name='Cisco-IOS-XE-icmp'] or (../../../../../../ncs:live-status-protocol[not(ncs:capability)]) or (../../../../../../ncs:live-status-protocol/ncs:capability/ncs:module[.='Cisco-IOS-XE-icmp'])";
      }
    }
  }
  augment "/ncs:devices/ncs:device/ncs:config/ios:native/ios:interface/ios:GigabitEthernet/ios:ip" {
    uses config-interface-ip-icmp-grouping {
      refine unreachables {
        tailf:ncs-device-type "netconf";
        tailf:display-when "not(../../../../../../ncs:module) or ../../../../../../ncs:module[ncs:name='Cisco-IOS-XE-icmp']";
      }
    }
  }
  augment "/ncs:devices/ncs:template/ncs:config/ios:native/ios:interface/ios:TenGigabitEthernet/ios:ip" {
    uses ncs_template_config-interface-ip-icmp-grouping;
  }
  augment "/ncs:devices/ncs:device/ncs:live-status/ios:native/ios:interface/ios:TenGigabitEthernet/ios:ip" {
    uses live_ncs_config-interface-ip-icmp-grouping {
      refine unreachables {
        tailf:ncs-device-type "netconf";
        tailf:display-when "not(../../../../../../ncs:module) or ../../../../../../ncs:module[ncs:name='Cisco-IOS-XE-icmp'] or (../../../../../../ncs:live-status-protocol[not(ncs:capability)]) or (../../../../../../ncs:live-status-protocol/ncs:capability/ncs:module[.='Cisco-IOS-XE-icmp'])";
      }
    }
  }
  augment "/ncs:devices/ncs:device/ncs:config/ios:native/ios:interface/ios:TenGigabitEthernet/ios:ip" {
    uses config-interface-ip-icmp-grouping {
      refine unreachables {
        tailf:ncs-device-type "netconf";
        tailf:display-when "not(../../../../../../ncs:module) or ../../../../../../ncs:module[ncs:name='Cisco-IOS-XE-icmp']";
      }
    }
  }
  augment "/ncs:devices/ncs:template/ncs:config/ios:native/ios:interface/ios:Tunnel/ios:ip" {
    uses ncs_template_config-interface-ip-icmp-grouping;
  }
  augment "/ncs:devices/ncs:device/ncs:live-status/ios:native/ios:interface/ios:Tunnel/ios:ip" {
    uses live_ncs_config-interface-ip-icmp-grouping {
      refine unreachables {
        tailf:ncs-device-type "netconf";
        tailf:display-when "not(../../../../../../ncs:module) or ../../../../../../ncs:module[ncs:name='Cisco-IOS-XE-icmp'] or (../../../../../../ncs:live-status-protocol[not(ncs:capability)]) or (../../../../../../ncs:live-status-protocol/ncs:capability/ncs:module[.='Cisco-IOS-XE-icmp'])";
      }
    }
  }
  augment "/ncs:devices/ncs:device/ncs:config/ios:native/ios:interface/ios:Tunnel/ios:ip" {
    uses config-interface-ip-icmp-grouping {
      refine unreachables {
        tailf:ncs-device-type "netconf";
        tailf:display-when "not(../../../../../../ncs:module) or ../../../../../../ncs:module[ncs:name='Cisco-IOS-XE-icmp']";
      }
    }
  }
  augment "/ncs:devices/ncs:template/ncs:config/ios:native/ios:interface/ios:FastEthernet/ios:ipv6" {
    uses ncs_template_config-interface-ip-icmp-grouping;
  }
  augment "/ncs:devices/ncs:device/ncs:live-status/ios:native/ios:interface/ios:FastEthernet/ios:ipv6" {
    uses live_ncs_config-interface-ip-icmp-grouping {
      refine unreachables {
        tailf:ncs-device-type "netconf";
        tailf:display-when "not(../../../../../../ncs:module) or ../../../../../../ncs:module[ncs:name='Cisco-IOS-XE-icmp'] or (../../../../../../ncs:live-status-protocol[not(ncs:capability)]) or (../../../../../../ncs:live-status-protocol/ncs:capability/ncs:module[.='Cisco-IOS-XE-icmp'])";
      }
    }
  }
  augment "/ncs:devices/ncs:device/ncs:config/ios:native/ios:interface/ios:FastEthernet/ios:ipv6" {
    uses config-interface-ip-icmp-grouping {
      refine unreachables {
        tailf:ncs-device-type "netconf";
        tailf:display-when "not(../../../../../../ncs:module) or ../../../../../../ncs:module[ncs:name='Cisco-IOS-XE-icmp']";
      }
    }
  }
  augment "/ncs:devices/ncs:template/ncs:config/ios:native/ios:interface/ios:GigabitEthernet/ios:ipv6" {
    uses ncs_template_config-interface-ip-icmp-grouping;
  }
  augment "/ncs:devices/ncs:device/ncs:live-status/ios:native/ios:interface/ios:GigabitEthernet/ios:ipv6" {
    uses live_ncs_config-interface-ip-icmp-grouping {
      refine unreachables {
        tailf:ncs-device-type "netconf";
        tailf:display-when "not(../../../../../../ncs:module) or ../../../../../../ncs:module[ncs:name='Cisco-IOS-XE-icmp'] or (../../../../../../ncs:live-status-protocol[not(ncs:capability)]) or (../../../../../../ncs:live-status-protocol/ncs:capability/ncs:module[.='Cisco-IOS-XE-icmp'])";
      }
    }
  }
  augment "/ncs:devices/ncs:device/ncs:config/ios:native/ios:interface/ios:GigabitEthernet/ios:ipv6" {
    uses config-interface-ip-icmp-grouping {
      refine unreachables {
        tailf:ncs-device-type "netconf";
        tailf:display-when "not(../../../../../../ncs:module) or ../../../../../../ncs:module[ncs:name='Cisco-IOS-XE-icmp']";
      }
    }
  }
  augment "/ncs:devices/ncs:template/ncs:config/ios:native/ios:interface/ios:TenGigabitEthernet/ios:ipv6" {
    uses ncs_template_config-interface-ip-icmp-grouping;
  }
  augment "/ncs:devices/ncs:device/ncs:live-status/ios:native/ios:interface/ios:TenGigabitEthernet/ios:ipv6" {
    uses live_ncs_config-interface-ip-icmp-grouping {
      refine unreachables {
        tailf:ncs-device-type "netconf";
        tailf:display-when "not(../../../../../../ncs:module) or ../../../../../../ncs:module[ncs:name='Cisco-IOS-XE-icmp'] or (../../../../../../ncs:live-status-protocol[not(ncs:capability)]) or (../../../../../../ncs:live-status-protocol/ncs:capability/ncs:module[.='Cisco-IOS-XE-icmp'])";
      }
    }
  }
  augment "/ncs:devices/ncs:device/ncs:config/ios:native/ios:interface/ios:TenGigabitEthernet/ios:ipv6" {
    uses config-interface-ip-icmp-grouping {
      refine unreachables {
        tailf:ncs-device-type "netconf";
        tailf:display-when "not(../../../../../../ncs:module) or ../../../../../../ncs:module[ncs:name='Cisco-IOS-XE-icmp']";
      }
    }
  }
  augment "/ncs:devices/ncs:template/ncs:config/ios:native/ios:interface/ios:Tunnel/ios:ipv6" {
    uses ncs_template_config-interface-ip-icmp-grouping;
  }
  augment "/ncs:devices/ncs:device/ncs:live-status/ios:native/ios:interface/ios:Tunnel/ios:ipv6" {
    uses live_ncs_config-interface-ip-icmp-grouping {
      refine unreachables {
        tailf:ncs-device-type "netconf";
        tailf:display-when "not(../../../../../../ncs:module) or ../../../../../../ncs:module[ncs:name='Cisco-IOS-XE-icmp'] or (../../../../../../ncs:live-status-protocol[not(ncs:capability)]) or (../../../../../../ncs:live-status-protocol/ncs:capability/ncs:module[.='Cisco-IOS-XE-icmp'])";
      }
    }
  }
  augment "/ncs:devices/ncs:device/ncs:config/ios:native/ios:interface/ios:Tunnel/ios:ipv6" {
    uses config-interface-ip-icmp-grouping {
      refine unreachables {
        tailf:ncs-device-type "netconf";
        tailf:display-when "not(../../../../../../ncs:module) or ../../../../../../ncs:module[ncs:name='Cisco-IOS-XE-icmp']";
      }
    }
  }
}
