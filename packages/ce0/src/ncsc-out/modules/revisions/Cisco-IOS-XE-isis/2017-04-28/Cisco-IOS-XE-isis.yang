module Cisco-IOS-XE-isis {
  // Generated by yanger -t ncs
  tailf:ncs-device-type "netconf";

  namespace "http://cisco.com/ns/yang/Cisco-IOS-XE-isis";
  prefix ios-isis;

  import ietf-inet-types {
    prefix inet;
  }
  import Cisco-IOS-XE-types {
    prefix ios-types;
  }
  import Cisco-IOS-XE-interface-common {
    prefix ios-ifc;
  }
  import Cisco-IOS-XE-snmp {
    prefix ios-snmp;
  }
  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Intermediate System-to-Intermediate System (IS-IS) Yang model.
     Copyright (c) 2016-2017 by Cisco Systems, Inc.
     All rights reserved.";

  revision 2017-04-28 {
    description
      "inet:ipv6-prefix changed to ios-types:ipv6-prefix";
  }
  revision 2017-03-28 {
    description
      "Added NED Yang Data Model support for MPLS-TE";
  }
  revision 2017-02-07 {
    description
      "Initial revision";
  }

  typedef authentication-level-type {
    type enumeration {
      enum "level-1";
      enum "level-2";
    }
  }

  typedef isis-routes-level-type {
    type enumeration {
      enum "level-1";
      enum "level-1-2";
      enum "level-2";
    }
  }

  typedef isis-level-type {
    type enumeration {
      enum "level-1";
      enum "level-1-2";
      enum "level-2";
    }
  }

  typedef isis-net {
    type string;
  }

  grouping ncs_template_config-interface-isis-grouping {
    container adjacency-filter {
      description
        "Filter IS-IS adjacencies";
      leaf name {
        type string;
      }
      leaf match-all {
        description
          "Match all area addresses";
        type empty;
      }
    }
    container advertise {
      description
        "Control addresses advertisements in LSPs";
      leaf prefix {
        description
          "Interface IP address";
        type empty;
      }
    }
    container authentication {
      description
        "ISIS authentication for interface related PDUs";
      uses ncs_template_isis-authentication-grouping;
    }
    container circuit-type {
      description
        "Configure circuit type for interface";
      presence "true";
      leaf levels {
        type string;
      }
    }
    container csnp-interval {
      description
        "Set CSNP interval in seconds";
      choice csnp-interval-choice {
        case csnp-interval-level-case {
          list csnp-interval-list {
            // NCS patched for predictable order
            ordered-by user;
            key "levels";
            leaf levels {
              type string;
            }
            leaf value {
              type string;
            }
          }
        }
        case csnp-interval-only-case {
          leaf value {
            type string;
          }
        }
      }
    }
    container hello {
      description
        "Add padding to IS-IS hello packets";
      container padding {
        description
          "Pad hello packets";
        presence "true";
        leaf always {
          description
            "Never pad hello packets if no prefix present";
          type empty;
        }
      }
    }
    container hello-interval {
      description
        "Set Hello interval in seconds";
      choice hello-interval-choice {
        case hello-interval-level-case {
          list hello-interval-list {
            // NCS patched for predictable order
            ordered-by user;
            key "levels";
            leaf levels {
              type string;
            }
            leaf value {
              type string;
            }
          }
        }
        case hello-interval-only-case {
          leaf value {
            type string;
          }
        }
      }
    }
    container hello-multiplier {
      description
        "Set multiplier for Hello holding time";
      choice hello-multiplier-choice {
        case hello-multiplier-level-case {
          list hello-multiplier-list {
            // NCS patched for predictable order
            ordered-by user;
            key "levels";
            leaf levels {
              type string;
            }
            leaf value {
              type string;
            }
          }
        }
        case hello-multiplier-only-case {
          leaf value {
            type string;
          }
        }
      }
    }
    container ipv6 {
      description
        "IPv6 interface configuration";
      uses ncs_template_isis-metric-grouping;
      leaf tag {
        description
          "Assign an admin tag to an ISIS interface IPv6 route";
        type string;
      }
    }
    leaf lsp-interval {
      description
        "Set LSP transmission interval";
      type string;
    }
    leaf mesh-group {
      description
        "Set ISIS mesh group";
      type string;
    }
    uses ncs_template_isis-metric-grouping;
    leaf network {
      description
        "Network type";
      type string;
    }
    container password {
      description
        "Configure the authentication password for interface";
      choice password-choice {
        case password-level-case {
          list password-list {
            // NCS patched for predictable order
            ordered-by user;
            key "levels";
            leaf levels {
              type string;
            }
            leaf password {
              type string;
            }
          }
        }
        case password-only-case {
          leaf password {
            type string;
          }
        }
      }
    }
    container priority {
      description
        "Set priority for Designated Router election";
      choice priority-choice {
        case priority-level-case {
          list priority-list {
            // NCS patched for predictable order
            ordered-by user;
            key "levels";
            leaf levels {
              type string;
            }
            leaf value {
              type string;
            }
          }
        }
        case priority-only-case {
          leaf value {
            type string;
          }
        }
      }
    }
    leaf protocol {
      description
        "Set ISIS protocol's state under current interface";
      type string;
    }
    leaf retransmit-interval {
      description
        "Set per-LSP retransmission interval";
      type string;
    }
    leaf retransmit-throttle-interval {
      description
        "Set interface LSP retransmission interval";
      type string;
    }
    leaf tag {
      description
        "Assign an admin tag to an ISIS interface IP route";
      type string;
    }
    container three-way-handshake {
      description
        "Select Cisco or IETF three-way handshake";
      presence "true";
      leaf implementor {
        type string;
      }
    }
  }

  grouping ncs_template_narrow-wide-transition-grouping {
    leaf narrow-wide {
      type string;
    }
    leaf transition {
      description
        "Accept both styles of TLVs during transition";
      type string;
    }
  }

  grouping ncs_template_spf-intervals-grouping {
    leaf interval {
      type string;
    }
    leaf initial-wait {
      type string;
    }
    leaf minimum-wait {
      type string;
    }
  }

  grouping ncs_template_authenticate-snp-grouping {
    leaf authenticate {
      description
        "Authentication";
      type empty;
    }
    leaf snp {
      description
        "SNP PDUs";
      type string;
    }
  }

  grouping ncs_template_lsp-gen-interval-grouping {
    leaf interval {
      type string;
    }
    leaf initial-wait {
      type string;
    }
    leaf wait {
      type string;
    }
  }

  grouping ncs_template_set-overload-bit-suppress-grouping {
    leaf external {
      description
        "If overload-bit set, don't advertise IP prefixes learned from other protocols";
      type empty;
    }
    leaf interlevel {
      description
        "If overload-bit set, don't advertise IP prefixes learned from another ISIS level";
      type empty;
    }
  }

  grouping ncs_template_summary-address-metric-tag-grouping {
    leaf metric {
      description
        "Set metric for summay route";
      type string;
    }
    leaf tag {
      description
        "Set tag";
      type string;
    }
  }

  grouping ncs_template_authentication-level-grouping {
    leaf levels {
      type string;
    }
  }

  grouping ncs_template_isis-authentication-grouping {
    container mode {
      description
        "Authentication mode";
      container md5 {
        description
          "Keyed message digest";
        presence "Keyed message digest";
        uses ncs_template_authentication-level-grouping;
      }
      container text {
        description
          "Clear text password";
        presence "Clear text password";
        uses ncs_template_authentication-level-grouping;
      }
    }
    container key-chain {
      description
        "Authentication key-chain";
      choice key-chain-choice {
        case key-chain-level-case {
          list key-chain-list {
            // NCS patched for predictable order
            ordered-by user;
            key "levels";
            uses ncs_template_authentication-level-grouping;
            leaf name {
              type string;
            }
          }
        }
        case key-chain-only-case {
          leaf name {
            type string;
          }
        }
      }
    }
    container send-only {
      description
        "Authentication send only, receive ignore";
      presence "Authentication send only, receive ignore";
      uses ncs_template_authentication-level-grouping;
    }
  }

  grouping ncs_template_isis-metric-grouping {
    container metric {
      description
        "Configure the metric for interface";
      choice metric-choice {
        case metric-level-case {
          list metric-list {
            // NCS patched for predictable order
            ordered-by user;
            key "levels";
            leaf levels {
              type string;
            }
            leaf value {
              type string;
            }
          }
        }
        case metric-only-case {
          leaf value {
            type string;
          }
        }
      }
    }
  }

  grouping ncs_template_redist-level-grouping {
    leaf levels {
      type string;
    }
  }

  grouping ncs_template_isis-redist-grouping {
    leaf levels {
      type string;
    }
    leaf metric {
      description
        "ISIS default metric";
      type string;
    }
    leaf metric-type {
      description
        "OSPF/IS-IS exterior metric type for redistributed routes";
      type string;
    }
    leaf route-map {
      description
        "Route map reference";
      type string;
    }
  }

  grouping ncs_template_isis-redist-af-grouping {
    leaf include-connected {
      description
        "Include connected";
      type empty;
    }
    uses ncs_template_isis-redist-grouping;
  }

  grouping ncs_template_isis-redist-ospf-match-grouping {
    uses ncs_template_redist-level-grouping;
    leaf metric {
      description
        "ISIS default metric";
      type string;
    }
    leaf route-map {
      description
        "Route map reference";
      type string;
    }
  }

  grouping ncs_template_isis-redist-clns-ip-grouping {
    container clns {
      description
        "Redistribution of BGP NSAP routes";
      presence "Redistribution of BGP NSAP routes";
      uses ncs_template_isis-redist-grouping;
    }
    container ip {
      description
        "Redistribution of BGP IP routes";
      presence "true";
      uses ncs_template_isis-redist-grouping;
    }
  }

  grouping ncs_template_isis-ipv4-ipv6-common-grouping {
    leaf adjacency-check {
      description
        "Check ISIS neighbor protocol support";
      type empty;
    }
    container bfd {
      description
        "BFD configuration commands";
      leaf all-interfaces {
        description
          "Enable BFD on all interfaces";
        type empty;
      }
      leaf check-ctrl-plane-failure {
        description
          "BFD check control plane failure";
        type empty;
      }
    }
    leaf router-id {
      description
        "Interface of stable IP address for system";
      type string;
    }
  }

  grouping ncs_template_isis-common-grouping {
    container advertise {
      description
        "Control which IP routes flow in L1 and L2 LSPs";
      leaf passive-only {
        description
          "only interface address of passive interfaces";
        type empty;
      }
    }
    container default-information {
      description
        "Control distribution of default information";
      container originate {
        presence "Distribute a default route";
        description
          "Distribute a default route";
        leaf route-map {
          description
            "Route-map reference";
          type string;
        }
      }
    }
    leaf help {
      description
        "Description of the interactive help system";
      type empty;
    }
    leaf maximum-paths {
      description
        "Forward packets over multiple paths";
      type string;
    }
    container metric {
      description
        "Set ISIS metric for all interfaces";
      choice metric-choice {
        case metric-level-case {
          list metrics {
            // NCS patched for predictable order
            ordered-by user;
            key "level";
            leaf level {
              type string;
            }
            leaf metric {
              type string;
            }
          }
        }
        case metric-only-case {
          leaf metric {
            type string;
          }
        }
      }
    }
    container prc-interval {
      description
        "Minimum interval between partial route calculations";
      leaf interval {
        type string;
      }
      leaf initial-wait {
        type string;
      }
      leaf minimum-wait {
        type string;
      }
    }
    container set-overload-bit {
      description
        "Signal other routers not to use us in SPF";
      presence "Signal other routers not to use us in SPF";
      choice set-overload-bit-choice {
        container on-startup {
          description
            "Set overload-bit only temporarily after reboot";
          choice on-startup-choice {
            container time {
              leaf time {
                type string;
              }
              leaf suppress {
                description
                  "If overload-bit set, suppress the following types of IP prefixes";
                type empty;
              }
              leaf external {
                description
                  "If overload-bit set, don't advertise IP prefixes learned from other protocols";
                type empty;
              }
              leaf interlevel {
                description
                  "If overload-bit set, don't advertise IP prefixes learned from another ISIS level";
                type empty;
              }
            }
            container wait-for-bgp {
              description
                "Let BGP decide when to unset the overload bit";
              presence "Let BGP decide when to unset the overload bitW";
              container suppress {
                description
                  "If overload-bit set, suppress the following types of IP prefixes";
                uses ncs_template_set-overload-bit-suppress-grouping;
              }
            }
          }
        }
        container suppress {
          description
            "If overload-bit set, suppress the following types of IP prefixes";
          uses ncs_template_set-overload-bit-suppress-grouping;
        }
      }
    }
    container spf-interval {
      description
        "Minimum interval between SPF calculations";
      choice spf-interval-choice {
        list level-1-2 {
          // NCS patched for predictable order
          ordered-by user;
          key "level";
          leaf level {
            type string;
          }
          uses ncs_template_spf-intervals-grouping;
        }
        container intervals {
          uses ncs_template_spf-intervals-grouping;
        }
      }
    }
  }

  grouping ncs_template_isis-address-family-grouping {
    uses ncs_template_isis-common-grouping;
    uses ncs_template_isis-ipv4-ipv6-common-grouping;
    leaf distance {
      description
        "Administrative distance";
      type string;
    }
    container distribute-list {
      description
        "Filter networks in routing updates";
      list prefix-list {
        // NCS patched for predictable order
        ordered-by user;
        description
          "Filter connections based on an IPv6 prefix-list";
        key "name";
        leaf name {
          type string;
        }
        container in {
          description
            "Filter incoming routing updates";
          presence "true";
          container interface {
            description
              "Specify interface";
            uses ios-ifc:ncs_template_interface-grouping;
          }
        }
      }
    }
    container ipv6 {
      description
        "IPv6 specific commands";
      container route {
        description
          "ISIS IPV6 routes";
        container priority {
          description
            "Assign priority to IPV6 prefixes";
          container high {
            description
              "Assign high priority to important IPV6 prefixes in ISIS IPV6 local RIB";
            leaf tag {
              description
                "Assign high priority to IPV6 prefixes with a specific route tag";
              type string;
            }
          }
        }
      }
    }
    container multi-topology {
      description
        "Enable multi-topology mode";
      presence "Enable multi-topology mode";
      leaf transition {
        description
          "Accept and generate both IS-IS IPv6 and Multi-topology IPv6 TLVs";
        type empty;
      }
    }
    container redistribute {
      description
        "Redistribute IPv6 prefixes from another routing protocol";
      container application {
        description
          "Application Protocol";
        presence "Application Protocol";
        uses ncs_template_isis-redist-af-grouping;
      }
      container bgp {
        description
          "Border Gateway Protocol (BGP)";
        leaf as-number {
          type string;
        }
        uses ncs_template_isis-redist-af-grouping;
      }
      container connected {
        description
          "Connected";
        presence "Connected";
        uses ncs_template_isis-redist-grouping;
      }
      list eigrp {
        // NCS patched for predictable order
        ordered-by user;
        description
          "Enhanced Interior Gateway Routing Protocol (EIGRP)";
        key "as-number";
        leaf as-number {
          type string;
        }
        uses ncs_template_isis-redist-af-grouping;
      }
      container isis {
        description
          "ISO IS-IS";
        presence "true";
        list isis-redistribute {
          // NCS patched for predictable order
          ordered-by user;
          key "area-tag";
          leaf area-tag {
            type string;
          }
          uses ncs_template_isis-redist-af-grouping;
        }
        list isis-leak {
          // NCS patched for predictable order
          ordered-by user;
          key "isis-redist-levels1 isis-redist-levels2";
          leaf isis-redist-levels1 {
            type string;
          }
          leaf isis-redist-levels2 {
            type string;
          }
          leaf into {
            description
              "from level-n into level-m";
            type empty;
          }
          choice isis-redist-isis-ip-choice {
            leaf distribute-list {
              description
                "select routes";
              type string;
            }
            leaf route-map {
              description
                "Route map for route matching";
              type string;
            }
          }
        }
      }
      container lisp {
        description
          "Locator ID Separation Protocol (LISP)";
        presence "Locator ID Separation Protocol (LISP)";
        uses ncs_template_isis-redist-af-grouping;
      }
      container nd {
        description
          "Neighbor Discovery";
        presence "Neighbor Discovery";
        uses ncs_template_isis-redist-af-grouping;
      }
      container nemo {
        description
          "Network Mobility (NEMO)";
        uses ncs_template_isis-redist-af-grouping;
      }
      list ospf {
        // NCS patched for predictable order
        ordered-by user;
        description
          "Open Shortest Path First (OSPF)";
        key "process-id";
        leaf process-id {
          type string;
        }
        uses ncs_template_isis-redist-af-grouping;
        container match {
          description
            "Redistribution of OSPF routes";
          container internal {
            presence "Redistribute OSPF internal routes";
            description
              "Redistribute OSPF internal routes";
            uses ncs_template_isis-redist-grouping;
          }
          container external {
            description
              "Redistribute OSPF external routes";
            presence "Redistribute OSPF external routes";
            leaf external-routes {
              type string;
            }
            uses ncs_template_isis-redist-grouping;
          }
          container nssa-external {
            description
              "Redistribute OSPF NSSA external routes";
            presence "Redistribute OSPF NSSA external routes";
            leaf nssa-external-routes {
              type string;
            }
            uses ncs_template_isis-redist-grouping;
          }
        }
      }
      list rip {
        // NCS patched for predictable order
        ordered-by user;
        description
          "IPv6 Routing Information Protocol (RIPv6)";
        key "process";
        leaf process {
          type string;
        }
        uses ncs_template_isis-redist-af-grouping;
      }
      container static {
        description
          "Static routes";
        presence "Static routes";
        uses ncs_template_isis-redist-grouping;
      }
    }
    list summary-prefix {
      // NCS patched for predictable order
      ordered-by user;
      description
        "Configure IPv6 summary prefix";
      key "prefix";
      leaf prefix {
        type string;
      }
      leaf levels {
        type string;
      }
    }
    container table-map {
      description
        "Map external entry attributes into routing table";
      leaf name {
        type string;
      }
      leaf filter {
        description
          "Selective route download";
        type empty;
      }
    }
  }

  grouping ncs_template_isis-redist-vrf-grouping {
    container application {
      description
        "Application";
      list appname {
        // NCS patched for predictable order
        ordered-by user;
        key "appname";
        leaf appname {
          description
            "Application name";
          type string;
        }
        uses ncs_template_isis-redist-grouping;
      }
    }
    container bgp {
      description
        "Border Gateway Protocol (BGP)";
      list bp-as-num {
        // NCS patched for predictable order
        ordered-by user;
        key "bp-as-num";
        leaf bp-as-num {
          description
            "Autonomous system number";
          type string;
        }
        uses ncs_template_isis-redist-clns-ip-grouping;
        uses ncs_template_isis-redist-grouping;
      }
      leaf a_LESSER_1_PERIOD_0-XX_PERIOD_YY_GREATER_ {
        description
          "Autonomous system number";
        type empty;
      }
    }
    container connected {
      description
        "Connected";
      presence "true";
      uses ncs_template_isis-redist-grouping;
    }
    container eigrp {
      description
        "Enhanced Interior Gateway Routing Protocol (EIGRP)";
      list eigrp-as {
        // NCS patched for predictable order
        ordered-by user;
        key "eigrp-as";
        leaf eigrp-as {
          description
            "AS number";
          type string;
        }
        uses ncs_template_isis-redist-grouping;
      }
    }
    container isis {
      description
        "ISO IS-IS";
      list isis-atag {
        // NCS patched for predictable order
        ordered-by user;
        key "isis-atag";
        leaf isis-atag {
          description
            "ISO routing area tag";
          type string;
        }
        container ip {
          description
            "Redistribution of IP routes between levels or processes";
          uses ncs_template_isis-redist-grouping;
        }
      }
      container ip {
        description
          "Redistribution of IP routes between levels or processes";
        presence "true";
        uses ncs_template_isis-redist-grouping;
      }
    }
    container iso-igrp {
      description
        "IGRP for OSI networks";
      presence "true";
      list iso-atag {
        // NCS patched for predictable order
        ordered-by user;
        key "iso-atag";
        leaf iso-atag {
          description
            "ISO routing area tag";
          type string;
        }
        leaf route-map {
          description
            "Route map reference";
          type empty;
        }
      }
      container route-map {
        description
          "Route map reference";
        presence "true";
        leaf rm-point {
          description
            "Pointer to route-map entries";
          type string;
        }
      }
    }
    container lisp {
      description
        "Locator ID Separation Protocol (LISP)";
      presence "true";
      uses ncs_template_isis-redist-grouping;
    }
    container mobile {
      description
        "Mobile routes";
      presence "true";
      uses ncs_template_isis-redist-grouping;
    }
    leaf ospf {
      description
        "Process ID";
      type string;
    }
    container ospfv3 {
      description
        "OSPFv3";
      list os3-id {
        // NCS patched for predictable order
        ordered-by user;
        key "os3-id";
        leaf os3-id {
          description
            "Process ID";
          type string;
        }
        uses ncs_template_isis-redist-grouping;
      }
    }
    container rip {
      description
        "Routing Information Protocol (RIP)";
      presence "true";
      uses ncs_template_isis-redist-grouping;
    }
    container static {
      description
        "Static routes";
      presence "true";
      uses ncs_template_isis-redist-clns-ip-grouping;
      uses ncs_template_isis-redist-grouping;
    }
  }

  grouping ncs_template_tie-break-prefer-repair-grouping {
    leaf downstream {
      description
        "priority number";
      type string;
    }
    leaf linecard-disjoint {
      description
        "priority number";
      type string;
    }
    leaf lowest-backup-path-metric {
      description
        "priority number";
      type string;
    }
    leaf node-protecting {
      description
        "priority number";
      type string;
    }
    leaf primary-path {
      description
        "priority number";
      type string;
    }
    leaf secondary-path {
      description
        "priority number";
      type string;
    }
    leaf srlg-disjoint {
      description
        "priority number";
      type string;
    }
  }

  grouping ncs_template_isis-topology-grouping {
    list distance {
      // NCS patched for predictable order
      ordered-by user;
      description
        "Define an administrative distance";
      key "number";
      leaf number {
        type string;
      }
      list ip-list {
        // NCS patched for predictable order
        ordered-by user;
        key "ip";
        leaf ip {
          description
            "IP Source address";
          type string;
        }
        list wildcard-bits {
          // NCS patched for predictable order
          ordered-by user;
          key "w-bits";
          leaf w-bits {
            type string;
          }
          leaf access-list {
            type string;
          }
        }
      }
      leaf clns {
        description
          "Distance applied for CLNS derived routes";
        type empty;
      }
      leaf ip {
        description
          "Distance applied for IP derived routes";
        type empty;
      }
    }
    container ip {
      description
        "IP specific commands";
      container route {
        description
          "ISIS IP routes";
        container priority {
          description
            "Assign priority to IP prefixes";
          container high {
            description
              "Assign high priority to important IP prefixes in ISIS IP local RIB";
            leaf tag {
              description
                "Assign high priority to IP prefixes with a specific route tag";
              type string;
            }
          }
        }
      }
    }
    leaf priority {
      description
        "priority value";
      type string;
    }
    container redistribute {
      description
        "Redistribute information from another routing protocol";
      list application {
        // NCS patched for predictable order
        ordered-by user;
        description
          "Application";
        key "name";
        leaf name {
          description
            "Application name";
          type string;
        }
        uses ncs_template_isis-redist-grouping;
      }
      container bgp {
        description
          "Border Gateway Protocol (BGP)";
        leaf as-number {
          type string;
        }
        uses ncs_template_isis-redist-grouping;
        uses ncs_template_isis-redist-clns-ip-grouping;
      }
      container connected {
        description
          "Connected";
        presence "Connected";
        uses ncs_template_isis-redist-grouping;
      }
      list eigrp {
        // NCS patched for predictable order
        ordered-by user;
        description
          "Enhanced Interior Gateway Routing Protocol (EIGRP)";
        key "as-number";
        leaf as-number {
          type string;
        }
        uses ncs_template_isis-redist-grouping;
      }
      container isis {
        description
          "ISO IS-IS";
        list isis-redistribute {
          // NCS patched for predictable order
          ordered-by user;
          key "area-tag";
          leaf area-tag {
            type string;
          }
          container ip {
            description
              "Redistribution of IP routes between levels or processes";
            presence "true";
            uses ncs_template_isis-redist-grouping;
          }
        }
        list ip {
          // NCS patched for predictable order
          ordered-by user;
          description
            "Redistribution of IP routes between levels";
          key "isis-redist-levels1 isis-redist-levels2";
          leaf isis-redist-levels1 {
            type string;
          }
          leaf isis-redist-levels2 {
            type string;
          }
          leaf into {
            description
              "from level-n into level-m";
            type empty;
          }
          choice isis-redist-isis-ip-choice {
            leaf distribute-list {
              description
                "select routes";
              type string;
            }
            leaf route-map {
              description
                "Route map for route matching";
              type string;
            }
          }
        }
      }
      container iso-igrp {
        description
          "IGRP for OSI networks";
        presence "IGRP for OSI networks";
        choice iso-igrp-choice {
          container area-tag-route-map-container {
            leaf area-tag {
              type string;
            }
            leaf route-map {
              description
                "Route map reference";
              type string;
            }
          }
          leaf route-map {
            description
              "Route map reference";
            type string;
          }
        }
        uses ncs_template_redist-level-grouping;
        leaf metric {
          description
            "ISIS default metric";
          type string;
        }
        leaf metric-type {
          description
            "OSPF/IS-IS exterior metric type for redistributed routes";
          type string;
        }
      }
      container lisp {
        description
          "Locator ID Separation Protocol (LISP)";
        presence "true";
        uses ncs_template_isis-redist-af-grouping;
      }
      container maximum-prefix {
        description
          "Maximum number of prefixes redistributed to protocol";
        leaf number {
          type string;
        }
        leaf threshold-value {
          type string;
        }
        leaf warning-only {
          description
            "Only give warning message when limit is exceeded";
          type empty;
        }
        leaf withdraw {
          description
            "Withdraw redistibuted prefixes";
          type empty;
        }
      }
      container mobile {
        description
          "Mobile routes";
        presence "Mobile routes";
        uses ncs_template_isis-redist-grouping;
      }
      container odr {
        description
          "On Demand stub Routes";
        presence "On Demand stub Routes";
        uses ncs_template_isis-redist-grouping;
      }
      list ospf {
        // NCS patched for predictable order
        ordered-by user;
        description
          "Open Shortest Path First (OSPF)";
        key "process-id";
        leaf process-id {
          type string;
        }
        uses ncs_template_isis-redist-grouping;
        container match {
          description
            "Redistribution of OSPF routes";
          container internal {
            presence "Redistribute OSPF internal routes";
            description
              "Redistribute OSPF internal routes";
            uses ncs_template_isis-redist-grouping;
          }
          container external {
            description
              "Redistribute OSPF external routes";
            presence "Redistribute OSPF external routes";
            leaf external-routes {
              type string;
            }
            uses ncs_template_isis-redist-grouping;
          }
          container nssa-external {
            description
              "Redistribute OSPF NSSA external routes";
            presence "Redistribute OSPF NSSA external routes";
            leaf nssa-external-routes {
              type string;
            }
            uses ncs_template_isis-redist-grouping;
          }
        }
        leaf vrf {
          description
            "VPN Routing/Forwarding Instance";
          type string;
        }
      }
      list ospfv3 {
        // NCS patched for predictable order
        ordered-by user;
        description
          "Open Shortest Path First (OSPF)";
        key "process-id";
        leaf process-id {
          type string;
        }
        uses ncs_template_isis-redist-grouping;
        container match {
          description
            "Redistribution of OSPF routes";
          container internal {
            presence "Redistribute OSPF internal routes";
            description
              "Redistribute OSPF internal routes";
            uses ncs_template_isis-redist-grouping;
          }
          container external {
            description
              "Redistribute OSPF external routes";
            presence "Redistribute OSPF external routes";
            leaf external-routes {
              type string;
            }
            uses ncs_template_isis-redist-grouping;
          }
          container nssa-external {
            description
              "Redistribute OSPF NSSA external routes";
            presence "Redistribute OSPF NSSA external routes";
            leaf nssa-external-routes {
              type string;
            }
            uses ncs_template_isis-redist-grouping;
          }
        }
        leaf vrf {
          description
            "VPN Routing/Forwarding Instance";
          type string;
        }
      }
      container rip {
        description
          "Routing Information Protocol (RIP)";
        presence "Routing Information Protocol (RIP)";
        uses ncs_template_isis-redist-grouping;
      }
      container static {
        description
          "Static routes";
        presence "Static routes";
        uses ncs_template_isis-redist-clns-ip-grouping;
      }
      container vrf {
        description
          "Specify a source VRF";
        list vrf-nm {
          // NCS patched for predictable order
          ordered-by user;
          key "vrf-nm";
          leaf vrf-nm {
            description
              "Source VRF name";
            type string;
          }
          uses ncs_template_isis-redist-vrf-grouping;
        }
        container global {
          description
            "global VRF";
          uses ncs_template_isis-redist-vrf-grouping;
        }
      }
    }
    container set-attached-bit {
      description
        "Conditionally advertise us as attached to L2";
      leaf route-map {
        description
          "Route-map reference";
        type string;
      }
    }
    uses ios-snmp:ncs_template_router-snmp-grouping;
    list summary-address {
      // NCS patched for predictable order
      ordered-by user;
      description
        "Configure IP address summaries";
      key "ip mask";
      leaf ip {
        type string;
      }
      leaf mask {
        type string;
      }
      container level-1 {
        description
          "Summarize into level-1 area";
        presence "Summarize into level-1 area";
        uses ncs_template_summary-address-metric-tag-grouping;
      }
      container level-1-2 {
        description
          "Summarize into both area and sub-domain";
        presence "Summarize into both area and sub-domain";
        uses ncs_template_summary-address-metric-tag-grouping;
      }
      container level-2 {
        description
          "Summarize into level-2 sub-domain";
        presence "Summarize into level-2 sub-domain";
        uses ncs_template_summary-address-metric-tag-grouping;
      }
      container metric-tag-container {
        uses ncs_template_summary-address-metric-tag-grouping;
      }
    }
    container traffic-share {
      description
        "How to compute traffic share over alternate paths";
      container min {
        description
          "All traffic shared among min metric paths";
        leaf across-interfaces {
          description
            "Use different interfaces for equal-cost paths";
          type empty;
        }
      }
    }
    uses ncs_template_isis-common-grouping;
  }

  grouping ncs_template_isis-af-ipv4-grouping {
    leaf help {
      description
        "Description of the interactive help system";
      type empty;
    }
    uses ios-snmp:ncs_template_router-snmp-grouping;
    list topology {
      // NCS patched for predictable order
      ordered-by user;
      description
        "Associate the routing protocol to a topology instance";
      key "name";
      leaf name {
        type string;
      }
      leaf tid {
        description
          "Configuring the routing protocol topology tid";
        type string;
      }
      leaf ignore-attached-bit {
        description
          "Never install default route to closest L2 router";
        type empty;
      }
      uses ncs_template_isis-topology-grouping;
    }
  }

  grouping ncs_template_config-isis-main-grouping {
    container metric-style {
      description
        "Use old-style (ISO 10589) or new-style packet formats";
      choice metric-style-choice {
        container narrow {
          description
            "Use old style of TLVs with narrow metric";
          presence "true";
          uses ncs_template_narrow-wide-transition-grouping;
        }
        container transition {
          description
            "Send and accept both styles of TLVs during transition";
          presence "true";
          leaf transition {
            type string;
          }
        }
        container wide {
          description
            "Use new style of TLVs to carry wider metric";
          presence "true";
          uses ncs_template_narrow-wide-transition-grouping;
        }
      }
    }
    container address-family {
      description
        "Enter Address Family command mode";
      container ipv4 {
        description
          "Address family";
        leaf unicast-multicast {
          type string;
        }
        uses ncs_template_isis-af-ipv4-grouping;
      }
      container ipv6 {
        description
          "Address family";
        leaf unicast {
          type empty;
        }
        uses ncs_template_isis-address-family-grouping;
      }
    }
    uses ncs_template_isis-topology-grouping;
    container area-password {
      description
        "Configure the authentication password for an area";
      leaf name {
        type string;
      }
      uses ncs_template_authenticate-snp-grouping;
    }
    container authentication {
      description
        "ISIS authentication for LSPs";
      uses ncs_template_isis-authentication-grouping;
    }
    container distribute-list {
      description
        "Filter networks in routing updates";
      choice distribute-list-choice {
        case acl-case {
          leaf acl-name {
            type string;
          }
          leaf in {
            description
              "Filter incoming routing updates";
            type string;
          }
        }
        case gateway-prefix-case {
          leaf gateway {
            description
              "Filtering incoming updates based on gateway";
            type string;
          }
          leaf prefix {
            description
              "Filter prefixes in routing updates";
            type string;
          }
          leaf gateway-prefix-in {
            description
              "Filter incoming routing updates";
            type string;
          }
        }
        case route-map-case {
          leaf route-map {
            description
              "Filter prefixes based on the route-map";
            type string;
          }
          leaf route-map-in {
            description
              "Filter incoming routing updates";
            type empty;
          }
        }
      }
    }
    container domain-password {
      description
        "Set the authentication password for a routing domain";
      leaf name {
        type string;
      }
      uses ncs_template_authenticate-snp-grouping;
    }
    container fast-flood {
      description
        "Flood LSPs (that triggered SPF) before running SPF";
      presence "Flood LSPs (that triggered SPF) before running SPF";
      leaf number {
        type string;
      }
    }
    container fast-reroute {
      description
        "Configure Fast-Reroute";
      container load-sharing {
        description
          "Distributes repair paths equally among links and prefixes";
        container level-1 {
          description
            "Apply to level-1";
          presence "true";
          leaf disable {
            description
              "Disable load-sharing";
            type empty;
          }
        }
        container level-2 {
          description
            "Apply to level-2";
          presence "true";
          leaf disable {
            description
              "Disable load-sharing";
            type empty;
          }
        }
      }
      container per-prefix {
        description
          "Enable Fast-Reroute Per-Prefix";
        container level-1 {
          description
            "Apply to level-1";
          leaf all {
            description
              "Enable Fast-Reroute for primary paths";
            type empty;
          }
          leaf route-map {
            description
              "route-map name";
            type string;
          }
        }
        container level-2 {
          description
            "Apply to level-2";
          leaf all {
            description
              "Enable Fast-Reroute for primary paths";
            type empty;
          }
          leaf route-map {
            description
              "route-map name";
            type string;
          }
        }
      }
      container remote-lfa {
        description
          "Configuring fast-reroute remote-lfa";
        container level-1 {
          description
            "Apply to level-1";
          container mpls-ldp {
            description
              "Use mpls-ldp tunnel type";
            presence "true";
            container maximum-metric {
              description
                "maximum metric to reach release node";
              presence "true";
              leaf max-met {
                description
                  "metric value";
                type string;
              }
            }
          }
        }
        container level-2 {
          description
            "Apply to level-2";
          container mpls-ldp {
            description
              "Use mpls-ldp tunnel type";
            presence "true";
            container maximum-metric {
              description
                "maximum metric to reach release node";
              presence "true";
              leaf max-met {
                description
                  "metric value";
                type string;
              }
            }
          }
        }
      }
      container tie-break {
        description
          "Set repair path preference";
        container level-1 {
          description
            "Apply to level-1";
          uses ncs_template_tie-break-prefer-repair-grouping;
        }
        container level-2 {
          description
            "Apply to level-2";
          uses ncs_template_tie-break-prefer-repair-grouping;
        }
      }
    }
    container ti-lfa {
      container level-1 {
        description
          "Apply to level-1";
        container maximum-metric {
          description
            "maximum metric to reach release node";
          leaf max-met {
            description
              "metric value";
            type string;
          }
        }
      }
      container level-2 {
        description
          "Apply to level-2";
        presence "true";
        container maximum-metric {
          description
            "maximum metric to reach release node";
          leaf max-met {
            description
              "metric value";
            type string;
          }
        }
      }
    }
    container hello {
      description
        "Pad ISIS hello PDUs to full MTU";
      container padding {
        description
          "Pad hello PDU";
        presence "Pad hello PDU";
        leaf pad-type {
          type string;
        }
      }
    }
    container hostname {
      description
        "Dynamic hostname for IS-IS";
      leaf dynamic {
        description
          "Dynamic hostname";
        type empty;
      }
    }
    leaf ignore-lsp-errors {
      description
        "Ignore LSPs with bad checksums";
      type empty;
    }
    leaf is-type {
      description
        "IS Level for this routing process (OSI only)";
      type string;
    }
    container ispf {
      description
        "Configure execution of incremental SPF";
      leaf level {
        type string;
      }
      leaf number {
        type string;
      }
    }
    container log-adjacency-changes {
      description
        "Log changes in adjacency state";
      presence "Log changes in adjacency state";
      leaf all {
        description
          "Include changes generated by non-IIH event";
        type empty;
      }
    }
    container lsp-full {
      description
        "If we run out of LSP fragments";
      container suppress {
        description
          "suppress the following types of IP prefixes";
        choice lsp-full-choince {
          container external-interlevel-container {
            leaf external {
              description
                "don't advertise IP prefixes learned from other protocols";
              type empty;
            }
            leaf interlevel {
              description
                "don't advertise IP prefixes learned from another ISIS level";
              type empty;
            }
          }
          leaf none {
            description
              "don't suppress any prefixes";
            type empty;
          }
        }
      }
    }
    container lsp-gen-interval {
      description
        "Minimum interval between regenerating same LSP";
      choice lsp-gen-interval-choice {
        container intervals {
          uses ncs_template_lsp-gen-interval-grouping;
        }
        container intervals-levels {
          container intervals-level-1 {
            leaf level-1 {
              description
                "Set interval for level 1 only";
              type empty;
            }
            uses ncs_template_lsp-gen-interval-grouping;
          }
          container intervals-level-2 {
            leaf level-2 {
              description
                "Set interval for level 2 only";
              type empty;
            }
            uses ncs_template_lsp-gen-interval-grouping;
          }
        }
      }
    }
    leaf lsp-mtu {
      description
        "Set maximum LSP size";
      type string;
    }
    leaf lsp-refresh-interval {
      description
        "Set LSP refresh interval";
      type string;
    }
    leaf max-area-addresses {
      description
        "Allow configuration of more manual area addresses";
      type string;
    }
    leaf max-lsp-lifetime {
      description
        "Set maximum LSP lifetime";
      type string;
    }
    container microloop {
      description
        "Enable microloop protection configuration commands";
      container avoidance {
        description
          "Enable local microloop avoidance";
        presence "true";
        leaf disable {
          description
            "Disable Microloop avoidance";
          type empty;
        }
        leaf protected {
          description
            "Microloop avoidance for protected link or prefix only";
          type empty;
        }
        leaf rib-update-delay {
          description
            "Value of the delay in milliseconds";
          type string;
        }
      }
    }
    container mpls {
      description
        "Configure MPLS routing protocol parameters";
      container ldp {
        description
          "routing protocol commands for MPLS LDP";
        container autoconfig {
          description
            "Configure LDP automatic configuration";
          presence "true";
          leaf level-1 {
            description
              "Configure ISIS level-1 to run MPLS LDP";
            type empty;
          }
          leaf level-2 {
            description
              "Configure ISIS level-2 to run MPLS LDP";
            type empty;
          }
        }
        leaf sync {
          description
            "Configure LDP-IGP Synchronization";
          type empty;
        }
        leaf sync-igp-shortcuts {
          description
            "Configure LDP-IGP Synchronization on MPLS shortcuts";
          type empty;
        }
      }
      container traffic-eng {
        description
          "routing protocol commands for MPLS Traffic Engineering";
        leaf level-1 {
          description
            "Run MPLS TE on IS-IS level 1 only";
          type empty;
        }
        leaf level-2 {
          description
            "Run MPLS TE on IS-IS level 2 only";
          type empty;
        }
        leaf multicast-intact {
          description
            "MPLS TE and PIM interaction";
          type empty;
        }
        container router-id {
          description
            "Traffic Engineering stable IP address for system";
          uses ios-ifc:ncs_template_interface-grouping;
        }
        container scanner {
          description
            "Timer parameters for TE database";
          leaf interval {
            description
              "Time (secs) between LSPDB walks for TE";
            type string;
          }
          leaf max-flash {
            description
              "Max. number of LSPs ISIS may send to TE db without delay: <0..200>";
            type string;
          }
        }
      }
    }
    list net {
      // NCS patched for predictable order
      ordered-by user;
      description
        "A Network Entity Title for this process (OSI only)";
      key "tag";
      leaf tag {
        type string;
      }
    }
    container nsf {
      description
        "Non-stop forwarding";
      leaf cisco {
        description
          "Checkpoint method";
        type empty;
      }
      leaf ietf {
        description
          "IETF method";
        type empty;
      }
      container interface {
        description
          "Interface properties";
        leaf wait {
          description
            "Seconds";
          type string;
        }
      }
      leaf interval {
        description
          "Minutes";
        type string;
      }
    }
    container partition {
      description
        "CLNS area partition";
      leaf avoidance {
        description
          "Withdraw area prefix if partition detected";
        type empty;
      }
    }
    uses ios-ifc:ncs_template_passive-interface-grouping;
    container protocol {
      description
        "Set protocol's administrative state";
      leaf shutdown {
        description
          "Set protocol's administrative state to disable";
        type empty;
      }
    }
    container segment-routing {
      description
        "Enable Segment Routing Feature";
      leaf mpls {
        description
          "Enable Segment Routing Feature using MPLS encapsulation";
        type empty;
      }
      container prefix-sid-map {
        description
          "Enable prefix-sid-map";
        leaf advertise-local {
          description
            "Advertise active local prefix-SID mappings";
          type empty;
        }
        container receive {
          description
            "Enable prefix-SID mapping client";
          presence "true";
          leaf disable {
            description
              "Disable prefix-SID mapping";
            type empty;
          }
        }
      }
    }
    container skeptical {
      description
        "Be a cautious NSF helper when refresh adjacency";
      leaf interval {
        description
          "Minutes";
        type string;
      }
    }
    leaf update-queue-depth {
      description
        "Set Update process queue depth";
      type string;
    }
    container use {
      description
        "Use different algorithms during SPF";
      leaf external-metrics {
        description
          "Honour external metrics during SPF";
        type empty;
      }
    }
    leaf vrf {
      description
        "VRF name for this process";
      type string;
    }
    uses ncs_template_isis-ipv4-ipv6-common-grouping;
  }

  grouping ncs_template_config-isis-container-grouping {
    container isis-container {
      list isis {
        // NCS patched for predictable order
        ordered-by user;
        description
          "ISO IS-IS";
        key "area-tag";
        leaf area-tag {
          type string;
        }
        uses ncs_template_config-isis-main-grouping;
      }
    }
  }

  grouping ncs_template_config-isis-grouping {
    container isis {
      description
        "ISO IS-IS";
      presence "true";
      uses ncs_template_config-isis-main-grouping;
    }
  }

  grouping ncs_rpc_notif_config-interface-isis-grouping {
    container adjacency-filter {
      description
        "Filter IS-IS adjacencies";
      leaf name {
        type string;
      }
      leaf match-all {
        description
          "Match all area addresses";
        type empty;
      }
    }
    container advertise {
      description
        "Control addresses advertisements in LSPs";
      leaf prefix {
        description
          "Interface IP address";
        type empty;
      }
    }
    container authentication {
      description
        "ISIS authentication for interface related PDUs";
      uses ncs_rpc_notif_isis-authentication-grouping;
    }
    container circuit-type {
      description
        "Configure circuit type for interface";
      presence "true";
      leaf levels {
        type enumeration {
          enum "level-1";
          enum "level-1-2";
          enum "level-2-only";
        }
      }
    }
    container csnp-interval {
      description
        "Set CSNP interval in seconds";
      choice csnp-interval-choice {
        case csnp-interval-level-case {
          list csnp-interval-list {
            key "levels";
            leaf levels {
              type enumeration {
                enum "level-1";
                enum "level-2";
              }
            }
            leaf value {
              type uint16;
            }
          }
        }
        case csnp-interval-only-case {
          leaf value {
            type uint16;
          }
        }
      }
    }
    container hello {
      description
        "Add padding to IS-IS hello packets";
      container padding {
        description
          "Pad hello packets";
        presence "true";
        leaf always {
          description
            "Never pad hello packets if no prefix present";
          type empty;
        }
      }
    }
    container hello-interval {
      description
        "Set Hello interval in seconds";
      choice hello-interval-choice {
        case hello-interval-level-case {
          list hello-interval-list {
            key "levels";
            leaf levels {
              type enumeration {
                enum "level-1";
                enum "level-2";
              }
            }
            leaf value {
              type union {
                type uint16 {
                  range "1..65535";
                }
                type enumeration {
                  enum "minimal";
                }
              }
            }
          }
        }
        case hello-interval-only-case {
          leaf value {
            type union {
              type uint16 {
                range "1..65535";
              }
              type enumeration {
                enum "minimal";
              }
            }
          }
        }
      }
    }
    container hello-multiplier {
      description
        "Set multiplier for Hello holding time";
      choice hello-multiplier-choice {
        case hello-multiplier-level-case {
          list hello-multiplier-list {
            key "levels";
            leaf levels {
              type enumeration {
                enum "level-1";
                enum "level-2";
              }
            }
            leaf value {
              type uint16 {
                range "3..1000";
              }
            }
          }
        }
        case hello-multiplier-only-case {
          leaf value {
            type uint16 {
              range "3..1000";
            }
          }
        }
      }
    }
    container ipv6 {
      description
        "IPv6 interface configuration";
      uses ncs_rpc_notif_isis-metric-grouping;
      leaf tag {
        description
          "Assign an admin tag to an ISIS interface IPv6 route";
        type uint32 {
          range "1..4294967295";
        }
      }
    }
    leaf lsp-interval {
      description
        "Set LSP transmission interval";
      type uint32 {
        range "1..4294967295";
      }
    }
    leaf mesh-group {
      description
        "Set ISIS mesh group";
      type union {
        type uint32 {
          range "1..4294967295";
        }
        type enumeration {
          enum "blocked";
        }
      }
    }
    uses ncs_rpc_notif_isis-metric-grouping;
    leaf network {
      description
        "Network type";
      type enumeration {
        enum "point-to-point";
      }
    }
    container password {
      description
        "Configure the authentication password for interface";
      choice password-choice {
        case password-level-case {
          list password-list {
            key "levels";
            leaf levels {
              type enumeration {
                enum "level-1";
                enum "level-2";
              }
            }
            leaf password {
              type string;
            }
          }
        }
        case password-only-case {
          leaf password {
            type string;
          }
        }
      }
    }
    container priority {
      description
        "Set priority for Designated Router election";
      choice priority-choice {
        case priority-level-case {
          list priority-list {
            key "levels";
            leaf levels {
              type enumeration {
                enum "level-1";
                enum "level-2";
              }
            }
            leaf value {
              type uint8 {
                range "0..127";
              }
            }
          }
        }
        case priority-only-case {
          leaf value {
            type uint8 {
              range "0..127";
            }
          }
        }
      }
    }
    leaf protocol {
      description
        "Set ISIS protocol's state under current interface";
      type enumeration {
        enum "shutdown";
      }
    }
    leaf retransmit-interval {
      description
        "Set per-LSP retransmission interval";
      type uint16;
    }
    leaf retransmit-throttle-interval {
      description
        "Set interface LSP retransmission interval";
      type uint16;
    }
    leaf tag {
      description
        "Assign an admin tag to an ISIS interface IP route";
      type uint32 {
        range "1..4294967295";
      }
    }
    container three-way-handshake {
      description
        "Select Cisco or IETF three-way handshake";
      presence "true";
      leaf implementor {
        type enumeration {
          enum "cisco";
          enum "ietf";
        }
      }
    }
  }

  grouping ncs_rpc_notif_narrow-wide-transition-grouping {
    leaf narrow-wide {
      type isis-level-type;
    }
    leaf transition {
      description
        "Accept both styles of TLVs during transition";
      type isis-level-type;
    }
  }

  grouping ncs_rpc_notif_spf-intervals-grouping {
    leaf interval {
      type uint32 {
        range "1 .. 120";
      }
    }
    leaf initial-wait {
      type uint32 {
        range "1 .. 120000";
      }
    }
    leaf minimum-wait {
      type uint32 {
        range "1 .. 120000";
      }
    }
  }

  grouping ncs_rpc_notif_authenticate-snp-grouping {
    leaf authenticate {
      description
        "Authentication";
      type empty;
    }
    leaf snp {
      description
        "SNP PDUs";
      type enumeration {
        enum "send-only";
        enum "validate";
      }
    }
  }

  grouping ncs_rpc_notif_lsp-gen-interval-grouping {
    leaf interval {
      type uint32 {
        range "1 .. 120";
      }
    }
    leaf initial-wait {
      type uint32 {
        range "1 .. 120000";
      }
    }
    leaf wait {
      type uint32 {
        range "1 .. 120000";
      }
    }
  }

  grouping ncs_rpc_notif_set-overload-bit-suppress-grouping {
    leaf external {
      description
        "If overload-bit set, don't advertise IP prefixes learned from other protocols";
      type empty;
    }
    leaf interlevel {
      description
        "If overload-bit set, don't advertise IP prefixes learned from another ISIS level";
      type empty;
    }
  }

  grouping ncs_rpc_notif_summary-address-metric-tag-grouping {
    leaf metric {
      description
        "Set metric for summay route";
      type uint32 {
        range "1 .. 4294967295";
      }
    }
    leaf tag {
      description
        "Set tag";
      type uint32 {
        range "1 .. 4294967295";
      }
    }
  }

  grouping ncs_rpc_notif_authentication-level-grouping {
    leaf levels {
      type authentication-level-type;
    }
  }

  grouping ncs_rpc_notif_isis-authentication-grouping {
    container mode {
      description
        "Authentication mode";
      container md5 {
        description
          "Keyed message digest";
        presence "Keyed message digest";
        uses ncs_rpc_notif_authentication-level-grouping;
      }
      container text {
        description
          "Clear text password";
        presence "Clear text password";
        uses ncs_rpc_notif_authentication-level-grouping;
      }
    }
    container key-chain {
      description
        "Authentication key-chain";
      choice key-chain-choice {
        case key-chain-level-case {
          list key-chain-list {
            key "levels";
            uses ncs_rpc_notif_authentication-level-grouping;
            leaf name {
              type string;
            }
          }
        }
        case key-chain-only-case {
          leaf name {
            type string;
          }
        }
      }
    }
    container send-only {
      description
        "Authentication send only, receive ignore";
      presence "Authentication send only, receive ignore";
      uses ncs_rpc_notif_authentication-level-grouping;
    }
  }

  grouping ncs_rpc_notif_isis-metric-grouping {
    container metric {
      description
        "Configure the metric for interface";
      choice metric-choice {
        case metric-level-case {
          list metric-list {
            key "levels";
            leaf levels {
              type enumeration {
                enum "level-1";
                enum "level-2";
              }
            }
            leaf value {
              type union {
                type uint32 {
                  range "1..16777214";
                }
                type enumeration {
                  enum "maximum";
                }
              }
            }
          }
        }
        case metric-only-case {
          leaf value {
            type union {
              type uint32 {
                range "1..16777214";
              }
              type enumeration {
                enum "maximum";
              }
            }
          }
        }
      }
    }
  }

  grouping ncs_rpc_notif_redist-level-grouping {
    leaf levels {
      type isis-routes-level-type;
    }
  }

  grouping ncs_rpc_notif_isis-redist-grouping {
    leaf levels {
      type isis-routes-level-type;
    }
    leaf metric {
      description
        "ISIS default metric";
      type uint32 {
        range "0 .. 4294967295";
      }
    }
    leaf metric-type {
      description
        "OSPF/IS-IS exterior metric type for redistributed routes";
      type enumeration {
        enum "external";
        enum "internal";
        enum "rib-metric-as-external";
        enum "rib-metric-as-internal";
      }
    }
    leaf route-map {
      description
        "Route map reference";
      type string;
    }
  }

  grouping ncs_rpc_notif_isis-redist-af-grouping {
    leaf include-connected {
      description
        "Include connected";
      type empty;
    }
    uses ncs_rpc_notif_isis-redist-grouping;
  }

  grouping ncs_rpc_notif_isis-redist-ospf-match-grouping {
    uses ncs_rpc_notif_redist-level-grouping;
    leaf metric {
      description
        "ISIS default metric";
      type uint32 {
        range "0 .. 4294967295";
      }
    }
    leaf route-map {
      description
        "Route map reference";
      type string;
    }
  }

  grouping ncs_rpc_notif_isis-redist-clns-ip-grouping {
    container clns {
      description
        "Redistribution of BGP NSAP routes";
      presence "Redistribution of BGP NSAP routes";
      uses ncs_rpc_notif_isis-redist-grouping;
    }
    container ip {
      description
        "Redistribution of BGP IP routes";
      presence "true";
      uses ncs_rpc_notif_isis-redist-grouping;
    }
  }

  grouping ncs_rpc_notif_isis-ipv4-ipv6-common-grouping {
    leaf adjacency-check {
      description
        "Check ISIS neighbor protocol support";
      type empty;
    }
    container bfd {
      description
        "BFD configuration commands";
      leaf all-interfaces {
        description
          "Enable BFD on all interfaces";
        type empty;
      }
      leaf check-ctrl-plane-failure {
        description
          "BFD check control plane failure";
        type empty;
      }
    }
    leaf router-id {
      description
        "Interface of stable IP address for system";
      type string;
    }
  }

  grouping ncs_rpc_notif_isis-common-grouping {
    container advertise {
      description
        "Control which IP routes flow in L1 and L2 LSPs";
      leaf passive-only {
        description
          "only interface address of passive interfaces";
        type empty;
      }
    }
    container default-information {
      description
        "Control distribution of default information";
      container originate {
        presence "Distribute a default route";
        description
          "Distribute a default route";
        leaf route-map {
          description
            "Route-map reference";
          type string;
        }
      }
    }
    leaf help {
      description
        "Description of the interactive help system";
      type empty;
    }
    leaf maximum-paths {
      description
        "Forward packets over multiple paths";
      type uint32 {
        range "1 .. 32";
      }
    }
    container metric {
      description
        "Set ISIS metric for all interfaces";
      choice metric-choice {
        case metric-level-case {
          list metrics {
            key "level";
            leaf level {
              type enumeration {
                enum "level-1";
                enum "level-2";
              }
            }
            leaf metric {
              type uint32 {
                range "1..16777214";
              }
            }
          }
        }
        case metric-only-case {
          leaf metric {
            type uint32 {
              range "1..16777214";
            }
          }
        }
      }
    }
    container prc-interval {
      description
        "Minimum interval between partial route calculations";
      leaf interval {
        type uint32 {
          range "1 .. 120";
        }
      }
      leaf initial-wait {
        type uint32 {
          range "1 .. 120000";
        }
      }
      leaf minimum-wait {
        type uint32 {
          range "1 .. 120000";
        }
      }
    }
    container set-overload-bit {
      description
        "Signal other routers not to use us in SPF";
      presence "Signal other routers not to use us in SPF";
      choice set-overload-bit-choice {
        container on-startup {
          description
            "Set overload-bit only temporarily after reboot";
          choice on-startup-choice {
            container time {
              leaf time {
                type uint32 {
                  range "5 .. 86400";
                }
              }
              leaf suppress {
                description
                  "If overload-bit set, suppress the following types of IP prefixes";
                type empty;
              }
              leaf external {
                description
                  "If overload-bit set, don't advertise IP prefixes learned from other protocols";
                type empty;
              }
              leaf interlevel {
                description
                  "If overload-bit set, don't advertise IP prefixes learned from another ISIS level";
                type empty;
              }
            }
            container wait-for-bgp {
              description
                "Let BGP decide when to unset the overload bit";
              presence "Let BGP decide when to unset the overload bitW";
              container suppress {
                description
                  "If overload-bit set, suppress the following types of IP prefixes";
                uses ncs_rpc_notif_set-overload-bit-suppress-grouping;
              }
            }
          }
        }
        container suppress {
          description
            "If overload-bit set, suppress the following types of IP prefixes";
          uses ncs_rpc_notif_set-overload-bit-suppress-grouping;
        }
      }
    }
    container spf-interval {
      description
        "Minimum interval between SPF calculations";
      choice spf-interval-choice {
        list level-1-2 {
          key "level";
          leaf level {
            type enumeration {
              enum "level-1";
              enum "level-2";
            }
          }
          uses ncs_rpc_notif_spf-intervals-grouping;
        }
        container intervals {
          uses ncs_rpc_notif_spf-intervals-grouping;
        }
      }
    }
  }

  grouping ncs_rpc_notif_isis-address-family-grouping {
    uses ncs_rpc_notif_isis-common-grouping;
    uses ncs_rpc_notif_isis-ipv4-ipv6-common-grouping;
    leaf distance {
      description
        "Administrative distance";
      type uint32 {
        range "1 .. 254";
      }
    }
    container distribute-list {
      description
        "Filter networks in routing updates";
      list prefix-list {
        description
          "Filter connections based on an IPv6 prefix-list";
        key "name";
        leaf name {
          type string;
        }
        container in {
          description
            "Filter incoming routing updates";
          presence "true";
          container interface {
            description
              "Specify interface";
            uses ios-ifc:ncs_rpc_notif_interface-grouping;
          }
        }
      }
    }
    container ipv6 {
      description
        "IPv6 specific commands";
      container route {
        description
          "ISIS IPV6 routes";
        container priority {
          description
            "Assign priority to IPV6 prefixes";
          container high {
            description
              "Assign high priority to important IPV6 prefixes in ISIS IPV6 local RIB";
            leaf tag {
              description
                "Assign high priority to IPV6 prefixes with a specific route tag";
              type uint32;
            }
          }
        }
      }
    }
    container multi-topology {
      description
        "Enable multi-topology mode";
      presence "Enable multi-topology mode";
      leaf transition {
        description
          "Accept and generate both IS-IS IPv6 and Multi-topology IPv6 TLVs";
        type empty;
      }
    }
    container redistribute {
      description
        "Redistribute IPv6 prefixes from another routing protocol";
      container application {
        description
          "Application Protocol";
        presence "Application Protocol";
        uses ncs_rpc_notif_isis-redist-af-grouping;
      }
      container bgp {
        description
          "Border Gateway Protocol (BGP)";
        leaf as-number {
          type ios-types:bgp-as-number-type;
        }
        uses ncs_rpc_notif_isis-redist-af-grouping;
      }
      container connected {
        description
          "Connected";
        presence "Connected";
        uses ncs_rpc_notif_isis-redist-grouping;
      }
      list eigrp {
        description
          "Enhanced Interior Gateway Routing Protocol (EIGRP)";
        key "as-number";
        leaf as-number {
          type uint32 {
            range "1 .. 65535";
          }
        }
        uses ncs_rpc_notif_isis-redist-af-grouping;
      }
      container isis {
        description
          "ISO IS-IS";
        presence "true";
        list isis-redistribute {
          key "area-tag";
          leaf area-tag {
            type string;
          }
          uses ncs_rpc_notif_isis-redist-af-grouping;
        }
        list isis-leak {
          key "isis-redist-levels1 isis-redist-levels2";
          leaf isis-redist-levels1 {
            type enumeration {
              enum "level-1";
              enum "level-2";
            }
          }
          leaf isis-redist-levels2 {
            type enumeration {
              enum "level-1";
              enum "level-2";
            }
          }
          leaf into {
            description
              "from level-n into level-m";
            type empty;
          }
          choice isis-redist-isis-ip-choice {
            leaf distribute-list {
              description
                "select routes";
              type string;
            }
            leaf route-map {
              description
                "Route map for route matching";
              type string;
            }
          }
        }
      }
      container lisp {
        description
          "Locator ID Separation Protocol (LISP)";
        presence "Locator ID Separation Protocol (LISP)";
        uses ncs_rpc_notif_isis-redist-af-grouping;
      }
      container nd {
        description
          "Neighbor Discovery";
        presence "Neighbor Discovery";
        uses ncs_rpc_notif_isis-redist-af-grouping;
      }
      container nemo {
        description
          "Network Mobility (NEMO)";
        uses ncs_rpc_notif_isis-redist-af-grouping;
      }
      list ospf {
        description
          "Open Shortest Path First (OSPF)";
        key "process-id";
        leaf process-id {
          type uint32 {
            range "1 .. 65535";
          }
        }
        uses ncs_rpc_notif_isis-redist-af-grouping;
        container match {
          description
            "Redistribution of OSPF routes";
          container internal {
            presence "Redistribute OSPF internal routes";
            description
              "Redistribute OSPF internal routes";
            uses ncs_rpc_notif_isis-redist-grouping;
          }
          container external {
            description
              "Redistribute OSPF external routes";
            presence "Redistribute OSPF external routes";
            leaf external-routes {
              type ios-types:redist-ospf-external-type;
            }
            uses ncs_rpc_notif_isis-redist-grouping;
          }
          container nssa-external {
            description
              "Redistribute OSPF NSSA external routes";
            presence "Redistribute OSPF NSSA external routes";
            leaf nssa-external-routes {
              type ios-types:redist-ospf-external-type;
            }
            uses ncs_rpc_notif_isis-redist-grouping;
          }
        }
      }
      list rip {
        description
          "IPv6 Routing Information Protocol (RIPv6)";
        key "process";
        leaf process {
          type string;
        }
        uses ncs_rpc_notif_isis-redist-af-grouping;
      }
      container static {
        description
          "Static routes";
        presence "Static routes";
        uses ncs_rpc_notif_isis-redist-grouping;
      }
    }
    list summary-prefix {
      description
        "Configure IPv6 summary prefix";
      key "prefix";
      leaf prefix {
        type ios-types:ipv6-prefix;
      }
      leaf levels {
        type enumeration {
          enum "level-1";
          enum "level-1-2";
          enum "level-2";
        }
      }
    }
    container table-map {
      description
        "Map external entry attributes into routing table";
      leaf name {
        type string;
      }
      leaf filter {
        description
          "Selective route download";
        type empty;
      }
    }
  }

  grouping ncs_rpc_notif_isis-redist-vrf-grouping {
    container application {
      description
        "Application";
      list appname {
        key "appname";
        leaf appname {
          description
            "Application name";
          type string;
        }
        uses ncs_rpc_notif_isis-redist-grouping;
      }
    }
    container bgp {
      description
        "Border Gateway Protocol (BGP)";
      list bp-as-num {
        key "bp-as-num";
        leaf bp-as-num {
          description
            "Autonomous system number";
          type ios-types:bgp-as-number-type;
        }
        uses ncs_rpc_notif_isis-redist-clns-ip-grouping;
        uses ncs_rpc_notif_isis-redist-grouping;
      }
      leaf a_LESSER_1_PERIOD_0-XX_PERIOD_YY_GREATER_ {
        description
          "Autonomous system number";
        type empty;
      }
    }
    container connected {
      description
        "Connected";
      presence "true";
      uses ncs_rpc_notif_isis-redist-grouping;
    }
    container eigrp {
      description
        "Enhanced Interior Gateway Routing Protocol (EIGRP)";
      list eigrp-as {
        key "eigrp-as";
        leaf eigrp-as {
          description
            "AS number";
          type uint16 {
            range "1..65535";
          }
        }
        uses ncs_rpc_notif_isis-redist-grouping;
      }
    }
    container isis {
      description
        "ISO IS-IS";
      list isis-atag {
        key "isis-atag";
        leaf isis-atag {
          description
            "ISO routing area tag";
          type string;
        }
        container ip {
          description
            "Redistribution of IP routes between levels or processes";
          uses ncs_rpc_notif_isis-redist-grouping;
        }
      }
      container ip {
        description
          "Redistribution of IP routes between levels or processes";
        presence "true";
        uses ncs_rpc_notif_isis-redist-grouping;
      }
    }
    container iso-igrp {
      description
        "IGRP for OSI networks";
      presence "true";
      list iso-atag {
        key "iso-atag";
        leaf iso-atag {
          description
            "ISO routing area tag";
          type string;
        }
        leaf route-map {
          description
            "Route map reference";
          type empty;
        }
      }
      container route-map {
        description
          "Route map reference";
        presence "true";
        leaf rm-point {
          description
            "Pointer to route-map entries";
          type string;
        }
      }
    }
    container lisp {
      description
        "Locator ID Separation Protocol (LISP)";
      presence "true";
      uses ncs_rpc_notif_isis-redist-grouping;
    }
    container mobile {
      description
        "Mobile routes";
      presence "true";
      uses ncs_rpc_notif_isis-redist-grouping;
    }
    leaf ospf {
      description
        "Process ID";
      type uint16 {
        range "1..65535";
      }
    }
    container ospfv3 {
      description
        "OSPFv3";
      list os3-id {
        key "os3-id";
        leaf os3-id {
          description
            "Process ID";
          type uint16 {
            range "1..65535";
          }
        }
        uses ncs_rpc_notif_isis-redist-grouping;
      }
    }
    container rip {
      description
        "Routing Information Protocol (RIP)";
      presence "true";
      uses ncs_rpc_notif_isis-redist-grouping;
    }
    container static {
      description
        "Static routes";
      presence "true";
      uses ncs_rpc_notif_isis-redist-clns-ip-grouping;
      uses ncs_rpc_notif_isis-redist-grouping;
    }
  }

  grouping ncs_rpc_notif_tie-break-prefer-repair-grouping {
    leaf downstream {
      description
        "priority number";
      type uint8 {
        range "1..255";
      }
    }
    leaf linecard-disjoint {
      description
        "priority number";
      type uint8 {
        range "1..255";
      }
    }
    leaf lowest-backup-path-metric {
      description
        "priority number";
      type uint8 {
        range "1..255";
      }
    }
    leaf node-protecting {
      description
        "priority number";
      type uint8 {
        range "1..255";
      }
    }
    leaf primary-path {
      description
        "priority number";
      type uint8 {
        range "1..255";
      }
    }
    leaf secondary-path {
      description
        "priority number";
      type uint8 {
        range "1..255";
      }
    }
    leaf srlg-disjoint {
      description
        "priority number";
      type uint8 {
        range "1..255";
      }
    }
  }

  grouping ncs_rpc_notif_isis-topology-grouping {
    list distance {
      description
        "Define an administrative distance";
      key "number";
      leaf number {
        type uint8 {
          range "1 .. 255";
        }
      }
      list ip-list {
        key "ip";
        leaf ip {
          description
            "IP Source address";
          type inet:ipv4-address;
        }
        list wildcard-bits {
          key "w-bits";
          leaf w-bits {
            type inet:ipv4-address;
          }
          leaf access-list {
            type ios-types:default-access-list-standard-id-type;
          }
        }
      }
      leaf clns {
        description
          "Distance applied for CLNS derived routes";
        type empty;
      }
      leaf ip {
        description
          "Distance applied for IP derived routes";
        type empty;
      }
    }
    container ip {
      description
        "IP specific commands";
      container route {
        description
          "ISIS IP routes";
        container priority {
          description
            "Assign priority to IP prefixes";
          container high {
            description
              "Assign high priority to important IP prefixes in ISIS IP local RIB";
            leaf tag {
              description
                "Assign high priority to IP prefixes with a specific route tag";
              type uint32 {
                range "1 .. 4294967295";
              }
            }
          }
        }
      }
    }
    leaf priority {
      description
        "priority value";
      type uint8 {
        range "0..127";
      }
    }
    container redistribute {
      description
        "Redistribute information from another routing protocol";
      list application {
        description
          "Application";
        key "name";
        leaf name {
          description
            "Application name";
          type string;
        }
        uses ncs_rpc_notif_isis-redist-grouping;
      }
      container bgp {
        description
          "Border Gateway Protocol (BGP)";
        leaf as-number {
          type ios-types:bgp-as-number-type;
        }
        uses ncs_rpc_notif_isis-redist-grouping;
        uses ncs_rpc_notif_isis-redist-clns-ip-grouping;
      }
      container connected {
        description
          "Connected";
        presence "Connected";
        uses ncs_rpc_notif_isis-redist-grouping;
      }
      list eigrp {
        description
          "Enhanced Interior Gateway Routing Protocol (EIGRP)";
        key "as-number";
        leaf as-number {
          type uint32 {
            range "1 .. 65535";
          }
        }
        uses ncs_rpc_notif_isis-redist-grouping;
      }
      container isis {
        description
          "ISO IS-IS";
        list isis-redistribute {
          key "area-tag";
          leaf area-tag {
            type string;
          }
          container ip {
            description
              "Redistribution of IP routes between levels or processes";
            presence "true";
            uses ncs_rpc_notif_isis-redist-grouping;
          }
        }
        list ip {
          description
            "Redistribution of IP routes between levels";
          key "isis-redist-levels1 isis-redist-levels2";
          leaf isis-redist-levels1 {
            type enumeration {
              enum "level-1";
              enum "level-2";
            }
          }
          leaf isis-redist-levels2 {
            type enumeration {
              enum "level-1";
              enum "level-2";
            }
          }
          leaf into {
            description
              "from level-n into level-m";
            type empty;
          }
          choice isis-redist-isis-ip-choice {
            leaf distribute-list {
              description
                "select routes";
              type uint32 {
                range "100 .. 199";
              }
            }
            leaf route-map {
              description
                "Route map for route matching";
              type string;
            }
          }
        }
      }
      container iso-igrp {
        description
          "IGRP for OSI networks";
        presence "IGRP for OSI networks";
        choice iso-igrp-choice {
          container area-tag-route-map-container {
            leaf area-tag {
              type string;
            }
            leaf route-map {
              description
                "Route map reference";
              type string;
            }
          }
          leaf route-map {
            description
              "Route map reference";
            type string;
          }
        }
        uses ncs_rpc_notif_redist-level-grouping;
        leaf metric {
          description
            "ISIS default metric";
          type uint32 {
            range "0 .. 4294967295";
          }
        }
        leaf metric-type {
          description
            "OSPF/IS-IS exterior metric type for redistributed routes";
          type enumeration {
            enum "external";
            enum "internal";
            enum "rib-metric-as-external";
            enum "rib-metric-as-internal";
          }
        }
      }
      container lisp {
        description
          "Locator ID Separation Protocol (LISP)";
        presence "true";
        uses ncs_rpc_notif_isis-redist-af-grouping;
      }
      container maximum-prefix {
        description
          "Maximum number of prefixes redistributed to protocol";
        leaf number {
          type uint32 {
            range "1 .. 4294967295";
          }
        }
        leaf threshold-value {
          type uint32 {
            range "1 .. 100";
          }
        }
        leaf warning-only {
          description
            "Only give warning message when limit is exceeded";
          type empty;
        }
        leaf withdraw {
          description
            "Withdraw redistibuted prefixes";
          type empty;
        }
      }
      container mobile {
        description
          "Mobile routes";
        presence "Mobile routes";
        uses ncs_rpc_notif_isis-redist-grouping;
      }
      container odr {
        description
          "On Demand stub Routes";
        presence "On Demand stub Routes";
        uses ncs_rpc_notif_isis-redist-grouping;
      }
      list ospf {
        description
          "Open Shortest Path First (OSPF)";
        key "process-id";
        leaf process-id {
          type uint32 {
            range "1 .. 65535";
          }
        }
        uses ncs_rpc_notif_isis-redist-grouping;
        container match {
          description
            "Redistribution of OSPF routes";
          container internal {
            presence "Redistribute OSPF internal routes";
            description
              "Redistribute OSPF internal routes";
            uses ncs_rpc_notif_isis-redist-grouping;
          }
          container external {
            description
              "Redistribute OSPF external routes";
            presence "Redistribute OSPF external routes";
            leaf external-routes {
              type ios-types:redist-ospf-external-type;
            }
            uses ncs_rpc_notif_isis-redist-grouping;
          }
          container nssa-external {
            description
              "Redistribute OSPF NSSA external routes";
            presence "Redistribute OSPF NSSA external routes";
            leaf nssa-external-routes {
              type ios-types:redist-ospf-external-type;
            }
            uses ncs_rpc_notif_isis-redist-grouping;
          }
        }
        leaf vrf {
          description
            "VPN Routing/Forwarding Instance";
          type string;
        }
      }
      list ospfv3 {
        description
          "Open Shortest Path First (OSPF)";
        key "process-id";
        leaf process-id {
          type uint32 {
            range "1 .. 65535";
          }
        }
        uses ncs_rpc_notif_isis-redist-grouping;
        container match {
          description
            "Redistribution of OSPF routes";
          container internal {
            presence "Redistribute OSPF internal routes";
            description
              "Redistribute OSPF internal routes";
            uses ncs_rpc_notif_isis-redist-grouping;
          }
          container external {
            description
              "Redistribute OSPF external routes";
            presence "Redistribute OSPF external routes";
            leaf external-routes {
              type ios-types:redist-ospf-external-type;
            }
            uses ncs_rpc_notif_isis-redist-grouping;
          }
          container nssa-external {
            description
              "Redistribute OSPF NSSA external routes";
            presence "Redistribute OSPF NSSA external routes";
            leaf nssa-external-routes {
              type ios-types:redist-ospf-external-type;
            }
            uses ncs_rpc_notif_isis-redist-grouping;
          }
        }
        leaf vrf {
          description
            "VPN Routing/Forwarding Instance";
          type string;
        }
      }
      container rip {
        description
          "Routing Information Protocol (RIP)";
        presence "Routing Information Protocol (RIP)";
        uses ncs_rpc_notif_isis-redist-grouping;
      }
      container static {
        description
          "Static routes";
        presence "Static routes";
        uses ncs_rpc_notif_isis-redist-clns-ip-grouping;
      }
      container vrf {
        description
          "Specify a source VRF";
        list vrf-nm {
          key "vrf-nm";
          leaf vrf-nm {
            description
              "Source VRF name";
            type string;
          }
          uses ncs_rpc_notif_isis-redist-vrf-grouping;
        }
        container global {
          description
            "global VRF";
          uses ncs_rpc_notif_isis-redist-vrf-grouping;
        }
      }
    }
    container set-attached-bit {
      description
        "Conditionally advertise us as attached to L2";
      leaf route-map {
        description
          "Route-map reference";
        type string;
      }
    }
    uses ios-snmp:ncs_rpc_notif_router-snmp-grouping;
    list summary-address {
      description
        "Configure IP address summaries";
      key "ip mask";
      leaf ip {
        type inet:ipv4-address;
      }
      leaf mask {
        type inet:ipv4-address;
      }
      container level-1 {
        description
          "Summarize into level-1 area";
        presence "Summarize into level-1 area";
        uses ncs_rpc_notif_summary-address-metric-tag-grouping;
      }
      container level-1-2 {
        description
          "Summarize into both area and sub-domain";
        presence "Summarize into both area and sub-domain";
        uses ncs_rpc_notif_summary-address-metric-tag-grouping;
      }
      container level-2 {
        description
          "Summarize into level-2 sub-domain";
        presence "Summarize into level-2 sub-domain";
        uses ncs_rpc_notif_summary-address-metric-tag-grouping;
      }
      container metric-tag-container {
        uses ncs_rpc_notif_summary-address-metric-tag-grouping;
      }
    }
    container traffic-share {
      description
        "How to compute traffic share over alternate paths";
      container min {
        description
          "All traffic shared among min metric paths";
        leaf across-interfaces {
          description
            "Use different interfaces for equal-cost paths";
          type empty;
        }
      }
    }
    uses ncs_rpc_notif_isis-common-grouping;
  }

  grouping ncs_rpc_notif_isis-af-ipv4-grouping {
    leaf help {
      description
        "Description of the interactive help system";
      type empty;
    }
    uses ios-snmp:ncs_rpc_notif_router-snmp-grouping;
    list topology {
      description
        "Associate the routing protocol to a topology instance";
      key "name";
      leaf name {
        type string;
      }
      leaf tid {
        description
          "Configuring the routing protocol topology tid";
        type uint32 {
          range "5..4095";
        }
      }
      leaf ignore-attached-bit {
        description
          "Never install default route to closest L2 router";
        type empty;
      }
      uses ncs_rpc_notif_isis-topology-grouping;
    }
  }

  grouping ncs_rpc_notif_config-isis-main-grouping {
    container metric-style {
      description
        "Use old-style (ISO 10589) or new-style packet formats";
      choice metric-style-choice {
        container narrow {
          description
            "Use old style of TLVs with narrow metric";
          presence "true";
          uses ncs_rpc_notif_narrow-wide-transition-grouping;
        }
        container transition {
          description
            "Send and accept both styles of TLVs during transition";
          presence "true";
          leaf transition {
            type isis-level-type;
          }
        }
        container wide {
          description
            "Use new style of TLVs to carry wider metric";
          presence "true";
          uses ncs_rpc_notif_narrow-wide-transition-grouping;
        }
      }
    }
    container address-family {
      description
        "Enter Address Family command mode";
      container ipv4 {
        description
          "Address family";
        leaf unicast-multicast {
          type enumeration {
            enum "unicast";
            enum "multicast";
          }
        }
        uses ncs_rpc_notif_isis-af-ipv4-grouping;
      }
      container ipv6 {
        description
          "Address family";
        leaf unicast {
          type empty;
        }
        uses ncs_rpc_notif_isis-address-family-grouping;
      }
    }
    uses ncs_rpc_notif_isis-topology-grouping;
    container area-password {
      description
        "Configure the authentication password for an area";
      leaf name {
        type string;
      }
      uses ncs_rpc_notif_authenticate-snp-grouping;
    }
    container authentication {
      description
        "ISIS authentication for LSPs";
      uses ncs_rpc_notif_isis-authentication-grouping;
    }
    container distribute-list {
      description
        "Filter networks in routing updates";
      choice distribute-list-choice {
        case acl-case {
          leaf acl-name {
            type ios-types:access-list-standard-id-type;
          }
          leaf in {
            description
              "Filter incoming routing updates";
            type string;
          }
        }
        case gateway-prefix-case {
          leaf gateway {
            description
              "Filtering incoming updates based on gateway";
            type string;
          }
          leaf prefix {
            description
              "Filter prefixes in routing updates";
            type string;
          }
          leaf gateway-prefix-in {
            description
              "Filter incoming routing updates";
            type string;
          }
        }
        case route-map-case {
          leaf route-map {
            description
              "Filter prefixes based on the route-map";
            type string;
          }
          leaf route-map-in {
            description
              "Filter incoming routing updates";
            type empty;
          }
        }
      }
    }
    container domain-password {
      description
        "Set the authentication password for a routing domain";
      leaf name {
        type string;
      }
      uses ncs_rpc_notif_authenticate-snp-grouping;
    }
    container fast-flood {
      description
        "Flood LSPs (that triggered SPF) before running SPF";
      presence "Flood LSPs (that triggered SPF) before running SPF";
      leaf number {
        type uint32 {
          range "1 .. 15";
        }
      }
    }
    container fast-reroute {
      description
        "Configure Fast-Reroute";
      container load-sharing {
        description
          "Distributes repair paths equally among links and prefixes";
        container level-1 {
          description
            "Apply to level-1";
          presence "true";
          leaf disable {
            description
              "Disable load-sharing";
            type empty;
          }
        }
        container level-2 {
          description
            "Apply to level-2";
          presence "true";
          leaf disable {
            description
              "Disable load-sharing";
            type empty;
          }
        }
      }
      container per-prefix {
        description
          "Enable Fast-Reroute Per-Prefix";
        container level-1 {
          description
            "Apply to level-1";
          leaf all {
            description
              "Enable Fast-Reroute for primary paths";
            type empty;
          }
          leaf route-map {
            description
              "route-map name";
            type string;
          }
        }
        container level-2 {
          description
            "Apply to level-2";
          leaf all {
            description
              "Enable Fast-Reroute for primary paths";
            type empty;
          }
          leaf route-map {
            description
              "route-map name";
            type string;
          }
        }
      }
      container remote-lfa {
        description
          "Configuring fast-reroute remote-lfa";
        container level-1 {
          description
            "Apply to level-1";
          container mpls-ldp {
            description
              "Use mpls-ldp tunnel type";
            presence "true";
            container maximum-metric {
              description
                "maximum metric to reach release node";
              presence "true";
              leaf max-met {
                description
                  "metric value";
                type uint32 {
                  range "1..4294967295";
                }
              }
            }
          }
        }
        container level-2 {
          description
            "Apply to level-2";
          container mpls-ldp {
            description
              "Use mpls-ldp tunnel type";
            presence "true";
            container maximum-metric {
              description
                "maximum metric to reach release node";
              presence "true";
              leaf max-met {
                description
                  "metric value";
                type uint32 {
                  range "1..4294967295";
                }
              }
            }
          }
        }
      }
      container tie-break {
        description
          "Set repair path preference";
        container level-1 {
          description
            "Apply to level-1";
          uses ncs_rpc_notif_tie-break-prefer-repair-grouping;
        }
        container level-2 {
          description
            "Apply to level-2";
          uses ncs_rpc_notif_tie-break-prefer-repair-grouping;
        }
      }
    }
    container ti-lfa {
      container level-1 {
        description
          "Apply to level-1";
        container maximum-metric {
          description
            "maximum metric to reach release node";
          leaf max-met {
            description
              "metric value";
            type uint32 {
              range "1..4294967295";
            }
          }
        }
      }
      container level-2 {
        description
          "Apply to level-2";
        presence "true";
        container maximum-metric {
          description
            "maximum metric to reach release node";
          leaf max-met {
            description
              "metric value";
            type uint32 {
              range "1..4294967295";
            }
          }
        }
      }
    }
    container hello {
      description
        "Pad ISIS hello PDUs to full MTU";
      container padding {
        description
          "Pad hello PDU";
        presence "Pad hello PDU";
        leaf pad-type {
          type enumeration {
            enum "multi-point";
            enum "point-to-point";
          }
        }
      }
    }
    container hostname {
      description
        "Dynamic hostname for IS-IS";
      leaf dynamic {
        description
          "Dynamic hostname";
        type empty;
      }
    }
    leaf ignore-lsp-errors {
      description
        "Ignore LSPs with bad checksums";
      type empty;
    }
    leaf is-type {
      description
        "IS Level for this routing process (OSI only)";
      type enumeration {
        enum "level-1";
        enum "level-1-2";
        enum "level-2-only";
      }
    }
    container ispf {
      description
        "Configure execution of incremental SPF";
      leaf level {
        type enumeration {
          enum "level-1";
          enum "level-1-2";
          enum "level-2";
        }
      }
      leaf number {
        type uint32 {
          range "1 .. 600";
        }
      }
    }
    container log-adjacency-changes {
      description
        "Log changes in adjacency state";
      presence "Log changes in adjacency state";
      leaf all {
        description
          "Include changes generated by non-IIH event";
        type empty;
      }
    }
    container lsp-full {
      description
        "If we run out of LSP fragments";
      container suppress {
        description
          "suppress the following types of IP prefixes";
        choice lsp-full-choince {
          container external-interlevel-container {
            leaf external {
              description
                "don't advertise IP prefixes learned from other protocols";
              type empty;
            }
            leaf interlevel {
              description
                "don't advertise IP prefixes learned from another ISIS level";
              type empty;
            }
          }
          leaf none {
            description
              "don't suppress any prefixes";
            type empty;
          }
        }
      }
    }
    container lsp-gen-interval {
      description
        "Minimum interval between regenerating same LSP";
      choice lsp-gen-interval-choice {
        container intervals {
          uses ncs_rpc_notif_lsp-gen-interval-grouping;
        }
        container intervals-levels {
          container intervals-level-1 {
            leaf level-1 {
              description
                "Set interval for level 1 only";
              type empty;
            }
            uses ncs_rpc_notif_lsp-gen-interval-grouping;
          }
          container intervals-level-2 {
            leaf level-2 {
              description
                "Set interval for level 2 only";
              type empty;
            }
            uses ncs_rpc_notif_lsp-gen-interval-grouping;
          }
        }
      }
    }
    leaf lsp-mtu {
      description
        "Set maximum LSP size";
      type uint32 {
        range "128 .. 4352";
      }
    }
    leaf lsp-refresh-interval {
      description
        "Set LSP refresh interval";
      type uint32 {
        range "1 .. 65535";
      }
    }
    leaf max-area-addresses {
      description
        "Allow configuration of more manual area addresses";
      type uint32 {
        range "3 .. 254";
      }
    }
    leaf max-lsp-lifetime {
      description
        "Set maximum LSP lifetime";
      type uint32 {
        range "1 .. 65535";
      }
    }
    container microloop {
      description
        "Enable microloop protection configuration commands";
      container avoidance {
        description
          "Enable local microloop avoidance";
        presence "true";
        leaf disable {
          description
            "Disable Microloop avoidance";
          type empty;
        }
        leaf protected {
          description
            "Microloop avoidance for protected link or prefix only";
          type empty;
        }
        leaf rib-update-delay {
          description
            "Value of the delay in milliseconds";
          type uint32 {
            range "1..600000";
          }
        }
      }
    }
    container mpls {
      description
        "Configure MPLS routing protocol parameters";
      container ldp {
        description
          "routing protocol commands for MPLS LDP";
        container autoconfig {
          description
            "Configure LDP automatic configuration";
          presence "true";
          leaf level-1 {
            description
              "Configure ISIS level-1 to run MPLS LDP";
            type empty;
          }
          leaf level-2 {
            description
              "Configure ISIS level-2 to run MPLS LDP";
            type empty;
          }
        }
        leaf sync {
          description
            "Configure LDP-IGP Synchronization";
          type empty;
        }
        leaf sync-igp-shortcuts {
          description
            "Configure LDP-IGP Synchronization on MPLS shortcuts";
          type empty;
        }
      }
      container traffic-eng {
        description
          "routing protocol commands for MPLS Traffic Engineering";
        leaf level-1 {
          description
            "Run MPLS TE on IS-IS level 1 only";
          type empty;
        }
        leaf level-2 {
          description
            "Run MPLS TE on IS-IS level 2 only";
          type empty;
        }
        leaf multicast-intact {
          description
            "MPLS TE and PIM interaction";
          type empty;
        }
        container router-id {
          description
            "Traffic Engineering stable IP address for system";
          uses ios-ifc:ncs_rpc_notif_interface-grouping;
        }
        container scanner {
          description
            "Timer parameters for TE database";
          leaf interval {
            description
              "Time (secs) between LSPDB walks for TE";
            type uint32 {
              range "1 .. 60";
            }
          }
          leaf max-flash {
            description
              "Max. number of LSPs ISIS may send to TE db without delay: <0..200>";
            type uint32 {
              range "0 .. 200";
            }
          }
        }
      }
    }
    list net {
      description
        "A Network Entity Title for this process (OSI only)";
      key "tag";
      leaf tag {
        type isis-net;
      }
    }
    container nsf {
      description
        "Non-stop forwarding";
      leaf cisco {
        description
          "Checkpoint method";
        type empty;
      }
      leaf ietf {
        description
          "IETF method";
        type empty;
      }
      container interface {
        description
          "Interface properties";
        leaf wait {
          description
            "Seconds";
          type uint8 {
            range "1..60";
          }
        }
      }
      leaf interval {
        description
          "Minutes";
        type uint16 {
          range "0..1440";
        }
      }
    }
    container partition {
      description
        "CLNS area partition";
      leaf avoidance {
        description
          "Withdraw area prefix if partition detected";
        type empty;
      }
    }
    uses ios-ifc:ncs_rpc_notif_passive-interface-grouping;
    container protocol {
      description
        "Set protocol's administrative state";
      leaf shutdown {
        description
          "Set protocol's administrative state to disable";
        type empty;
      }
    }
    container segment-routing {
      description
        "Enable Segment Routing Feature";
      leaf mpls {
        description
          "Enable Segment Routing Feature using MPLS encapsulation";
        type empty;
      }
      container prefix-sid-map {
        description
          "Enable prefix-sid-map";
        leaf advertise-local {
          description
            "Advertise active local prefix-SID mappings";
          type empty;
        }
        container receive {
          description
            "Enable prefix-SID mapping client";
          presence "true";
          leaf disable {
            description
              "Disable prefix-SID mapping";
            type empty;
          }
        }
      }
    }
    container skeptical {
      description
        "Be a cautious NSF helper when refresh adjacency";
      leaf interval {
        description
          "Minutes";
        type uint16 {
          range "0..1440";
        }
      }
    }
    leaf update-queue-depth {
      description
        "Set Update process queue depth";
      type uint32 {
        range "1 .. 2147483647";
      }
    }
    container use {
      description
        "Use different algorithms during SPF";
      leaf external-metrics {
        description
          "Honour external metrics during SPF";
        type empty;
      }
    }
    leaf vrf {
      description
        "VRF name for this process";
      type string;
    }
    uses ncs_rpc_notif_isis-ipv4-ipv6-common-grouping;
  }

  grouping ncs_rpc_notif_config-isis-container-grouping {
    container isis-container {
      list isis {
        description
          "ISO IS-IS";
        key "area-tag";
        leaf area-tag {
          type string;
        }
        uses ncs_rpc_notif_config-isis-main-grouping;
      }
    }
  }

  grouping ncs_rpc_notif_config-isis-grouping {
    container isis {
      description
        "ISO IS-IS";
      presence "true";
      uses ncs_rpc_notif_config-isis-main-grouping;
    }
  }

  grouping live_ncs_config-interface-isis-grouping {
    container adjacency-filter {
      description
        "Filter IS-IS adjacencies";
      leaf name {
        type string;
      }
      leaf match-all {
        description
          "Match all area addresses";
        type empty;
      }
    }
    container advertise {
      description
        "Control addresses advertisements in LSPs";
      leaf prefix {
        description
          "Interface IP address";
        type empty;
      }
    }
    container authentication {
      description
        "ISIS authentication for interface related PDUs";
      uses live_ncs_isis-authentication-grouping;
    }
    container circuit-type {
      description
        "Configure circuit type for interface";
      presence "true";
      leaf levels {
        type enumeration {
          enum "level-1";
          enum "level-1-2";
          enum "level-2-only";
        }
      }
    }
    container csnp-interval {
      description
        "Set CSNP interval in seconds";
      choice csnp-interval-choice {
        case csnp-interval-level-case {
          list csnp-interval-list {
            key "levels";
            leaf levels {
              type enumeration {
                enum "level-1";
                enum "level-2";
              }
            }
            leaf value {
              type uint16;
            }
          }
        }
        case csnp-interval-only-case {
          leaf value {
            type uint16;
          }
        }
      }
    }
    container hello {
      description
        "Add padding to IS-IS hello packets";
      container padding {
        description
          "Pad hello packets";
        presence "true";
        leaf always {
          description
            "Never pad hello packets if no prefix present";
          type empty;
        }
      }
    }
    container hello-interval {
      description
        "Set Hello interval in seconds";
      choice hello-interval-choice {
        case hello-interval-level-case {
          list hello-interval-list {
            key "levels";
            leaf levels {
              type enumeration {
                enum "level-1";
                enum "level-2";
              }
            }
            leaf value {
              type union {
                type uint16 {
                  range "1..65535";
                }
                type enumeration {
                  enum "minimal";
                }
              }
            }
          }
        }
        case hello-interval-only-case {
          leaf value {
            type union {
              type uint16 {
                range "1..65535";
              }
              type enumeration {
                enum "minimal";
              }
            }
          }
        }
      }
    }
    container hello-multiplier {
      description
        "Set multiplier for Hello holding time";
      choice hello-multiplier-choice {
        case hello-multiplier-level-case {
          list hello-multiplier-list {
            key "levels";
            leaf levels {
              type enumeration {
                enum "level-1";
                enum "level-2";
              }
            }
            leaf value {
              type uint16 {
                range "3..1000";
              }
            }
          }
        }
        case hello-multiplier-only-case {
          leaf value {
            type uint16 {
              range "3..1000";
            }
          }
        }
      }
    }
    container ipv6 {
      description
        "IPv6 interface configuration";
      uses live_ncs_isis-metric-grouping;
      leaf tag {
        description
          "Assign an admin tag to an ISIS interface IPv6 route";
        type uint32 {
          range "1..4294967295";
        }
      }
    }
    leaf lsp-interval {
      description
        "Set LSP transmission interval";
      type uint32 {
        range "1..4294967295";
      }
    }
    leaf mesh-group {
      description
        "Set ISIS mesh group";
      type union {
        type uint32 {
          range "1..4294967295";
        }
        type enumeration {
          enum "blocked";
        }
      }
    }
    uses live_ncs_isis-metric-grouping;
    leaf network {
      description
        "Network type";
      type enumeration {
        enum "point-to-point";
      }
    }
    container password {
      description
        "Configure the authentication password for interface";
      choice password-choice {
        case password-level-case {
          list password-list {
            key "levels";
            leaf levels {
              type enumeration {
                enum "level-1";
                enum "level-2";
              }
            }
            leaf password {
              type string;
            }
          }
        }
        case password-only-case {
          leaf password {
            type string;
          }
        }
      }
    }
    container priority {
      description
        "Set priority for Designated Router election";
      choice priority-choice {
        case priority-level-case {
          list priority-list {
            key "levels";
            leaf levels {
              type enumeration {
                enum "level-1";
                enum "level-2";
              }
            }
            leaf value {
              type uint8 {
                range "0..127";
              }
            }
          }
        }
        case priority-only-case {
          leaf value {
            type uint8 {
              range "0..127";
            }
          }
        }
      }
    }
    leaf protocol {
      description
        "Set ISIS protocol's state under current interface";
      type enumeration {
        enum "shutdown";
      }
    }
    leaf retransmit-interval {
      description
        "Set per-LSP retransmission interval";
      type uint16;
    }
    leaf retransmit-throttle-interval {
      description
        "Set interface LSP retransmission interval";
      type uint16;
    }
    leaf tag {
      description
        "Assign an admin tag to an ISIS interface IP route";
      type uint32 {
        range "1..4294967295";
      }
    }
    container three-way-handshake {
      description
        "Select Cisco or IETF three-way handshake";
      presence "true";
      leaf implementor {
        type enumeration {
          enum "cisco";
          enum "ietf";
        }
      }
    }
  }

  grouping live_ncs_narrow-wide-transition-grouping {
    leaf narrow-wide {
      type isis-level-type;
    }
    leaf transition {
      description
        "Accept both styles of TLVs during transition";
      type isis-level-type;
    }
  }

  grouping live_ncs_spf-intervals-grouping {
    leaf interval {
      type uint32 {
        range "1 .. 120";
      }
    }
    leaf initial-wait {
      type uint32 {
        range "1 .. 120000";
      }
    }
    leaf minimum-wait {
      type uint32 {
        range "1 .. 120000";
      }
    }
  }

  grouping live_ncs_authenticate-snp-grouping {
    leaf authenticate {
      description
        "Authentication";
      type empty;
    }
    leaf snp {
      description
        "SNP PDUs";
      type enumeration {
        enum "send-only";
        enum "validate";
      }
    }
  }

  grouping live_ncs_lsp-gen-interval-grouping {
    leaf interval {
      type uint32 {
        range "1 .. 120";
      }
    }
    leaf initial-wait {
      type uint32 {
        range "1 .. 120000";
      }
    }
    leaf wait {
      type uint32 {
        range "1 .. 120000";
      }
    }
  }

  grouping live_ncs_set-overload-bit-suppress-grouping {
    leaf external {
      description
        "If overload-bit set, don't advertise IP prefixes learned from other protocols";
      type empty;
    }
    leaf interlevel {
      description
        "If overload-bit set, don't advertise IP prefixes learned from another ISIS level";
      type empty;
    }
  }

  grouping live_ncs_summary-address-metric-tag-grouping {
    leaf metric {
      description
        "Set metric for summay route";
      type uint32 {
        range "1 .. 4294967295";
      }
    }
    leaf tag {
      description
        "Set tag";
      type uint32 {
        range "1 .. 4294967295";
      }
    }
  }

  grouping live_ncs_authentication-level-grouping {
    leaf levels {
      type authentication-level-type;
    }
  }

  grouping live_ncs_isis-authentication-grouping {
    container mode {
      description
        "Authentication mode";
      container md5 {
        description
          "Keyed message digest";
        presence "Keyed message digest";
        uses live_ncs_authentication-level-grouping;
      }
      container text {
        description
          "Clear text password";
        presence "Clear text password";
        uses live_ncs_authentication-level-grouping;
      }
    }
    container key-chain {
      description
        "Authentication key-chain";
      choice key-chain-choice {
        case key-chain-level-case {
          list key-chain-list {
            key "levels";
            uses live_ncs_authentication-level-grouping;
            leaf name {
              type string;
            }
          }
        }
        case key-chain-only-case {
          leaf name {
            type string;
          }
        }
      }
    }
    container send-only {
      description
        "Authentication send only, receive ignore";
      presence "Authentication send only, receive ignore";
      uses live_ncs_authentication-level-grouping;
    }
  }

  grouping live_ncs_isis-metric-grouping {
    container metric {
      description
        "Configure the metric for interface";
      choice metric-choice {
        case metric-level-case {
          list metric-list {
            key "levels";
            leaf levels {
              type enumeration {
                enum "level-1";
                enum "level-2";
              }
            }
            leaf value {
              type union {
                type uint32 {
                  range "1..16777214";
                }
                type enumeration {
                  enum "maximum";
                }
              }
            }
          }
        }
        case metric-only-case {
          leaf value {
            type union {
              type uint32 {
                range "1..16777214";
              }
              type enumeration {
                enum "maximum";
              }
            }
          }
        }
      }
    }
  }

  grouping live_ncs_redist-level-grouping {
    leaf levels {
      type isis-routes-level-type;
    }
  }

  grouping live_ncs_isis-redist-grouping {
    leaf levels {
      type isis-routes-level-type;
    }
    leaf metric {
      description
        "ISIS default metric";
      type uint32 {
        range "0 .. 4294967295";
      }
    }
    leaf metric-type {
      description
        "OSPF/IS-IS exterior metric type for redistributed routes";
      type enumeration {
        enum "external";
        enum "internal";
        enum "rib-metric-as-external";
        enum "rib-metric-as-internal";
      }
    }
    leaf route-map {
      description
        "Route map reference";
      type string;
    }
  }

  grouping live_ncs_isis-redist-af-grouping {
    leaf include-connected {
      description
        "Include connected";
      type empty;
    }
    uses live_ncs_isis-redist-grouping;
  }

  grouping live_ncs_isis-redist-ospf-match-grouping {
    uses live_ncs_redist-level-grouping;
    leaf metric {
      description
        "ISIS default metric";
      type uint32 {
        range "0 .. 4294967295";
      }
    }
    leaf route-map {
      description
        "Route map reference";
      type string;
    }
  }

  grouping live_ncs_isis-redist-clns-ip-grouping {
    container clns {
      description
        "Redistribution of BGP NSAP routes";
      presence "Redistribution of BGP NSAP routes";
      uses live_ncs_isis-redist-grouping;
    }
    container ip {
      description
        "Redistribution of BGP IP routes";
      presence "true";
      uses live_ncs_isis-redist-grouping;
    }
  }

  grouping live_ncs_isis-ipv4-ipv6-common-grouping {
    leaf adjacency-check {
      description
        "Check ISIS neighbor protocol support";
      type empty;
    }
    container bfd {
      description
        "BFD configuration commands";
      leaf all-interfaces {
        description
          "Enable BFD on all interfaces";
        type empty;
      }
      leaf check-ctrl-plane-failure {
        description
          "BFD check control plane failure";
        type empty;
      }
    }
    leaf router-id {
      description
        "Interface of stable IP address for system";
      type string;
    }
  }

  grouping live_ncs_isis-common-grouping {
    container advertise {
      description
        "Control which IP routes flow in L1 and L2 LSPs";
      leaf passive-only {
        description
          "only interface address of passive interfaces";
        type empty;
      }
    }
    container default-information {
      description
        "Control distribution of default information";
      container originate {
        presence "Distribute a default route";
        description
          "Distribute a default route";
        leaf route-map {
          description
            "Route-map reference";
          type string;
        }
      }
    }
    leaf help {
      description
        "Description of the interactive help system";
      type empty;
    }
    leaf maximum-paths {
      description
        "Forward packets over multiple paths";
      type uint32 {
        range "1 .. 32";
      }
    }
    container metric {
      description
        "Set ISIS metric for all interfaces";
      choice metric-choice {
        case metric-level-case {
          list metrics {
            key "level";
            leaf level {
              type enumeration {
                enum "level-1";
                enum "level-2";
              }
            }
            leaf metric {
              type uint32 {
                range "1..16777214";
              }
            }
          }
        }
        case metric-only-case {
          leaf metric {
            type uint32 {
              range "1..16777214";
            }
          }
        }
      }
    }
    container prc-interval {
      description
        "Minimum interval between partial route calculations";
      leaf interval {
        type uint32 {
          range "1 .. 120";
        }
      }
      leaf initial-wait {
        type uint32 {
          range "1 .. 120000";
        }
      }
      leaf minimum-wait {
        type uint32 {
          range "1 .. 120000";
        }
      }
    }
    container set-overload-bit {
      description
        "Signal other routers not to use us in SPF";
      presence "Signal other routers not to use us in SPF";
      choice set-overload-bit-choice {
        container on-startup {
          description
            "Set overload-bit only temporarily after reboot";
          choice on-startup-choice {
            container time {
              leaf time {
                type uint32 {
                  range "5 .. 86400";
                }
              }
              leaf suppress {
                description
                  "If overload-bit set, suppress the following types of IP prefixes";
                type empty;
              }
              leaf external {
                description
                  "If overload-bit set, don't advertise IP prefixes learned from other protocols";
                type empty;
              }
              leaf interlevel {
                description
                  "If overload-bit set, don't advertise IP prefixes learned from another ISIS level";
                type empty;
              }
            }
            container wait-for-bgp {
              description
                "Let BGP decide when to unset the overload bit";
              presence "Let BGP decide when to unset the overload bitW";
              container suppress {
                description
                  "If overload-bit set, suppress the following types of IP prefixes";
                uses live_ncs_set-overload-bit-suppress-grouping;
              }
            }
          }
        }
        container suppress {
          description
            "If overload-bit set, suppress the following types of IP prefixes";
          uses live_ncs_set-overload-bit-suppress-grouping;
        }
      }
    }
    container spf-interval {
      description
        "Minimum interval between SPF calculations";
      choice spf-interval-choice {
        list level-1-2 {
          key "level";
          leaf level {
            type enumeration {
              enum "level-1";
              enum "level-2";
            }
          }
          uses live_ncs_spf-intervals-grouping;
        }
        container intervals {
          uses live_ncs_spf-intervals-grouping;
        }
      }
    }
  }

  grouping live_ncs_isis-address-family-grouping {
    uses live_ncs_isis-common-grouping;
    uses live_ncs_isis-ipv4-ipv6-common-grouping;
    leaf distance {
      description
        "Administrative distance";
      type uint32 {
        range "1 .. 254";
      }
    }
    container distribute-list {
      description
        "Filter networks in routing updates";
      list prefix-list {
        description
          "Filter connections based on an IPv6 prefix-list";
        key "name";
        leaf name {
          type string;
        }
        container in {
          description
            "Filter incoming routing updates";
          presence "true";
          container interface {
            description
              "Specify interface";
            uses ios-ifc:live_ncs_interface-grouping;
          }
        }
      }
    }
    container ipv6 {
      description
        "IPv6 specific commands";
      container route {
        description
          "ISIS IPV6 routes";
        container priority {
          description
            "Assign priority to IPV6 prefixes";
          container high {
            description
              "Assign high priority to important IPV6 prefixes in ISIS IPV6 local RIB";
            leaf tag {
              description
                "Assign high priority to IPV6 prefixes with a specific route tag";
              type uint32;
            }
          }
        }
      }
    }
    container multi-topology {
      description
        "Enable multi-topology mode";
      presence "Enable multi-topology mode";
      leaf transition {
        description
          "Accept and generate both IS-IS IPv6 and Multi-topology IPv6 TLVs";
        type empty;
      }
    }
    container redistribute {
      description
        "Redistribute IPv6 prefixes from another routing protocol";
      container application {
        description
          "Application Protocol";
        presence "Application Protocol";
        uses live_ncs_isis-redist-af-grouping;
      }
      container bgp {
        description
          "Border Gateway Protocol (BGP)";
        leaf as-number {
          type ios-types:bgp-as-number-type;
        }
        uses live_ncs_isis-redist-af-grouping;
      }
      container connected {
        description
          "Connected";
        presence "Connected";
        uses live_ncs_isis-redist-grouping;
      }
      list eigrp {
        description
          "Enhanced Interior Gateway Routing Protocol (EIGRP)";
        key "as-number";
        leaf as-number {
          type uint32 {
            range "1 .. 65535";
          }
        }
        uses live_ncs_isis-redist-af-grouping;
      }
      container isis {
        description
          "ISO IS-IS";
        presence "true";
        list isis-redistribute {
          key "area-tag";
          leaf area-tag {
            type string;
          }
          uses live_ncs_isis-redist-af-grouping;
        }
        list isis-leak {
          key "isis-redist-levels1 isis-redist-levels2";
          leaf isis-redist-levels1 {
            type enumeration {
              enum "level-1";
              enum "level-2";
            }
          }
          leaf isis-redist-levels2 {
            type enumeration {
              enum "level-1";
              enum "level-2";
            }
          }
          leaf into {
            description
              "from level-n into level-m";
            type empty;
          }
          choice isis-redist-isis-ip-choice {
            leaf distribute-list {
              description
                "select routes";
              type string;
            }
            leaf route-map {
              description
                "Route map for route matching";
              type string;
            }
          }
        }
      }
      container lisp {
        description
          "Locator ID Separation Protocol (LISP)";
        presence "Locator ID Separation Protocol (LISP)";
        uses live_ncs_isis-redist-af-grouping;
      }
      container nd {
        description
          "Neighbor Discovery";
        presence "Neighbor Discovery";
        uses live_ncs_isis-redist-af-grouping;
      }
      container nemo {
        description
          "Network Mobility (NEMO)";
        uses live_ncs_isis-redist-af-grouping;
      }
      list ospf {
        description
          "Open Shortest Path First (OSPF)";
        key "process-id";
        leaf process-id {
          type uint32 {
            range "1 .. 65535";
          }
        }
        uses live_ncs_isis-redist-af-grouping;
        container match {
          description
            "Redistribution of OSPF routes";
          container internal {
            presence "Redistribute OSPF internal routes";
            description
              "Redistribute OSPF internal routes";
            uses live_ncs_isis-redist-grouping;
          }
          container external {
            description
              "Redistribute OSPF external routes";
            presence "Redistribute OSPF external routes";
            leaf external-routes {
              type ios-types:redist-ospf-external-type;
            }
            uses live_ncs_isis-redist-grouping;
          }
          container nssa-external {
            description
              "Redistribute OSPF NSSA external routes";
            presence "Redistribute OSPF NSSA external routes";
            leaf nssa-external-routes {
              type ios-types:redist-ospf-external-type;
            }
            uses live_ncs_isis-redist-grouping;
          }
        }
      }
      list rip {
        description
          "IPv6 Routing Information Protocol (RIPv6)";
        key "process";
        leaf process {
          type string;
        }
        uses live_ncs_isis-redist-af-grouping;
      }
      container static {
        description
          "Static routes";
        presence "Static routes";
        uses live_ncs_isis-redist-grouping;
      }
    }
    list summary-prefix {
      description
        "Configure IPv6 summary prefix";
      key "prefix";
      leaf prefix {
        type ios-types:ipv6-prefix;
      }
      leaf levels {
        type enumeration {
          enum "level-1";
          enum "level-1-2";
          enum "level-2";
        }
      }
    }
    container table-map {
      description
        "Map external entry attributes into routing table";
      leaf name {
        type string;
      }
      leaf filter {
        description
          "Selective route download";
        type empty;
      }
    }
  }

  grouping live_ncs_isis-redist-vrf-grouping {
    container application {
      description
        "Application";
      list appname {
        key "appname";
        leaf appname {
          description
            "Application name";
          type string;
        }
        uses live_ncs_isis-redist-grouping;
      }
    }
    container bgp {
      description
        "Border Gateway Protocol (BGP)";
      list bp-as-num {
        key "bp-as-num";
        leaf bp-as-num {
          description
            "Autonomous system number";
          type ios-types:bgp-as-number-type;
        }
        uses live_ncs_isis-redist-clns-ip-grouping;
        uses live_ncs_isis-redist-grouping;
      }
      leaf a_LESSER_1_PERIOD_0-XX_PERIOD_YY_GREATER_ {
        description
          "Autonomous system number";
        type empty;
      }
    }
    container connected {
      description
        "Connected";
      presence "true";
      uses live_ncs_isis-redist-grouping;
    }
    container eigrp {
      description
        "Enhanced Interior Gateway Routing Protocol (EIGRP)";
      list eigrp-as {
        key "eigrp-as";
        leaf eigrp-as {
          description
            "AS number";
          type uint16 {
            range "1..65535";
          }
        }
        uses live_ncs_isis-redist-grouping;
      }
    }
    container isis {
      description
        "ISO IS-IS";
      list isis-atag {
        key "isis-atag";
        leaf isis-atag {
          description
            "ISO routing area tag";
          type string;
        }
        container ip {
          description
            "Redistribution of IP routes between levels or processes";
          uses live_ncs_isis-redist-grouping;
        }
      }
      container ip {
        description
          "Redistribution of IP routes between levels or processes";
        presence "true";
        uses live_ncs_isis-redist-grouping;
      }
    }
    container iso-igrp {
      description
        "IGRP for OSI networks";
      presence "true";
      list iso-atag {
        key "iso-atag";
        leaf iso-atag {
          description
            "ISO routing area tag";
          type string;
        }
        leaf route-map {
          description
            "Route map reference";
          type empty;
        }
      }
      container route-map {
        description
          "Route map reference";
        presence "true";
        leaf rm-point {
          description
            "Pointer to route-map entries";
          type string;
        }
      }
    }
    container lisp {
      description
        "Locator ID Separation Protocol (LISP)";
      presence "true";
      uses live_ncs_isis-redist-grouping;
    }
    container mobile {
      description
        "Mobile routes";
      presence "true";
      uses live_ncs_isis-redist-grouping;
    }
    leaf ospf {
      description
        "Process ID";
      type uint16 {
        range "1..65535";
      }
    }
    container ospfv3 {
      description
        "OSPFv3";
      list os3-id {
        key "os3-id";
        leaf os3-id {
          description
            "Process ID";
          type uint16 {
            range "1..65535";
          }
        }
        uses live_ncs_isis-redist-grouping;
      }
    }
    container rip {
      description
        "Routing Information Protocol (RIP)";
      presence "true";
      uses live_ncs_isis-redist-grouping;
    }
    container static {
      description
        "Static routes";
      presence "true";
      uses live_ncs_isis-redist-clns-ip-grouping;
      uses live_ncs_isis-redist-grouping;
    }
  }

  grouping live_ncs_tie-break-prefer-repair-grouping {
    leaf downstream {
      description
        "priority number";
      type uint8 {
        range "1..255";
      }
    }
    leaf linecard-disjoint {
      description
        "priority number";
      type uint8 {
        range "1..255";
      }
    }
    leaf lowest-backup-path-metric {
      description
        "priority number";
      type uint8 {
        range "1..255";
      }
    }
    leaf node-protecting {
      description
        "priority number";
      type uint8 {
        range "1..255";
      }
    }
    leaf primary-path {
      description
        "priority number";
      type uint8 {
        range "1..255";
      }
    }
    leaf secondary-path {
      description
        "priority number";
      type uint8 {
        range "1..255";
      }
    }
    leaf srlg-disjoint {
      description
        "priority number";
      type uint8 {
        range "1..255";
      }
    }
  }

  grouping live_ncs_isis-topology-grouping {
    list distance {
      description
        "Define an administrative distance";
      key "number";
      leaf number {
        type uint8 {
          range "1 .. 255";
        }
      }
      list ip-list {
        key "ip";
        leaf ip {
          description
            "IP Source address";
          type inet:ipv4-address;
        }
        list wildcard-bits {
          key "w-bits";
          leaf w-bits {
            type inet:ipv4-address;
          }
          leaf access-list {
            type ios-types:default-access-list-standard-id-type;
          }
        }
      }
      leaf clns {
        description
          "Distance applied for CLNS derived routes";
        type empty;
      }
      leaf ip {
        description
          "Distance applied for IP derived routes";
        type empty;
      }
    }
    container ip {
      description
        "IP specific commands";
      container route {
        description
          "ISIS IP routes";
        container priority {
          description
            "Assign priority to IP prefixes";
          container high {
            description
              "Assign high priority to important IP prefixes in ISIS IP local RIB";
            leaf tag {
              description
                "Assign high priority to IP prefixes with a specific route tag";
              type uint32 {
                range "1 .. 4294967295";
              }
            }
          }
        }
      }
    }
    leaf priority {
      description
        "priority value";
      type uint8 {
        range "0..127";
      }
    }
    container redistribute {
      description
        "Redistribute information from another routing protocol";
      list application {
        description
          "Application";
        key "name";
        leaf name {
          description
            "Application name";
          type string;
        }
        uses live_ncs_isis-redist-grouping;
      }
      container bgp {
        description
          "Border Gateway Protocol (BGP)";
        leaf as-number {
          type ios-types:bgp-as-number-type;
        }
        uses live_ncs_isis-redist-grouping;
        uses live_ncs_isis-redist-clns-ip-grouping;
      }
      container connected {
        description
          "Connected";
        presence "Connected";
        uses live_ncs_isis-redist-grouping;
      }
      list eigrp {
        description
          "Enhanced Interior Gateway Routing Protocol (EIGRP)";
        key "as-number";
        leaf as-number {
          type uint32 {
            range "1 .. 65535";
          }
        }
        uses live_ncs_isis-redist-grouping;
      }
      container isis {
        description
          "ISO IS-IS";
        list isis-redistribute {
          key "area-tag";
          leaf area-tag {
            type string;
          }
          container ip {
            description
              "Redistribution of IP routes between levels or processes";
            presence "true";
            uses live_ncs_isis-redist-grouping;
          }
        }
        list ip {
          description
            "Redistribution of IP routes between levels";
          key "isis-redist-levels1 isis-redist-levels2";
          leaf isis-redist-levels1 {
            type enumeration {
              enum "level-1";
              enum "level-2";
            }
          }
          leaf isis-redist-levels2 {
            type enumeration {
              enum "level-1";
              enum "level-2";
            }
          }
          leaf into {
            description
              "from level-n into level-m";
            type empty;
          }
          choice isis-redist-isis-ip-choice {
            leaf distribute-list {
              description
                "select routes";
              type uint32 {
                range "100 .. 199";
              }
            }
            leaf route-map {
              description
                "Route map for route matching";
              type string;
            }
          }
        }
      }
      container iso-igrp {
        description
          "IGRP for OSI networks";
        presence "IGRP for OSI networks";
        choice iso-igrp-choice {
          container area-tag-route-map-container {
            leaf area-tag {
              type string;
            }
            leaf route-map {
              description
                "Route map reference";
              type string;
            }
          }
          leaf route-map {
            description
              "Route map reference";
            type string;
          }
        }
        uses live_ncs_redist-level-grouping;
        leaf metric {
          description
            "ISIS default metric";
          type uint32 {
            range "0 .. 4294967295";
          }
        }
        leaf metric-type {
          description
            "OSPF/IS-IS exterior metric type for redistributed routes";
          type enumeration {
            enum "external";
            enum "internal";
            enum "rib-metric-as-external";
            enum "rib-metric-as-internal";
          }
        }
      }
      container lisp {
        description
          "Locator ID Separation Protocol (LISP)";
        presence "true";
        uses live_ncs_isis-redist-af-grouping;
      }
      container maximum-prefix {
        description
          "Maximum number of prefixes redistributed to protocol";
        leaf number {
          type uint32 {
            range "1 .. 4294967295";
          }
        }
        leaf threshold-value {
          type uint32 {
            range "1 .. 100";
          }
        }
        leaf warning-only {
          description
            "Only give warning message when limit is exceeded";
          type empty;
        }
        leaf withdraw {
          description
            "Withdraw redistibuted prefixes";
          type empty;
        }
      }
      container mobile {
        description
          "Mobile routes";
        presence "Mobile routes";
        uses live_ncs_isis-redist-grouping;
      }
      container odr {
        description
          "On Demand stub Routes";
        presence "On Demand stub Routes";
        uses live_ncs_isis-redist-grouping;
      }
      list ospf {
        description
          "Open Shortest Path First (OSPF)";
        key "process-id";
        leaf process-id {
          type uint32 {
            range "1 .. 65535";
          }
        }
        uses live_ncs_isis-redist-grouping;
        container match {
          description
            "Redistribution of OSPF routes";
          container internal {
            presence "Redistribute OSPF internal routes";
            description
              "Redistribute OSPF internal routes";
            uses live_ncs_isis-redist-grouping;
          }
          container external {
            description
              "Redistribute OSPF external routes";
            presence "Redistribute OSPF external routes";
            leaf external-routes {
              type ios-types:redist-ospf-external-type;
            }
            uses live_ncs_isis-redist-grouping;
          }
          container nssa-external {
            description
              "Redistribute OSPF NSSA external routes";
            presence "Redistribute OSPF NSSA external routes";
            leaf nssa-external-routes {
              type ios-types:redist-ospf-external-type;
            }
            uses live_ncs_isis-redist-grouping;
          }
        }
        leaf vrf {
          description
            "VPN Routing/Forwarding Instance";
          type string;
        }
      }
      list ospfv3 {
        description
          "Open Shortest Path First (OSPF)";
        key "process-id";
        leaf process-id {
          type uint32 {
            range "1 .. 65535";
          }
        }
        uses live_ncs_isis-redist-grouping;
        container match {
          description
            "Redistribution of OSPF routes";
          container internal {
            presence "Redistribute OSPF internal routes";
            description
              "Redistribute OSPF internal routes";
            uses live_ncs_isis-redist-grouping;
          }
          container external {
            description
              "Redistribute OSPF external routes";
            presence "Redistribute OSPF external routes";
            leaf external-routes {
              type ios-types:redist-ospf-external-type;
            }
            uses live_ncs_isis-redist-grouping;
          }
          container nssa-external {
            description
              "Redistribute OSPF NSSA external routes";
            presence "Redistribute OSPF NSSA external routes";
            leaf nssa-external-routes {
              type ios-types:redist-ospf-external-type;
            }
            uses live_ncs_isis-redist-grouping;
          }
        }
        leaf vrf {
          description
            "VPN Routing/Forwarding Instance";
          type string;
        }
      }
      container rip {
        description
          "Routing Information Protocol (RIP)";
        presence "Routing Information Protocol (RIP)";
        uses live_ncs_isis-redist-grouping;
      }
      container static {
        description
          "Static routes";
        presence "Static routes";
        uses live_ncs_isis-redist-clns-ip-grouping;
      }
      container vrf {
        description
          "Specify a source VRF";
        list vrf-nm {
          key "vrf-nm";
          leaf vrf-nm {
            description
              "Source VRF name";
            type string;
          }
          uses live_ncs_isis-redist-vrf-grouping;
        }
        container global {
          description
            "global VRF";
          uses live_ncs_isis-redist-vrf-grouping;
        }
      }
    }
    container set-attached-bit {
      description
        "Conditionally advertise us as attached to L2";
      leaf route-map {
        description
          "Route-map reference";
        type string;
      }
    }
    uses ios-snmp:live_ncs_router-snmp-grouping;
    list summary-address {
      description
        "Configure IP address summaries";
      key "ip mask";
      leaf ip {
        type inet:ipv4-address;
      }
      leaf mask {
        type inet:ipv4-address;
      }
      container level-1 {
        description
          "Summarize into level-1 area";
        presence "Summarize into level-1 area";
        uses live_ncs_summary-address-metric-tag-grouping;
      }
      container level-1-2 {
        description
          "Summarize into both area and sub-domain";
        presence "Summarize into both area and sub-domain";
        uses live_ncs_summary-address-metric-tag-grouping;
      }
      container level-2 {
        description
          "Summarize into level-2 sub-domain";
        presence "Summarize into level-2 sub-domain";
        uses live_ncs_summary-address-metric-tag-grouping;
      }
      container metric-tag-container {
        uses live_ncs_summary-address-metric-tag-grouping;
      }
    }
    container traffic-share {
      description
        "How to compute traffic share over alternate paths";
      container min {
        description
          "All traffic shared among min metric paths";
        leaf across-interfaces {
          description
            "Use different interfaces for equal-cost paths";
          type empty;
        }
      }
    }
    uses live_ncs_isis-common-grouping;
  }

  grouping live_ncs_isis-af-ipv4-grouping {
    leaf help {
      description
        "Description of the interactive help system";
      type empty;
    }
    uses ios-snmp:live_ncs_router-snmp-grouping;
    list topology {
      description
        "Associate the routing protocol to a topology instance";
      key "name";
      leaf name {
        type string;
      }
      leaf tid {
        description
          "Configuring the routing protocol topology tid";
        type uint32 {
          range "5..4095";
        }
      }
      leaf ignore-attached-bit {
        description
          "Never install default route to closest L2 router";
        type empty;
      }
      uses live_ncs_isis-topology-grouping;
    }
  }

  grouping live_ncs_config-isis-main-grouping {
    container metric-style {
      description
        "Use old-style (ISO 10589) or new-style packet formats";
      choice metric-style-choice {
        container narrow {
          description
            "Use old style of TLVs with narrow metric";
          presence "true";
          uses live_ncs_narrow-wide-transition-grouping;
        }
        container transition {
          description
            "Send and accept both styles of TLVs during transition";
          presence "true";
          leaf transition {
            type isis-level-type;
          }
        }
        container wide {
          description
            "Use new style of TLVs to carry wider metric";
          presence "true";
          uses live_ncs_narrow-wide-transition-grouping;
        }
      }
    }
    container address-family {
      description
        "Enter Address Family command mode";
      container ipv4 {
        description
          "Address family";
        leaf unicast-multicast {
          type enumeration {
            enum "unicast";
            enum "multicast";
          }
        }
        uses live_ncs_isis-af-ipv4-grouping;
      }
      container ipv6 {
        description
          "Address family";
        leaf unicast {
          type empty;
        }
        uses live_ncs_isis-address-family-grouping;
      }
    }
    uses live_ncs_isis-topology-grouping;
    container area-password {
      description
        "Configure the authentication password for an area";
      leaf name {
        type string;
      }
      uses live_ncs_authenticate-snp-grouping;
    }
    container authentication {
      description
        "ISIS authentication for LSPs";
      uses live_ncs_isis-authentication-grouping;
    }
    container distribute-list {
      description
        "Filter networks in routing updates";
      choice distribute-list-choice {
        case acl-case {
          leaf acl-name {
            type ios-types:access-list-standard-id-type;
          }
          leaf in {
            description
              "Filter incoming routing updates";
            type string;
          }
        }
        case gateway-prefix-case {
          leaf gateway {
            description
              "Filtering incoming updates based on gateway";
            type string;
          }
          leaf prefix {
            description
              "Filter prefixes in routing updates";
            type string;
          }
          leaf gateway-prefix-in {
            description
              "Filter incoming routing updates";
            type string;
          }
        }
        case route-map-case {
          leaf route-map {
            description
              "Filter prefixes based on the route-map";
            type string;
          }
          leaf route-map-in {
            description
              "Filter incoming routing updates";
            type empty;
          }
        }
      }
    }
    container domain-password {
      description
        "Set the authentication password for a routing domain";
      leaf name {
        type string;
      }
      uses live_ncs_authenticate-snp-grouping;
    }
    container fast-flood {
      description
        "Flood LSPs (that triggered SPF) before running SPF";
      presence "Flood LSPs (that triggered SPF) before running SPF";
      leaf number {
        type uint32 {
          range "1 .. 15";
        }
      }
    }
    container fast-reroute {
      description
        "Configure Fast-Reroute";
      container load-sharing {
        description
          "Distributes repair paths equally among links and prefixes";
        container level-1 {
          description
            "Apply to level-1";
          presence "true";
          leaf disable {
            description
              "Disable load-sharing";
            type empty;
          }
        }
        container level-2 {
          description
            "Apply to level-2";
          presence "true";
          leaf disable {
            description
              "Disable load-sharing";
            type empty;
          }
        }
      }
      container per-prefix {
        description
          "Enable Fast-Reroute Per-Prefix";
        container level-1 {
          description
            "Apply to level-1";
          leaf all {
            description
              "Enable Fast-Reroute for primary paths";
            type empty;
          }
          leaf route-map {
            description
              "route-map name";
            type string;
          }
        }
        container level-2 {
          description
            "Apply to level-2";
          leaf all {
            description
              "Enable Fast-Reroute for primary paths";
            type empty;
          }
          leaf route-map {
            description
              "route-map name";
            type string;
          }
        }
      }
      container remote-lfa {
        description
          "Configuring fast-reroute remote-lfa";
        container level-1 {
          description
            "Apply to level-1";
          container mpls-ldp {
            description
              "Use mpls-ldp tunnel type";
            presence "true";
            container maximum-metric {
              description
                "maximum metric to reach release node";
              presence "true";
              leaf max-met {
                description
                  "metric value";
                type uint32 {
                  range "1..4294967295";
                }
              }
            }
          }
        }
        container level-2 {
          description
            "Apply to level-2";
          container mpls-ldp {
            description
              "Use mpls-ldp tunnel type";
            presence "true";
            container maximum-metric {
              description
                "maximum metric to reach release node";
              presence "true";
              leaf max-met {
                description
                  "metric value";
                type uint32 {
                  range "1..4294967295";
                }
              }
            }
          }
        }
      }
      container tie-break {
        description
          "Set repair path preference";
        container level-1 {
          description
            "Apply to level-1";
          uses live_ncs_tie-break-prefer-repair-grouping;
        }
        container level-2 {
          description
            "Apply to level-2";
          uses live_ncs_tie-break-prefer-repair-grouping;
        }
      }
    }
    container ti-lfa {
      container level-1 {
        description
          "Apply to level-1";
        container maximum-metric {
          description
            "maximum metric to reach release node";
          leaf max-met {
            description
              "metric value";
            type uint32 {
              range "1..4294967295";
            }
          }
        }
      }
      container level-2 {
        description
          "Apply to level-2";
        presence "true";
        container maximum-metric {
          description
            "maximum metric to reach release node";
          leaf max-met {
            description
              "metric value";
            type uint32 {
              range "1..4294967295";
            }
          }
        }
      }
    }
    container hello {
      description
        "Pad ISIS hello PDUs to full MTU";
      container padding {
        description
          "Pad hello PDU";
        presence "Pad hello PDU";
        leaf pad-type {
          type enumeration {
            enum "multi-point";
            enum "point-to-point";
          }
        }
      }
    }
    container hostname {
      description
        "Dynamic hostname for IS-IS";
      leaf dynamic {
        description
          "Dynamic hostname";
        type empty;
      }
    }
    leaf ignore-lsp-errors {
      description
        "Ignore LSPs with bad checksums";
      type empty;
    }
    leaf is-type {
      description
        "IS Level for this routing process (OSI only)";
      type enumeration {
        enum "level-1";
        enum "level-1-2";
        enum "level-2-only";
      }
    }
    container ispf {
      description
        "Configure execution of incremental SPF";
      leaf level {
        type enumeration {
          enum "level-1";
          enum "level-1-2";
          enum "level-2";
        }
      }
      leaf number {
        type uint32 {
          range "1 .. 600";
        }
      }
    }
    container log-adjacency-changes {
      description
        "Log changes in adjacency state";
      presence "Log changes in adjacency state";
      leaf all {
        description
          "Include changes generated by non-IIH event";
        type empty;
      }
    }
    container lsp-full {
      description
        "If we run out of LSP fragments";
      container suppress {
        description
          "suppress the following types of IP prefixes";
        choice lsp-full-choince {
          container external-interlevel-container {
            leaf external {
              description
                "don't advertise IP prefixes learned from other protocols";
              type empty;
            }
            leaf interlevel {
              description
                "don't advertise IP prefixes learned from another ISIS level";
              type empty;
            }
          }
          leaf none {
            description
              "don't suppress any prefixes";
            type empty;
          }
        }
      }
    }
    container lsp-gen-interval {
      description
        "Minimum interval between regenerating same LSP";
      choice lsp-gen-interval-choice {
        container intervals {
          uses live_ncs_lsp-gen-interval-grouping;
        }
        container intervals-levels {
          container intervals-level-1 {
            leaf level-1 {
              description
                "Set interval for level 1 only";
              type empty;
            }
            uses live_ncs_lsp-gen-interval-grouping;
          }
          container intervals-level-2 {
            leaf level-2 {
              description
                "Set interval for level 2 only";
              type empty;
            }
            uses live_ncs_lsp-gen-interval-grouping;
          }
        }
      }
    }
    leaf lsp-mtu {
      description
        "Set maximum LSP size";
      type uint32 {
        range "128 .. 4352";
      }
    }
    leaf lsp-refresh-interval {
      description
        "Set LSP refresh interval";
      type uint32 {
        range "1 .. 65535";
      }
    }
    leaf max-area-addresses {
      description
        "Allow configuration of more manual area addresses";
      type uint32 {
        range "3 .. 254";
      }
    }
    leaf max-lsp-lifetime {
      description
        "Set maximum LSP lifetime";
      type uint32 {
        range "1 .. 65535";
      }
    }
    container microloop {
      description
        "Enable microloop protection configuration commands";
      container avoidance {
        description
          "Enable local microloop avoidance";
        presence "true";
        leaf disable {
          description
            "Disable Microloop avoidance";
          type empty;
        }
        leaf protected {
          description
            "Microloop avoidance for protected link or prefix only";
          type empty;
        }
        leaf rib-update-delay {
          description
            "Value of the delay in milliseconds";
          type uint32 {
            range "1..600000";
          }
        }
      }
    }
    container mpls {
      description
        "Configure MPLS routing protocol parameters";
      container ldp {
        description
          "routing protocol commands for MPLS LDP";
        container autoconfig {
          description
            "Configure LDP automatic configuration";
          presence "true";
          leaf level-1 {
            description
              "Configure ISIS level-1 to run MPLS LDP";
            type empty;
          }
          leaf level-2 {
            description
              "Configure ISIS level-2 to run MPLS LDP";
            type empty;
          }
        }
        leaf sync {
          description
            "Configure LDP-IGP Synchronization";
          type empty;
        }
        leaf sync-igp-shortcuts {
          description
            "Configure LDP-IGP Synchronization on MPLS shortcuts";
          type empty;
        }
      }
      container traffic-eng {
        description
          "routing protocol commands for MPLS Traffic Engineering";
        leaf level-1 {
          description
            "Run MPLS TE on IS-IS level 1 only";
          type empty;
        }
        leaf level-2 {
          description
            "Run MPLS TE on IS-IS level 2 only";
          type empty;
        }
        leaf multicast-intact {
          description
            "MPLS TE and PIM interaction";
          type empty;
        }
        container router-id {
          description
            "Traffic Engineering stable IP address for system";
          uses ios-ifc:live_ncs_interface-grouping;
        }
        container scanner {
          description
            "Timer parameters for TE database";
          leaf interval {
            description
              "Time (secs) between LSPDB walks for TE";
            type uint32 {
              range "1 .. 60";
            }
          }
          leaf max-flash {
            description
              "Max. number of LSPs ISIS may send to TE db without delay: <0..200>";
            type uint32 {
              range "0 .. 200";
            }
          }
        }
      }
    }
    list net {
      description
        "A Network Entity Title for this process (OSI only)";
      key "tag";
      leaf tag {
        type isis-net;
      }
    }
    container nsf {
      description
        "Non-stop forwarding";
      leaf cisco {
        description
          "Checkpoint method";
        type empty;
      }
      leaf ietf {
        description
          "IETF method";
        type empty;
      }
      container interface {
        description
          "Interface properties";
        leaf wait {
          description
            "Seconds";
          type uint8 {
            range "1..60";
          }
        }
      }
      leaf interval {
        description
          "Minutes";
        type uint16 {
          range "0..1440";
        }
      }
    }
    container partition {
      description
        "CLNS area partition";
      leaf avoidance {
        description
          "Withdraw area prefix if partition detected";
        type empty;
      }
    }
    uses ios-ifc:live_ncs_passive-interface-grouping;
    container protocol {
      description
        "Set protocol's administrative state";
      leaf shutdown {
        description
          "Set protocol's administrative state to disable";
        type empty;
      }
    }
    container segment-routing {
      description
        "Enable Segment Routing Feature";
      leaf mpls {
        description
          "Enable Segment Routing Feature using MPLS encapsulation";
        type empty;
      }
      container prefix-sid-map {
        description
          "Enable prefix-sid-map";
        leaf advertise-local {
          description
            "Advertise active local prefix-SID mappings";
          type empty;
        }
        container receive {
          description
            "Enable prefix-SID mapping client";
          presence "true";
          leaf disable {
            description
              "Disable prefix-SID mapping";
            type empty;
          }
        }
      }
    }
    container skeptical {
      description
        "Be a cautious NSF helper when refresh adjacency";
      leaf interval {
        description
          "Minutes";
        type uint16 {
          range "0..1440";
        }
      }
    }
    leaf update-queue-depth {
      description
        "Set Update process queue depth";
      type uint32 {
        range "1 .. 2147483647";
      }
    }
    container use {
      description
        "Use different algorithms during SPF";
      leaf external-metrics {
        description
          "Honour external metrics during SPF";
        type empty;
      }
    }
    leaf vrf {
      description
        "VRF name for this process";
      type string;
    }
    uses live_ncs_isis-ipv4-ipv6-common-grouping;
  }

  grouping live_ncs_config-isis-container-grouping {
    container isis-container {
      list isis {
        description
          "ISO IS-IS";
        key "area-tag";
        leaf area-tag {
          type string;
        }
        uses live_ncs_config-isis-main-grouping;
      }
    }
  }

  grouping live_ncs_config-isis-grouping {
    container isis {
      description
        "ISO IS-IS";
      presence "true";
      uses live_ncs_config-isis-main-grouping;
    }
  }

  grouping config-interface-isis-grouping {
    container adjacency-filter {
      description
        "Filter IS-IS adjacencies";
      leaf name {
        type string;
      }
      leaf match-all {
        description
          "Match all area addresses";
        type empty;
      }
    }
    container advertise {
      description
        "Control addresses advertisements in LSPs";
      leaf prefix {
        description
          "Interface IP address";
        type empty;
      }
    }
    container authentication {
      description
        "ISIS authentication for interface related PDUs";
      uses isis-authentication-grouping;
    }
    container circuit-type {
      description
        "Configure circuit type for interface";
      presence "true";
      leaf levels {
        type enumeration {
          enum "level-1";
          enum "level-1-2";
          enum "level-2-only";
        }
      }
    }
    container csnp-interval {
      description
        "Set CSNP interval in seconds";
      choice csnp-interval-choice {
        case csnp-interval-level-case {
          list csnp-interval-list {
            key "levels";
            leaf levels {
              type enumeration {
                enum "level-1";
                enum "level-2";
              }
            }
            leaf value {
              type uint16;
            }
          }
        }
        case csnp-interval-only-case {
          leaf value {
            type uint16;
          }
        }
      }
    }
    container hello {
      description
        "Add padding to IS-IS hello packets";
      container padding {
        description
          "Pad hello packets";
        presence "true";
        leaf always {
          description
            "Never pad hello packets if no prefix present";
          type empty;
        }
      }
    }
    container hello-interval {
      description
        "Set Hello interval in seconds";
      choice hello-interval-choice {
        case hello-interval-level-case {
          list hello-interval-list {
            key "levels";
            leaf levels {
              type enumeration {
                enum "level-1";
                enum "level-2";
              }
            }
            leaf value {
              type union {
                type uint16 {
                  range "1..65535";
                }
                type enumeration {
                  enum "minimal";
                }
              }
            }
          }
        }
        case hello-interval-only-case {
          leaf value {
            type union {
              type uint16 {
                range "1..65535";
              }
              type enumeration {
                enum "minimal";
              }
            }
          }
        }
      }
    }
    container hello-multiplier {
      description
        "Set multiplier for Hello holding time";
      choice hello-multiplier-choice {
        case hello-multiplier-level-case {
          list hello-multiplier-list {
            key "levels";
            leaf levels {
              type enumeration {
                enum "level-1";
                enum "level-2";
              }
            }
            leaf value {
              type uint16 {
                range "3..1000";
              }
            }
          }
        }
        case hello-multiplier-only-case {
          leaf value {
            type uint16 {
              range "3..1000";
            }
          }
        }
      }
    }
    container ipv6 {
      description
        "IPv6 interface configuration";
      uses isis-metric-grouping;
      leaf tag {
        description
          "Assign an admin tag to an ISIS interface IPv6 route";
        type uint32 {
          range "1..4294967295";
        }
      }
    }
    leaf lsp-interval {
      description
        "Set LSP transmission interval";
      type uint32 {
        range "1..4294967295";
      }
    }
    leaf mesh-group {
      description
        "Set ISIS mesh group";
      type union {
        type uint32 {
          range "1..4294967295";
        }
        type enumeration {
          enum "blocked";
        }
      }
    }
    uses isis-metric-grouping;
    leaf network {
      description
        "Network type";
      type enumeration {
        enum "point-to-point";
      }
    }
    container password {
      description
        "Configure the authentication password for interface";
      choice password-choice {
        case password-level-case {
          list password-list {
            key "levels";
            leaf levels {
              type enumeration {
                enum "level-1";
                enum "level-2";
              }
            }
            leaf password {
              type string;
            }
          }
        }
        case password-only-case {
          leaf password {
            type string;
          }
        }
      }
    }
    container priority {
      description
        "Set priority for Designated Router election";
      choice priority-choice {
        case priority-level-case {
          list priority-list {
            key "levels";
            leaf levels {
              type enumeration {
                enum "level-1";
                enum "level-2";
              }
            }
            leaf value {
              type uint8 {
                range "0..127";
              }
            }
          }
        }
        case priority-only-case {
          leaf value {
            type uint8 {
              range "0..127";
            }
          }
        }
      }
    }
    leaf protocol {
      description
        "Set ISIS protocol's state under current interface";
      type enumeration {
        enum "shutdown";
      }
    }
    leaf retransmit-interval {
      description
        "Set per-LSP retransmission interval";
      type uint16;
    }
    leaf retransmit-throttle-interval {
      description
        "Set interface LSP retransmission interval";
      type uint16;
    }
    leaf tag {
      description
        "Assign an admin tag to an ISIS interface IP route";
      type uint32 {
        range "1..4294967295";
      }
    }
    container three-way-handshake {
      description
        "Select Cisco or IETF three-way handshake";
      presence "true";
      leaf implementor {
        type enumeration {
          enum "cisco";
          enum "ietf";
        }
      }
    }
  }

  grouping narrow-wide-transition-grouping {
    leaf narrow-wide {
      type isis-level-type;
    }
    leaf transition {
      description
        "Accept both styles of TLVs during transition";
      type isis-level-type;
    }
  }

  grouping spf-intervals-grouping {
    leaf interval {
      type uint32 {
        range "1 .. 120";
      }
    }
    leaf initial-wait {
      type uint32 {
        range "1 .. 120000";
      }
    }
    leaf minimum-wait {
      type uint32 {
        range "1 .. 120000";
      }
    }
  }

  grouping authenticate-snp-grouping {
    leaf authenticate {
      description
        "Authentication";
      type empty;
    }
    leaf snp {
      description
        "SNP PDUs";
      type enumeration {
        enum "send-only";
        enum "validate";
      }
    }
  }

  grouping lsp-gen-interval-grouping {
    leaf interval {
      type uint32 {
        range "1 .. 120";
      }
    }
    leaf initial-wait {
      type uint32 {
        range "1 .. 120000";
      }
    }
    leaf wait {
      type uint32 {
        range "1 .. 120000";
      }
    }
  }

  grouping set-overload-bit-suppress-grouping {
    leaf external {
      description
        "If overload-bit set, don't advertise IP prefixes learned from other protocols";
      type empty;
    }
    leaf interlevel {
      description
        "If overload-bit set, don't advertise IP prefixes learned from another ISIS level";
      type empty;
    }
  }

  grouping summary-address-metric-tag-grouping {
    leaf metric {
      description
        "Set metric for summay route";
      type uint32 {
        range "1 .. 4294967295";
      }
    }
    leaf tag {
      description
        "Set tag";
      type uint32 {
        range "1 .. 4294967295";
      }
    }
  }

  grouping authentication-level-grouping {
    leaf levels {
      type authentication-level-type;
    }
  }

  grouping isis-authentication-grouping {
    container mode {
      description
        "Authentication mode";
      container md5 {
        description
          "Keyed message digest";
        presence "Keyed message digest";
        uses authentication-level-grouping;
      }
      container text {
        description
          "Clear text password";
        presence "Clear text password";
        uses authentication-level-grouping;
      }
    }
    container key-chain {
      description
        "Authentication key-chain";
      choice key-chain-choice {
        case key-chain-level-case {
          list key-chain-list {
            key "levels";
            uses authentication-level-grouping;
            leaf name {
              type string;
            }
          }
        }
        case key-chain-only-case {
          leaf name {
            type string;
          }
        }
      }
    }
    container send-only {
      description
        "Authentication send only, receive ignore";
      presence "Authentication send only, receive ignore";
      uses authentication-level-grouping;
    }
  }

  grouping isis-metric-grouping {
    container metric {
      description
        "Configure the metric for interface";
      choice metric-choice {
        case metric-level-case {
          list metric-list {
            key "levels";
            leaf levels {
              type enumeration {
                enum "level-1";
                enum "level-2";
              }
            }
            leaf value {
              type union {
                type uint32 {
                  range "1..16777214";
                }
                type enumeration {
                  enum "maximum";
                }
              }
            }
          }
        }
        case metric-only-case {
          leaf value {
            type union {
              type uint32 {
                range "1..16777214";
              }
              type enumeration {
                enum "maximum";
              }
            }
          }
        }
      }
    }
  }

  grouping redist-level-grouping {
    leaf levels {
      type isis-routes-level-type;
    }
  }

  grouping isis-redist-grouping {
    leaf levels {
      type isis-routes-level-type;
    }
    leaf metric {
      description
        "ISIS default metric";
      type uint32 {
        range "0 .. 4294967295";
      }
    }
    leaf metric-type {
      description
        "OSPF/IS-IS exterior metric type for redistributed routes";
      type enumeration {
        enum "external";
        enum "internal";
        enum "rib-metric-as-external";
        enum "rib-metric-as-internal";
      }
    }
    leaf route-map {
      description
        "Route map reference";
      type string;
    }
  }

  grouping isis-redist-af-grouping {
    leaf include-connected {
      description
        "Include connected";
      type empty;
    }
    uses isis-redist-grouping;
  }

  grouping isis-redist-ospf-match-grouping {
    uses redist-level-grouping;
    leaf metric {
      description
        "ISIS default metric";
      type uint32 {
        range "0 .. 4294967295";
      }
    }
    leaf route-map {
      description
        "Route map reference";
      type string;
    }
  }

  grouping isis-redist-clns-ip-grouping {
    container clns {
      description
        "Redistribution of BGP NSAP routes";
      presence "Redistribution of BGP NSAP routes";
      uses isis-redist-grouping;
    }
    container ip {
      description
        "Redistribution of BGP IP routes";
      presence "true";
      uses isis-redist-grouping;
    }
  }

  grouping isis-ipv4-ipv6-common-grouping {
    leaf adjacency-check {
      description
        "Check ISIS neighbor protocol support";
      type empty;
    }
    container bfd {
      description
        "BFD configuration commands";
      leaf all-interfaces {
        description
          "Enable BFD on all interfaces";
        type empty;
      }
      leaf check-ctrl-plane-failure {
        description
          "BFD check control plane failure";
        type empty;
      }
    }
    leaf router-id {
      description
        "Interface of stable IP address for system";
      type string;
    }
  }

  grouping isis-common-grouping {
    container advertise {
      description
        "Control which IP routes flow in L1 and L2 LSPs";
      leaf passive-only {
        description
          "only interface address of passive interfaces";
        type empty;
      }
    }
    container default-information {
      description
        "Control distribution of default information";
      container originate {
        presence "Distribute a default route";
        description
          "Distribute a default route";
        leaf route-map {
          description
            "Route-map reference";
          type string;
        }
      }
    }
    leaf help {
      description
        "Description of the interactive help system";
      type empty;
    }
    leaf maximum-paths {
      description
        "Forward packets over multiple paths";
      type uint32 {
        range "1 .. 32";
      }
    }
    container metric {
      description
        "Set ISIS metric for all interfaces";
      choice metric-choice {
        case metric-level-case {
          list metrics {
            key "level";
            leaf level {
              type enumeration {
                enum "level-1";
                enum "level-2";
              }
            }
            leaf metric {
              type uint32 {
                range "1..16777214";
              }
            }
          }
        }
        case metric-only-case {
          leaf metric {
            type uint32 {
              range "1..16777214";
            }
          }
        }
      }
    }
    container prc-interval {
      description
        "Minimum interval between partial route calculations";
      leaf interval {
        type uint32 {
          range "1 .. 120";
        }
      }
      leaf initial-wait {
        type uint32 {
          range "1 .. 120000";
        }
      }
      leaf minimum-wait {
        type uint32 {
          range "1 .. 120000";
        }
      }
    }
    container set-overload-bit {
      description
        "Signal other routers not to use us in SPF";
      presence "Signal other routers not to use us in SPF";
      choice set-overload-bit-choice {
        container on-startup {
          description
            "Set overload-bit only temporarily after reboot";
          choice on-startup-choice {
            container time {
              leaf time {
                type uint32 {
                  range "5 .. 86400";
                }
              }
              leaf suppress {
                description
                  "If overload-bit set, suppress the following types of IP prefixes";
                type empty;
              }
              leaf external {
                description
                  "If overload-bit set, don't advertise IP prefixes learned from other protocols";
                type empty;
              }
              leaf interlevel {
                description
                  "If overload-bit set, don't advertise IP prefixes learned from another ISIS level";
                type empty;
              }
            }
            container wait-for-bgp {
              description
                "Let BGP decide when to unset the overload bit";
              presence "Let BGP decide when to unset the overload bitW";
              container suppress {
                description
                  "If overload-bit set, suppress the following types of IP prefixes";
                uses set-overload-bit-suppress-grouping;
              }
            }
          }
        }
        container suppress {
          description
            "If overload-bit set, suppress the following types of IP prefixes";
          uses set-overload-bit-suppress-grouping;
        }
      }
    }
    container spf-interval {
      description
        "Minimum interval between SPF calculations";
      choice spf-interval-choice {
        list level-1-2 {
          key "level";
          leaf level {
            type enumeration {
              enum "level-1";
              enum "level-2";
            }
          }
          uses spf-intervals-grouping;
        }
        container intervals {
          uses spf-intervals-grouping;
        }
      }
    }
  }

  grouping isis-address-family-grouping {
    uses isis-common-grouping;
    uses isis-ipv4-ipv6-common-grouping;
    leaf distance {
      description
        "Administrative distance";
      type uint32 {
        range "1 .. 254";
      }
    }
    container distribute-list {
      description
        "Filter networks in routing updates";
      list prefix-list {
        description
          "Filter connections based on an IPv6 prefix-list";
        key "name";
        leaf name {
          type string;
        }
        container in {
          description
            "Filter incoming routing updates";
          presence "true";
          container interface {
            description
              "Specify interface";
            uses ios-ifc:interface-grouping;
          }
        }
      }
    }
    container ipv6 {
      description
        "IPv6 specific commands";
      container route {
        description
          "ISIS IPV6 routes";
        container priority {
          description
            "Assign priority to IPV6 prefixes";
          container high {
            description
              "Assign high priority to important IPV6 prefixes in ISIS IPV6 local RIB";
            leaf tag {
              description
                "Assign high priority to IPV6 prefixes with a specific route tag";
              type uint32;
            }
          }
        }
      }
    }
    container multi-topology {
      description
        "Enable multi-topology mode";
      presence "Enable multi-topology mode";
      leaf transition {
        description
          "Accept and generate both IS-IS IPv6 and Multi-topology IPv6 TLVs";
        type empty;
      }
    }
    container redistribute {
      description
        "Redistribute IPv6 prefixes from another routing protocol";
      container application {
        description
          "Application Protocol";
        presence "Application Protocol";
        uses isis-redist-af-grouping;
      }
      container bgp {
        description
          "Border Gateway Protocol (BGP)";
        leaf as-number {
          type ios-types:bgp-as-number-type;
        }
        uses isis-redist-af-grouping;
      }
      container connected {
        description
          "Connected";
        presence "Connected";
        uses isis-redist-grouping;
      }
      list eigrp {
        description
          "Enhanced Interior Gateway Routing Protocol (EIGRP)";
        key "as-number";
        leaf as-number {
          type uint32 {
            range "1 .. 65535";
          }
        }
        uses isis-redist-af-grouping;
      }
      container isis {
        description
          "ISO IS-IS";
        presence "true";
        list isis-redistribute {
          key "area-tag";
          leaf area-tag {
            type string;
          }
          uses isis-redist-af-grouping;
        }
        list isis-leak {
          key "isis-redist-levels1 isis-redist-levels2";
          leaf isis-redist-levels1 {
            type enumeration {
              enum "level-1";
              enum "level-2";
            }
          }
          leaf isis-redist-levels2 {
            type enumeration {
              enum "level-1";
              enum "level-2";
            }
          }
          leaf into {
            description
              "from level-n into level-m";
            type empty;
          }
          choice isis-redist-isis-ip-choice {
            leaf distribute-list {
              description
                "select routes";
              type string;
            }
            leaf route-map {
              description
                "Route map for route matching";
              type string;
            }
          }
        }
      }
      container lisp {
        description
          "Locator ID Separation Protocol (LISP)";
        presence "Locator ID Separation Protocol (LISP)";
        uses isis-redist-af-grouping;
      }
      container nd {
        description
          "Neighbor Discovery";
        presence "Neighbor Discovery";
        uses isis-redist-af-grouping;
      }
      container nemo {
        description
          "Network Mobility (NEMO)";
        uses isis-redist-af-grouping;
      }
      list ospf {
        description
          "Open Shortest Path First (OSPF)";
        key "process-id";
        leaf process-id {
          type uint32 {
            range "1 .. 65535";
          }
        }
        uses isis-redist-af-grouping;
        container match {
          description
            "Redistribution of OSPF routes";
          container internal {
            presence "Redistribute OSPF internal routes";
            description
              "Redistribute OSPF internal routes";
            uses isis-redist-grouping;
          }
          container external {
            description
              "Redistribute OSPF external routes";
            presence "Redistribute OSPF external routes";
            leaf external-routes {
              type ios-types:redist-ospf-external-type;
            }
            uses isis-redist-grouping;
          }
          container nssa-external {
            description
              "Redistribute OSPF NSSA external routes";
            presence "Redistribute OSPF NSSA external routes";
            leaf nssa-external-routes {
              type ios-types:redist-ospf-external-type;
            }
            uses isis-redist-grouping;
          }
        }
      }
      list rip {
        description
          "IPv6 Routing Information Protocol (RIPv6)";
        key "process";
        leaf process {
          type string;
        }
        uses isis-redist-af-grouping;
      }
      container static {
        description
          "Static routes";
        presence "Static routes";
        uses isis-redist-grouping;
      }
    }
    list summary-prefix {
      description
        "Configure IPv6 summary prefix";
      key "prefix";
      leaf prefix {
        type ios-types:ipv6-prefix;
      }
      leaf levels {
        type enumeration {
          enum "level-1";
          enum "level-1-2";
          enum "level-2";
        }
      }
    }
    container table-map {
      description
        "Map external entry attributes into routing table";
      leaf name {
        type string;
      }
      leaf filter {
        description
          "Selective route download";
        type empty;
      }
    }
  }

  grouping isis-redist-vrf-grouping {
    container application {
      description
        "Application";
      list appname {
        key "appname";
        leaf appname {
          description
            "Application name";
          type string;
        }
        uses isis-redist-grouping;
      }
    }
    container bgp {
      description
        "Border Gateway Protocol (BGP)";
      list bp-as-num {
        key "bp-as-num";
        leaf bp-as-num {
          description
            "Autonomous system number";
          type ios-types:bgp-as-number-type;
        }
        uses isis-redist-clns-ip-grouping;
        uses isis-redist-grouping;
      }
      leaf a_LESSER_1_PERIOD_0-XX_PERIOD_YY_GREATER_ {
        description
          "Autonomous system number";
        type empty;
      }
    }
    container connected {
      description
        "Connected";
      presence "true";
      uses isis-redist-grouping;
    }
    container eigrp {
      description
        "Enhanced Interior Gateway Routing Protocol (EIGRP)";
      list eigrp-as {
        key "eigrp-as";
        leaf eigrp-as {
          description
            "AS number";
          type uint16 {
            range "1..65535";
          }
        }
        uses isis-redist-grouping;
      }
    }
    container isis {
      description
        "ISO IS-IS";
      list isis-atag {
        key "isis-atag";
        leaf isis-atag {
          description
            "ISO routing area tag";
          type string;
        }
        container ip {
          description
            "Redistribution of IP routes between levels or processes";
          uses isis-redist-grouping;
        }
      }
      container ip {
        description
          "Redistribution of IP routes between levels or processes";
        presence "true";
        uses isis-redist-grouping;
      }
    }
    container iso-igrp {
      description
        "IGRP for OSI networks";
      presence "true";
      list iso-atag {
        key "iso-atag";
        leaf iso-atag {
          description
            "ISO routing area tag";
          type string;
        }
        leaf route-map {
          description
            "Route map reference";
          type empty;
        }
      }
      container route-map {
        description
          "Route map reference";
        presence "true";
        leaf rm-point {
          description
            "Pointer to route-map entries";
          type string;
        }
      }
    }
    container lisp {
      description
        "Locator ID Separation Protocol (LISP)";
      presence "true";
      uses isis-redist-grouping;
    }
    container mobile {
      description
        "Mobile routes";
      presence "true";
      uses isis-redist-grouping;
    }
    leaf ospf {
      description
        "Process ID";
      type uint16 {
        range "1..65535";
      }
    }
    container ospfv3 {
      description
        "OSPFv3";
      list os3-id {
        key "os3-id";
        leaf os3-id {
          description
            "Process ID";
          type uint16 {
            range "1..65535";
          }
        }
        uses isis-redist-grouping;
      }
    }
    container rip {
      description
        "Routing Information Protocol (RIP)";
      presence "true";
      uses isis-redist-grouping;
    }
    container static {
      description
        "Static routes";
      presence "true";
      uses isis-redist-clns-ip-grouping;
      uses isis-redist-grouping;
    }
  }

  grouping tie-break-prefer-repair-grouping {
    leaf downstream {
      description
        "priority number";
      type uint8 {
        range "1..255";
      }
    }
    leaf linecard-disjoint {
      description
        "priority number";
      type uint8 {
        range "1..255";
      }
    }
    leaf lowest-backup-path-metric {
      description
        "priority number";
      type uint8 {
        range "1..255";
      }
    }
    leaf node-protecting {
      description
        "priority number";
      type uint8 {
        range "1..255";
      }
    }
    leaf primary-path {
      description
        "priority number";
      type uint8 {
        range "1..255";
      }
    }
    leaf secondary-path {
      description
        "priority number";
      type uint8 {
        range "1..255";
      }
    }
    leaf srlg-disjoint {
      description
        "priority number";
      type uint8 {
        range "1..255";
      }
    }
  }

  grouping isis-topology-grouping {
    list distance {
      description
        "Define an administrative distance";
      key "number";
      leaf number {
        type uint8 {
          range "1 .. 255";
        }
      }
      list ip-list {
        key "ip";
        leaf ip {
          description
            "IP Source address";
          type inet:ipv4-address;
        }
        list wildcard-bits {
          key "w-bits";
          leaf w-bits {
            type inet:ipv4-address;
          }
          leaf access-list {
            type ios-types:default-access-list-standard-id-type;
          }
        }
      }
      leaf clns {
        description
          "Distance applied for CLNS derived routes";
        type empty;
      }
      leaf ip {
        description
          "Distance applied for IP derived routes";
        type empty;
      }
    }
    container ip {
      description
        "IP specific commands";
      container route {
        description
          "ISIS IP routes";
        container priority {
          description
            "Assign priority to IP prefixes";
          container high {
            description
              "Assign high priority to important IP prefixes in ISIS IP local RIB";
            leaf tag {
              description
                "Assign high priority to IP prefixes with a specific route tag";
              type uint32 {
                range "1 .. 4294967295";
              }
            }
          }
        }
      }
    }
    leaf priority {
      description
        "priority value";
      type uint8 {
        range "0..127";
      }
    }
    container redistribute {
      description
        "Redistribute information from another routing protocol";
      list application {
        description
          "Application";
        key "name";
        leaf name {
          description
            "Application name";
          type string;
        }
        uses isis-redist-grouping;
      }
      container bgp {
        description
          "Border Gateway Protocol (BGP)";
        leaf as-number {
          type ios-types:bgp-as-number-type;
        }
        uses isis-redist-grouping;
        uses isis-redist-clns-ip-grouping;
      }
      container connected {
        description
          "Connected";
        presence "Connected";
        uses isis-redist-grouping;
      }
      list eigrp {
        description
          "Enhanced Interior Gateway Routing Protocol (EIGRP)";
        key "as-number";
        leaf as-number {
          type uint32 {
            range "1 .. 65535";
          }
        }
        uses isis-redist-grouping;
      }
      container isis {
        description
          "ISO IS-IS";
        list isis-redistribute {
          key "area-tag";
          leaf area-tag {
            type string;
          }
          container ip {
            description
              "Redistribution of IP routes between levels or processes";
            presence "true";
            uses isis-redist-grouping;
          }
        }
        list ip {
          description
            "Redistribution of IP routes between levels";
          key "isis-redist-levels1 isis-redist-levels2";
          leaf isis-redist-levels1 {
            type enumeration {
              enum "level-1";
              enum "level-2";
            }
          }
          leaf isis-redist-levels2 {
            type enumeration {
              enum "level-1";
              enum "level-2";
            }
          }
          leaf into {
            description
              "from level-n into level-m";
            type empty;
          }
          choice isis-redist-isis-ip-choice {
            leaf distribute-list {
              description
                "select routes";
              type uint32 {
                range "100 .. 199";
              }
            }
            leaf route-map {
              description
                "Route map for route matching";
              type string;
            }
          }
        }
      }
      container iso-igrp {
        description
          "IGRP for OSI networks";
        presence "IGRP for OSI networks";
        choice iso-igrp-choice {
          container area-tag-route-map-container {
            leaf area-tag {
              type string;
            }
            leaf route-map {
              description
                "Route map reference";
              type string;
            }
          }
          leaf route-map {
            description
              "Route map reference";
            type string;
          }
        }
        uses redist-level-grouping;
        leaf metric {
          description
            "ISIS default metric";
          type uint32 {
            range "0 .. 4294967295";
          }
        }
        leaf metric-type {
          description
            "OSPF/IS-IS exterior metric type for redistributed routes";
          type enumeration {
            enum "external";
            enum "internal";
            enum "rib-metric-as-external";
            enum "rib-metric-as-internal";
          }
        }
      }
      container lisp {
        description
          "Locator ID Separation Protocol (LISP)";
        presence "true";
        uses isis-redist-af-grouping;
      }
      container maximum-prefix {
        description
          "Maximum number of prefixes redistributed to protocol";
        leaf number {
          type uint32 {
            range "1 .. 4294967295";
          }
        }
        leaf threshold-value {
          type uint32 {
            range "1 .. 100";
          }
        }
        leaf warning-only {
          description
            "Only give warning message when limit is exceeded";
          type empty;
        }
        leaf withdraw {
          description
            "Withdraw redistibuted prefixes";
          type empty;
        }
      }
      container mobile {
        description
          "Mobile routes";
        presence "Mobile routes";
        uses isis-redist-grouping;
      }
      container odr {
        description
          "On Demand stub Routes";
        presence "On Demand stub Routes";
        uses isis-redist-grouping;
      }
      list ospf {
        description
          "Open Shortest Path First (OSPF)";
        key "process-id";
        leaf process-id {
          type uint32 {
            range "1 .. 65535";
          }
        }
        uses isis-redist-grouping;
        container match {
          description
            "Redistribution of OSPF routes";
          container internal {
            presence "Redistribute OSPF internal routes";
            description
              "Redistribute OSPF internal routes";
            uses isis-redist-grouping;
          }
          container external {
            description
              "Redistribute OSPF external routes";
            presence "Redistribute OSPF external routes";
            leaf external-routes {
              type ios-types:redist-ospf-external-type;
            }
            uses isis-redist-grouping;
          }
          container nssa-external {
            description
              "Redistribute OSPF NSSA external routes";
            presence "Redistribute OSPF NSSA external routes";
            leaf nssa-external-routes {
              type ios-types:redist-ospf-external-type;
            }
            uses isis-redist-grouping;
          }
        }
        leaf vrf {
          description
            "VPN Routing/Forwarding Instance";
          type string;
        }
      }
      list ospfv3 {
        description
          "Open Shortest Path First (OSPF)";
        key "process-id";
        leaf process-id {
          type uint32 {
            range "1 .. 65535";
          }
        }
        uses isis-redist-grouping;
        container match {
          description
            "Redistribution of OSPF routes";
          container internal {
            presence "Redistribute OSPF internal routes";
            description
              "Redistribute OSPF internal routes";
            uses isis-redist-grouping;
          }
          container external {
            description
              "Redistribute OSPF external routes";
            presence "Redistribute OSPF external routes";
            leaf external-routes {
              type ios-types:redist-ospf-external-type;
            }
            uses isis-redist-grouping;
          }
          container nssa-external {
            description
              "Redistribute OSPF NSSA external routes";
            presence "Redistribute OSPF NSSA external routes";
            leaf nssa-external-routes {
              type ios-types:redist-ospf-external-type;
            }
            uses isis-redist-grouping;
          }
        }
        leaf vrf {
          description
            "VPN Routing/Forwarding Instance";
          type string;
        }
      }
      container rip {
        description
          "Routing Information Protocol (RIP)";
        presence "Routing Information Protocol (RIP)";
        uses isis-redist-grouping;
      }
      container static {
        description
          "Static routes";
        presence "Static routes";
        uses isis-redist-clns-ip-grouping;
      }
      container vrf {
        description
          "Specify a source VRF";
        list vrf-nm {
          key "vrf-nm";
          leaf vrf-nm {
            description
              "Source VRF name";
            type string;
          }
          uses isis-redist-vrf-grouping;
        }
        container global {
          description
            "global VRF";
          uses isis-redist-vrf-grouping;
        }
      }
    }
    container set-attached-bit {
      description
        "Conditionally advertise us as attached to L2";
      leaf route-map {
        description
          "Route-map reference";
        type string;
      }
    }
    uses ios-snmp:router-snmp-grouping;
    list summary-address {
      description
        "Configure IP address summaries";
      key "ip mask";
      leaf ip {
        type inet:ipv4-address;
      }
      leaf mask {
        type inet:ipv4-address;
      }
      container level-1 {
        description
          "Summarize into level-1 area";
        presence "Summarize into level-1 area";
        uses summary-address-metric-tag-grouping;
      }
      container level-1-2 {
        description
          "Summarize into both area and sub-domain";
        presence "Summarize into both area and sub-domain";
        uses summary-address-metric-tag-grouping;
      }
      container level-2 {
        description
          "Summarize into level-2 sub-domain";
        presence "Summarize into level-2 sub-domain";
        uses summary-address-metric-tag-grouping;
      }
      container metric-tag-container {
        uses summary-address-metric-tag-grouping;
      }
    }
    container traffic-share {
      description
        "How to compute traffic share over alternate paths";
      container min {
        description
          "All traffic shared among min metric paths";
        leaf across-interfaces {
          description
            "Use different interfaces for equal-cost paths";
          type empty;
        }
      }
    }
    uses isis-common-grouping;
  }

  grouping isis-af-ipv4-grouping {
    leaf help {
      description
        "Description of the interactive help system";
      type empty;
    }
    uses ios-snmp:router-snmp-grouping;
    list topology {
      description
        "Associate the routing protocol to a topology instance";
      key "name";
      leaf name {
        type string;
      }
      leaf tid {
        description
          "Configuring the routing protocol topology tid";
        type uint32 {
          range "5..4095";
        }
      }
      leaf ignore-attached-bit {
        description
          "Never install default route to closest L2 router";
        type empty;
      }
      uses isis-topology-grouping;
    }
  }

  grouping config-isis-main-grouping {
    container metric-style {
      description
        "Use old-style (ISO 10589) or new-style packet formats";
      choice metric-style-choice {
        container narrow {
          description
            "Use old style of TLVs with narrow metric";
          presence "true";
          uses narrow-wide-transition-grouping;
        }
        container transition {
          description
            "Send and accept both styles of TLVs during transition";
          presence "true";
          leaf transition {
            type isis-level-type;
          }
        }
        container wide {
          description
            "Use new style of TLVs to carry wider metric";
          presence "true";
          uses narrow-wide-transition-grouping;
        }
      }
    }
    container address-family {
      description
        "Enter Address Family command mode";
      container ipv4 {
        description
          "Address family";
        leaf unicast-multicast {
          type enumeration {
            enum "unicast";
            enum "multicast";
          }
        }
        uses isis-af-ipv4-grouping;
      }
      container ipv6 {
        description
          "Address family";
        leaf unicast {
          type empty;
        }
        uses isis-address-family-grouping;
      }
    }
    uses isis-topology-grouping;
    container area-password {
      description
        "Configure the authentication password for an area";
      leaf name {
        type string;
      }
      uses authenticate-snp-grouping;
    }
    container authentication {
      description
        "ISIS authentication for LSPs";
      uses isis-authentication-grouping;
    }
    container distribute-list {
      description
        "Filter networks in routing updates";
      choice distribute-list-choice {
        case acl-case {
          leaf acl-name {
            type ios-types:access-list-standard-id-type;
          }
          leaf in {
            description
              "Filter incoming routing updates";
            type string;
          }
        }
        case gateway-prefix-case {
          leaf gateway {
            description
              "Filtering incoming updates based on gateway";
            type string;
          }
          leaf prefix {
            description
              "Filter prefixes in routing updates";
            type string;
          }
          leaf gateway-prefix-in {
            description
              "Filter incoming routing updates";
            type string;
          }
        }
        case route-map-case {
          leaf route-map {
            description
              "Filter prefixes based on the route-map";
            type string;
          }
          leaf route-map-in {
            description
              "Filter incoming routing updates";
            type empty;
          }
        }
      }
    }
    container domain-password {
      description
        "Set the authentication password for a routing domain";
      leaf name {
        type string;
      }
      uses authenticate-snp-grouping;
    }
    container fast-flood {
      description
        "Flood LSPs (that triggered SPF) before running SPF";
      presence "Flood LSPs (that triggered SPF) before running SPF";
      leaf number {
        type uint32 {
          range "1 .. 15";
        }
      }
    }
    container fast-reroute {
      description
        "Configure Fast-Reroute";
      container load-sharing {
        description
          "Distributes repair paths equally among links and prefixes";
        container level-1 {
          description
            "Apply to level-1";
          presence "true";
          leaf disable {
            description
              "Disable load-sharing";
            type empty;
          }
        }
        container level-2 {
          description
            "Apply to level-2";
          presence "true";
          leaf disable {
            description
              "Disable load-sharing";
            type empty;
          }
        }
      }
      container per-prefix {
        description
          "Enable Fast-Reroute Per-Prefix";
        container level-1 {
          description
            "Apply to level-1";
          leaf all {
            description
              "Enable Fast-Reroute for primary paths";
            type empty;
          }
          leaf route-map {
            description
              "route-map name";
            type string;
          }
        }
        container level-2 {
          description
            "Apply to level-2";
          leaf all {
            description
              "Enable Fast-Reroute for primary paths";
            type empty;
          }
          leaf route-map {
            description
              "route-map name";
            type string;
          }
        }
      }
      container remote-lfa {
        description
          "Configuring fast-reroute remote-lfa";
        container level-1 {
          description
            "Apply to level-1";
          container mpls-ldp {
            description
              "Use mpls-ldp tunnel type";
            presence "true";
            container maximum-metric {
              description
                "maximum metric to reach release node";
              presence "true";
              leaf max-met {
                description
                  "metric value";
                type uint32 {
                  range "1..4294967295";
                }
              }
            }
          }
        }
        container level-2 {
          description
            "Apply to level-2";
          container mpls-ldp {
            description
              "Use mpls-ldp tunnel type";
            presence "true";
            container maximum-metric {
              description
                "maximum metric to reach release node";
              presence "true";
              leaf max-met {
                description
                  "metric value";
                type uint32 {
                  range "1..4294967295";
                }
              }
            }
          }
        }
      }
      container tie-break {
        description
          "Set repair path preference";
        container level-1 {
          description
            "Apply to level-1";
          uses tie-break-prefer-repair-grouping;
        }
        container level-2 {
          description
            "Apply to level-2";
          uses tie-break-prefer-repair-grouping;
        }
      }
    }
    container ti-lfa {
      container level-1 {
        description
          "Apply to level-1";
        container maximum-metric {
          description
            "maximum metric to reach release node";
          leaf max-met {
            description
              "metric value";
            type uint32 {
              range "1..4294967295";
            }
          }
        }
      }
      container level-2 {
        description
          "Apply to level-2";
        presence "true";
        container maximum-metric {
          description
            "maximum metric to reach release node";
          leaf max-met {
            description
              "metric value";
            type uint32 {
              range "1..4294967295";
            }
          }
        }
      }
    }
    container hello {
      description
        "Pad ISIS hello PDUs to full MTU";
      container padding {
        description
          "Pad hello PDU";
        presence "Pad hello PDU";
        leaf pad-type {
          type enumeration {
            enum "multi-point";
            enum "point-to-point";
          }
        }
      }
    }
    container hostname {
      description
        "Dynamic hostname for IS-IS";
      leaf dynamic {
        description
          "Dynamic hostname";
        type empty;
      }
    }
    leaf ignore-lsp-errors {
      description
        "Ignore LSPs with bad checksums";
      type empty;
    }
    leaf is-type {
      description
        "IS Level for this routing process (OSI only)";
      type enumeration {
        enum "level-1";
        enum "level-1-2";
        enum "level-2-only";
      }
    }
    container ispf {
      description
        "Configure execution of incremental SPF";
      leaf level {
        type enumeration {
          enum "level-1";
          enum "level-1-2";
          enum "level-2";
        }
      }
      leaf number {
        type uint32 {
          range "1 .. 600";
        }
      }
    }
    container log-adjacency-changes {
      description
        "Log changes in adjacency state";
      presence "Log changes in adjacency state";
      leaf all {
        description
          "Include changes generated by non-IIH event";
        type empty;
      }
    }
    container lsp-full {
      description
        "If we run out of LSP fragments";
      container suppress {
        description
          "suppress the following types of IP prefixes";
        choice lsp-full-choince {
          container external-interlevel-container {
            leaf external {
              description
                "don't advertise IP prefixes learned from other protocols";
              type empty;
            }
            leaf interlevel {
              description
                "don't advertise IP prefixes learned from another ISIS level";
              type empty;
            }
          }
          leaf none {
            description
              "don't suppress any prefixes";
            type empty;
          }
        }
      }
    }
    container lsp-gen-interval {
      description
        "Minimum interval between regenerating same LSP";
      choice lsp-gen-interval-choice {
        container intervals {
          uses lsp-gen-interval-grouping;
        }
        container intervals-levels {
          container intervals-level-1 {
            leaf level-1 {
              description
                "Set interval for level 1 only";
              type empty;
            }
            uses lsp-gen-interval-grouping;
          }
          container intervals-level-2 {
            leaf level-2 {
              description
                "Set interval for level 2 only";
              type empty;
            }
            uses lsp-gen-interval-grouping;
          }
        }
      }
    }
    leaf lsp-mtu {
      description
        "Set maximum LSP size";
      type uint32 {
        range "128 .. 4352";
      }
    }
    leaf lsp-refresh-interval {
      description
        "Set LSP refresh interval";
      type uint32 {
        range "1 .. 65535";
      }
    }
    leaf max-area-addresses {
      description
        "Allow configuration of more manual area addresses";
      type uint32 {
        range "3 .. 254";
      }
    }
    leaf max-lsp-lifetime {
      description
        "Set maximum LSP lifetime";
      type uint32 {
        range "1 .. 65535";
      }
    }
    container microloop {
      description
        "Enable microloop protection configuration commands";
      container avoidance {
        description
          "Enable local microloop avoidance";
        presence "true";
        leaf disable {
          description
            "Disable Microloop avoidance";
          type empty;
        }
        leaf protected {
          description
            "Microloop avoidance for protected link or prefix only";
          type empty;
        }
        leaf rib-update-delay {
          description
            "Value of the delay in milliseconds";
          type uint32 {
            range "1..600000";
          }
        }
      }
    }
    container mpls {
      description
        "Configure MPLS routing protocol parameters";
      container ldp {
        description
          "routing protocol commands for MPLS LDP";
        container autoconfig {
          description
            "Configure LDP automatic configuration";
          presence "true";
          leaf level-1 {
            description
              "Configure ISIS level-1 to run MPLS LDP";
            type empty;
          }
          leaf level-2 {
            description
              "Configure ISIS level-2 to run MPLS LDP";
            type empty;
          }
        }
        leaf sync {
          description
            "Configure LDP-IGP Synchronization";
          type empty;
        }
        leaf sync-igp-shortcuts {
          description
            "Configure LDP-IGP Synchronization on MPLS shortcuts";
          type empty;
        }
      }
      container traffic-eng {
        description
          "routing protocol commands for MPLS Traffic Engineering";
        leaf level-1 {
          description
            "Run MPLS TE on IS-IS level 1 only";
          type empty;
        }
        leaf level-2 {
          description
            "Run MPLS TE on IS-IS level 2 only";
          type empty;
        }
        leaf multicast-intact {
          description
            "MPLS TE and PIM interaction";
          type empty;
        }
        container router-id {
          description
            "Traffic Engineering stable IP address for system";
          uses ios-ifc:interface-grouping;
        }
        container scanner {
          description
            "Timer parameters for TE database";
          leaf interval {
            description
              "Time (secs) between LSPDB walks for TE";
            type uint32 {
              range "1 .. 60";
            }
          }
          leaf max-flash {
            description
              "Max. number of LSPs ISIS may send to TE db without delay: <0..200>";
            type uint32 {
              range "0 .. 200";
            }
          }
        }
      }
    }
    list net {
      description
        "A Network Entity Title for this process (OSI only)";
      key "tag";
      leaf tag {
        type isis-net;
      }
    }
    container nsf {
      description
        "Non-stop forwarding";
      leaf cisco {
        description
          "Checkpoint method";
        type empty;
      }
      leaf ietf {
        description
          "IETF method";
        type empty;
      }
      container interface {
        description
          "Interface properties";
        leaf wait {
          description
            "Seconds";
          type uint8 {
            range "1..60";
          }
        }
      }
      leaf interval {
        description
          "Minutes";
        type uint16 {
          range "0..1440";
        }
      }
    }
    container partition {
      description
        "CLNS area partition";
      leaf avoidance {
        description
          "Withdraw area prefix if partition detected";
        type empty;
      }
    }
    uses ios-ifc:passive-interface-grouping;
    container protocol {
      description
        "Set protocol's administrative state";
      leaf shutdown {
        description
          "Set protocol's administrative state to disable";
        type empty;
      }
    }
    container segment-routing {
      description
        "Enable Segment Routing Feature";
      leaf mpls {
        description
          "Enable Segment Routing Feature using MPLS encapsulation";
        type empty;
      }
      container prefix-sid-map {
        description
          "Enable prefix-sid-map";
        leaf advertise-local {
          description
            "Advertise active local prefix-SID mappings";
          type empty;
        }
        container receive {
          description
            "Enable prefix-SID mapping client";
          presence "true";
          leaf disable {
            description
              "Disable prefix-SID mapping";
            type empty;
          }
        }
      }
    }
    container skeptical {
      description
        "Be a cautious NSF helper when refresh adjacency";
      leaf interval {
        description
          "Minutes";
        type uint16 {
          range "0..1440";
        }
      }
    }
    leaf update-queue-depth {
      description
        "Set Update process queue depth";
      type uint32 {
        range "1 .. 2147483647";
      }
    }
    container use {
      description
        "Use different algorithms during SPF";
      leaf external-metrics {
        description
          "Honour external metrics during SPF";
        type empty;
      }
    }
    leaf vrf {
      description
        "VRF name for this process";
      type string;
    }
    uses isis-ipv4-ipv6-common-grouping;
  }

  grouping config-isis-container-grouping {
    container isis-container {
      list isis {
        description
          "ISO IS-IS";
        key "area-tag";
        leaf area-tag {
          type string;
        }
        uses config-isis-main-grouping;
      }
    }
  }

  grouping config-isis-grouping {
    container isis {
      description
        "ISO IS-IS";
      presence "true";
      uses config-isis-main-grouping;
    }
  }

  augment "/ncs:devices/ncs:template/ncs:config/ios:native/ios:router" {
    uses ncs_template_config-isis-grouping;
    uses ncs_template_config-isis-container-grouping;
  }
  augment "/ncs:devices/ncs:device/ncs:live-status/ios:native/ios:router" {
    uses live_ncs_config-isis-grouping {
      refine isis {
        tailf:ncs-device-type "netconf";
        tailf:display-when "not(../../../../ncs:module) or ../../../../ncs:module[ncs:name='Cisco-IOS-XE-isis'] or (../../../../ncs:live-status-protocol[not(ncs:capability)]) or (../../../../ncs:live-status-protocol/ncs:capability/ncs:module[.='Cisco-IOS-XE-isis'])";
      }
    }
    uses live_ncs_config-isis-container-grouping {
      refine isis-container {
        tailf:ncs-device-type "netconf";
        tailf:display-when "not(../../../../ncs:module) or ../../../../ncs:module[ncs:name='Cisco-IOS-XE-isis'] or (../../../../ncs:live-status-protocol[not(ncs:capability)]) or (../../../../ncs:live-status-protocol/ncs:capability/ncs:module[.='Cisco-IOS-XE-isis'])";
      }
    }
  }
  augment "/ncs:devices/ncs:device/ncs:config/ios:native/ios:router" {
    uses config-isis-grouping {
      refine isis {
        tailf:ncs-device-type "netconf";
        tailf:display-when "not(../../../../ncs:module) or ../../../../ncs:module[ncs:name='Cisco-IOS-XE-isis']";
      }
    }
    uses config-isis-container-grouping {
      refine isis-container {
        tailf:ncs-device-type "netconf";
        tailf:display-when "not(../../../../ncs:module) or ../../../../ncs:module[ncs:name='Cisco-IOS-XE-isis']";
      }
    }
  }
  augment "/ncs:devices/ncs:template/ncs:config/ios:native/ios:interface/ios:FastEthernet/ios:isis" {
    uses ncs_template_config-interface-isis-grouping;
  }
  augment "/ncs:devices/ncs:device/ncs:live-status/ios:native/ios:interface/ios:FastEthernet/ios:isis" {
    uses live_ncs_config-interface-isis-grouping {
      refine three-way-handshake {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine tag {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-throttle-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine protocol {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine priority {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine password {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine network {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine metric {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine mesh-group {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine lsp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine ipv6 {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-multiplier {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine csnp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine circuit-type {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine authentication {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine advertise {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine adjacency-filter {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
    }
  }
  augment "/ncs:devices/ncs:device/ncs:config/ios:native/ios:interface/ios:FastEthernet/ios:isis" {
    uses config-interface-isis-grouping {
      refine three-way-handshake {
        tailf:ncs-device-type "netconf";
        tailf:display-when "not(../../../../../../ncs:module) or ../../../../../../ncs:module[ncs:name='Cisco-IOS-XE-isis']";
      }
      refine tag {
        tailf:ncs-device-type "netconf";
        tailf:display-when "not(../../../../../../ncs:module) or ../../../../../../ncs:module[ncs:name='Cisco-IOS-XE-isis']";
      }
      refine retransmit-throttle-interval {
        tailf:ncs-device-type "netconf";
        tailf:display-when "not(../../../../../../ncs:module) or ../../../../../../ncs:module[ncs:name='Cisco-IOS-XE-isis']";
      }
      refine retransmit-interval {
        tailf:ncs-device-type "netconf";
        tailf:display-when "not(../../../../../../ncs:module) or ../../../../../../ncs:module[ncs:name='Cisco-IOS-XE-isis']";
      }
      refine protocol {
        tailf:ncs-device-type "netconf";
        tailf:display-when "not(../../../../../../ncs:module) or ../../../../../../ncs:module[ncs:name='Cisco-IOS-XE-isis']";
      }
      refine priority {
        tailf:ncs-device-type "netconf";
        tailf:display-when "not(../../../../../../ncs:module) or ../../../../../../ncs:module[ncs:name='Cisco-IOS-XE-isis']";
      }
      refine password {
        tailf:ncs-device-type "netconf";
        tailf:display-when "not(../../../../../../ncs:module) or ../../../../../../ncs:module[ncs:name='Cisco-IOS-XE-isis']";
      }
      refine network {
        tailf:ncs-device-type "netconf";
        tailf:display-when "not(../../../../../../ncs:module) or ../../../../../../ncs:module[ncs:name='Cisco-IOS-XE-isis']";
      }
      refine metric {
        tailf:ncs-device-type "netconf";
        tailf:display-when "not(../../../../../../ncs:module) or ../../../../../../ncs:module[ncs:name='Cisco-IOS-XE-isis']";
      }
      refine mesh-group {
        tailf:ncs-device-type "netconf";
        tailf:display-when "not(../../../../../../ncs:module) or ../../../../../../ncs:module[ncs:name='Cisco-IOS-XE-isis']";
      }
      refine lsp-interval {
        tailf:ncs-device-type "netconf";
        tailf:display-when "not(../../../../../../ncs:module) or ../../../../../../ncs:module[ncs:name='Cisco-IOS-XE-isis']";
      }
      refine ipv6 {
        tailf:ncs-device-type "netconf";
        tailf:display-when "not(../../../../../../ncs:module) or ../../../../../../ncs:module[ncs:name='Cisco-IOS-XE-isis']";
      }
      refine hello-multiplier {
        tailf:ncs-device-type "netconf";
        tailf:display-when "not(../../../../../../ncs:module) or ../../../../../../ncs:module[ncs:name='Cisco-IOS-XE-isis']";
      }
      refine hello-interval {
        tailf:ncs-device-type "netconf";
        tailf:display-when "not(../../../../../../ncs:module) or ../../../../../../ncs:module[ncs:name='Cisco-IOS-XE-isis']";
      }
      refine hello {
        tailf:ncs-device-type "netconf";
        tailf:display-when "not(../../../../../../ncs:module) or ../../../../../../ncs:module[ncs:name='Cisco-IOS-XE-isis']";
      }
      refine csnp-interval {
        tailf:ncs-device-type "netconf";
        tailf:display-when "not(../../../../../../ncs:module) or ../../../../../../ncs:module[ncs:name='Cisco-IOS-XE-isis']";
      }
      refine circuit-type {
        tailf:ncs-device-type "netconf";
        tailf:display-when "not(../../../../../../ncs:module) or ../../../../../../ncs:module[ncs:name='Cisco-IOS-XE-isis']";
      }
      refine authentication {
        tailf:ncs-device-type "netconf";
        tailf:display-when "not(../../../../../../ncs:module) or ../../../../../../ncs:module[ncs:name='Cisco-IOS-XE-isis']";
      }
      refine advertise {
        tailf:ncs-device-type "netconf";
        tailf:display-when "not(../../../../../../ncs:module) or ../../../../../../ncs:module[ncs:name='Cisco-IOS-XE-isis']";
      }
      refine adjacency-filter {
        tailf:ncs-device-type "netconf";
        tailf:display-when "not(../../../../../../ncs:module) or ../../../../../../ncs:module[ncs:name='Cisco-IOS-XE-isis']";
      }
    }
  }
  augment "/ncs:devices/ncs:template/ncs:config/ios:native/ios:interface/ios:GigabitEthernet/ios:isis" {
    uses ncs_template_config-interface-isis-grouping;
  }
  augment "/ncs:devices/ncs:device/ncs:live-status/ios:native/ios:interface/ios:GigabitEthernet/ios:isis" {
    uses live_ncs_config-interface-isis-grouping {
      refine three-way-handshake {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine tag {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-throttle-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine protocol {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine priority {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine password {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine network {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine metric {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine mesh-group {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine lsp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine ipv6 {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-multiplier {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine csnp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine circuit-type {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine authentication {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine advertise {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine adjacency-filter {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
    }
  }
  augment "/ncs:devices/ncs:device/ncs:config/ios:native/ios:interface/ios:GigabitEthernet/ios:isis" {
    uses config-interface-isis-grouping {
      refine three-way-handshake {
        tailf:ncs-device-type "netconf";
        tailf:display-when "not(../../../../../../ncs:module) or ../../../../../../ncs:module[ncs:name='Cisco-IOS-XE-isis']";
      }
      refine tag {
        tailf:ncs-device-type "netconf";
        tailf:display-when "not(../../../../../../ncs:module) or ../../../../../../ncs:module[ncs:name='Cisco-IOS-XE-isis']";
      }
      refine retransmit-throttle-interval {
        tailf:ncs-device-type "netconf";
        tailf:display-when "not(../../../../../../ncs:module) or ../../../../../../ncs:module[ncs:name='Cisco-IOS-XE-isis']";
      }
      refine retransmit-interval {
        tailf:ncs-device-type "netconf";
        tailf:display-when "not(../../../../../../ncs:module) or ../../../../../../ncs:module[ncs:name='Cisco-IOS-XE-isis']";
      }
      refine protocol {
        tailf:ncs-device-type "netconf";
        tailf:display-when "not(../../../../../../ncs:module) or ../../../../../../ncs:module[ncs:name='Cisco-IOS-XE-isis']";
      }
      refine priority {
        tailf:ncs-device-type "netconf";
        tailf:display-when "not(../../../../../../ncs:module) or ../../../../../../ncs:module[ncs:name='Cisco-IOS-XE-isis']";
      }
      refine password {
        tailf:ncs-device-type "netconf";
        tailf:display-when "not(../../../../../../ncs:module) or ../../../../../../ncs:module[ncs:name='Cisco-IOS-XE-isis']";
      }
      refine network {
        tailf:ncs-device-type "netconf";
        tailf:display-when "not(../../../../../../ncs:module) or ../../../../../../ncs:module[ncs:name='Cisco-IOS-XE-isis']";
      }
      refine metric {
        tailf:ncs-device-type "netconf";
        tailf:display-when "not(../../../../../../ncs:module) or ../../../../../../ncs:module[ncs:name='Cisco-IOS-XE-isis']";
      }
      refine mesh-group {
        tailf:ncs-device-type "netconf";
        tailf:display-when "not(../../../../../../ncs:module) or ../../../../../../ncs:module[ncs:name='Cisco-IOS-XE-isis']";
      }
      refine lsp-interval {
        tailf:ncs-device-type "netconf";
        tailf:display-when "not(../../../../../../ncs:module) or ../../../../../../ncs:module[ncs:name='Cisco-IOS-XE-isis']";
      }
      refine ipv6 {
        tailf:ncs-device-type "netconf";
        tailf:display-when "not(../../../../../../ncs:module) or ../../../../../../ncs:module[ncs:name='Cisco-IOS-XE-isis']";
      }
      refine hello-multiplier {
        tailf:ncs-device-type "netconf";
        tailf:display-when "not(../../../../../../ncs:module) or ../../../../../../ncs:module[ncs:name='Cisco-IOS-XE-isis']";
      }
      refine hello-interval {
        tailf:ncs-device-type "netconf";
        tailf:display-when "not(../../../../../../ncs:module) or ../../../../../../ncs:module[ncs:name='Cisco-IOS-XE-isis']";
      }
      refine hello {
        tailf:ncs-device-type "netconf";
        tailf:display-when "not(../../../../../../ncs:module) or ../../../../../../ncs:module[ncs:name='Cisco-IOS-XE-isis']";
      }
      refine csnp-interval {
        tailf:ncs-device-type "netconf";
        tailf:display-when "not(../../../../../../ncs:module) or ../../../../../../ncs:module[ncs:name='Cisco-IOS-XE-isis']";
      }
      refine circuit-type {
        tailf:ncs-device-type "netconf";
        tailf:display-when "not(../../../../../../ncs:module) or ../../../../../../ncs:module[ncs:name='Cisco-IOS-XE-isis']";
      }
      refine authentication {
        tailf:ncs-device-type "netconf";
        tailf:display-when "not(../../../../../../ncs:module) or ../../../../../../ncs:module[ncs:name='Cisco-IOS-XE-isis']";
      }
      refine advertise {
        tailf:ncs-device-type "netconf";
        tailf:display-when "not(../../../../../../ncs:module) or ../../../../../../ncs:module[ncs:name='Cisco-IOS-XE-isis']";
      }
      refine adjacency-filter {
        tailf:ncs-device-type "netconf";
        tailf:display-when "not(../../../../../../ncs:module) or ../../../../../../ncs:module[ncs:name='Cisco-IOS-XE-isis']";
      }
    }
  }
  augment "/ncs:devices/ncs:template/ncs:config/ios:native/ios:interface/ios:TenGigabitEthernet/ios:isis" {
    uses ncs_template_config-interface-isis-grouping;
  }
  augment "/ncs:devices/ncs:device/ncs:live-status/ios:native/ios:interface/ios:TenGigabitEthernet/ios:isis" {
    uses live_ncs_config-interface-isis-grouping {
      refine three-way-handshake {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine tag {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-throttle-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine protocol {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine priority {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine password {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine network {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine metric {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine mesh-group {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine lsp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine ipv6 {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-multiplier {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine csnp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine circuit-type {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine authentication {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine advertise {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine adjacency-filter {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
    }
  }
  augment "/ncs:devices/ncs:device/ncs:config/ios:native/ios:interface/ios:TenGigabitEthernet/ios:isis" {
    uses config-interface-isis-grouping {
      refine three-way-handshake {
        tailf:ncs-device-type "netconf";
        tailf:display-when "not(../../../../../../ncs:module) or ../../../../../../ncs:module[ncs:name='Cisco-IOS-XE-isis']";
      }
      refine tag {
        tailf:ncs-device-type "netconf";
        tailf:display-when "not(../../../../../../ncs:module) or ../../../../../../ncs:module[ncs:name='Cisco-IOS-XE-isis']";
      }
      refine retransmit-throttle-interval {
        tailf:ncs-device-type "netconf";
        tailf:display-when "not(../../../../../../ncs:module) or ../../../../../../ncs:module[ncs:name='Cisco-IOS-XE-isis']";
      }
      refine retransmit-interval {
        tailf:ncs-device-type "netconf";
        tailf:display-when "not(../../../../../../ncs:module) or ../../../../../../ncs:module[ncs:name='Cisco-IOS-XE-isis']";
      }
      refine protocol {
        tailf:ncs-device-type "netconf";
        tailf:display-when "not(../../../../../../ncs:module) or ../../../../../../ncs:module[ncs:name='Cisco-IOS-XE-isis']";
      }
      refine priority {
        tailf:ncs-device-type "netconf";
        tailf:display-when "not(../../../../../../ncs:module) or ../../../../../../ncs:module[ncs:name='Cisco-IOS-XE-isis']";
      }
      refine password {
        tailf:ncs-device-type "netconf";
        tailf:display-when "not(../../../../../../ncs:module) or ../../../../../../ncs:module[ncs:name='Cisco-IOS-XE-isis']";
      }
      refine network {
        tailf:ncs-device-type "netconf";
        tailf:display-when "not(../../../../../../ncs:module) or ../../../../../../ncs:module[ncs:name='Cisco-IOS-XE-isis']";
      }
      refine metric {
        tailf:ncs-device-type "netconf";
        tailf:display-when "not(../../../../../../ncs:module) or ../../../../../../ncs:module[ncs:name='Cisco-IOS-XE-isis']";
      }
      refine mesh-group {
        tailf:ncs-device-type "netconf";
        tailf:display-when "not(../../../../../../ncs:module) or ../../../../../../ncs:module[ncs:name='Cisco-IOS-XE-isis']";
      }
      refine lsp-interval {
        tailf:ncs-device-type "netconf";
        tailf:display-when "not(../../../../../../ncs:module) or ../../../../../../ncs:module[ncs:name='Cisco-IOS-XE-isis']";
      }
      refine ipv6 {
        tailf:ncs-device-type "netconf";
        tailf:display-when "not(../../../../../../ncs:module) or ../../../../../../ncs:module[ncs:name='Cisco-IOS-XE-isis']";
      }
      refine hello-multiplier {
        tailf:ncs-device-type "netconf";
        tailf:display-when "not(../../../../../../ncs:module) or ../../../../../../ncs:module[ncs:name='Cisco-IOS-XE-isis']";
      }
      refine hello-interval {
        tailf:ncs-device-type "netconf";
        tailf:display-when "not(../../../../../../ncs:module) or ../../../../../../ncs:module[ncs:name='Cisco-IOS-XE-isis']";
      }
      refine hello {
        tailf:ncs-device-type "netconf";
        tailf:display-when "not(../../../../../../ncs:module) or ../../../../../../ncs:module[ncs:name='Cisco-IOS-XE-isis']";
      }
      refine csnp-interval {
        tailf:ncs-device-type "netconf";
        tailf:display-when "not(../../../../../../ncs:module) or ../../../../../../ncs:module[ncs:name='Cisco-IOS-XE-isis']";
      }
      refine circuit-type {
        tailf:ncs-device-type "netconf";
        tailf:display-when "not(../../../../../../ncs:module) or ../../../../../../ncs:module[ncs:name='Cisco-IOS-XE-isis']";
      }
      refine authentication {
        tailf:ncs-device-type "netconf";
        tailf:display-when "not(../../../../../../ncs:module) or ../../../../../../ncs:module[ncs:name='Cisco-IOS-XE-isis']";
      }
      refine advertise {
        tailf:ncs-device-type "netconf";
        tailf:display-when "not(../../../../../../ncs:module) or ../../../../../../ncs:module[ncs:name='Cisco-IOS-XE-isis']";
      }
      refine adjacency-filter {
        tailf:ncs-device-type "netconf";
        tailf:display-when "not(../../../../../../ncs:module) or ../../../../../../ncs:module[ncs:name='Cisco-IOS-XE-isis']";
      }
    }
  }
  augment "/ncs:devices/ncs:template/ncs:config/ios:native/ios:interface/ios:Loopback/ios:isis" {
    uses ncs_template_config-interface-isis-grouping;
  }
  augment "/ncs:devices/ncs:device/ncs:live-status/ios:native/ios:interface/ios:Loopback/ios:isis" {
    uses live_ncs_config-interface-isis-grouping {
      refine three-way-handshake {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine tag {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-throttle-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine protocol {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine priority {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine password {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine network {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine metric {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine mesh-group {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine lsp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine ipv6 {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-multiplier {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine csnp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine circuit-type {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine authentication {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine advertise {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine adjacency-filter {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
    }
  }
  augment "/ncs:devices/ncs:device/ncs:config/ios:native/ios:interface/ios:Loopback/ios:isis" {
    uses config-interface-isis-grouping {
      refine three-way-handshake {
        tailf:ncs-device-type "netconf";
        tailf:display-when "not(../../../../../../ncs:module) or ../../../../../../ncs:module[ncs:name='Cisco-IOS-XE-isis']";
      }
      refine tag {
        tailf:ncs-device-type "netconf";
        tailf:display-when "not(../../../../../../ncs:module) or ../../../../../../ncs:module[ncs:name='Cisco-IOS-XE-isis']";
      }
      refine retransmit-throttle-interval {
        tailf:ncs-device-type "netconf";
        tailf:display-when "not(../../../../../../ncs:module) or ../../../../../../ncs:module[ncs:name='Cisco-IOS-XE-isis']";
      }
      refine retransmit-interval {
        tailf:ncs-device-type "netconf";
        tailf:display-when "not(../../../../../../ncs:module) or ../../../../../../ncs:module[ncs:name='Cisco-IOS-XE-isis']";
      }
      refine protocol {
        tailf:ncs-device-type "netconf";
        tailf:display-when "not(../../../../../../ncs:module) or ../../../../../../ncs:module[ncs:name='Cisco-IOS-XE-isis']";
      }
      refine priority {
        tailf:ncs-device-type "netconf";
        tailf:display-when "not(../../../../../../ncs:module) or ../../../../../../ncs:module[ncs:name='Cisco-IOS-XE-isis']";
      }
      refine password {
        tailf:ncs-device-type "netconf";
        tailf:display-when "not(../../../../../../ncs:module) or ../../../../../../ncs:module[ncs:name='Cisco-IOS-XE-isis']";
      }
      refine network {
        tailf:ncs-device-type "netconf";
        tailf:display-when "not(../../../../../../ncs:module) or ../../../../../../ncs:module[ncs:name='Cisco-IOS-XE-isis']";
      }
      refine metric {
        tailf:ncs-device-type "netconf";
        tailf:display-when "not(../../../../../../ncs:module) or ../../../../../../ncs:module[ncs:name='Cisco-IOS-XE-isis']";
      }
      refine mesh-group {
        tailf:ncs-device-type "netconf";
        tailf:display-when "not(../../../../../../ncs:module) or ../../../../../../ncs:module[ncs:name='Cisco-IOS-XE-isis']";
      }
      refine lsp-interval {
        tailf:ncs-device-type "netconf";
        tailf:display-when "not(../../../../../../ncs:module) or ../../../../../../ncs:module[ncs:name='Cisco-IOS-XE-isis']";
      }
      refine ipv6 {
        tailf:ncs-device-type "netconf";
        tailf:display-when "not(../../../../../../ncs:module) or ../../../../../../ncs:module[ncs:name='Cisco-IOS-XE-isis']";
      }
      refine hello-multiplier {
        tailf:ncs-device-type "netconf";
        tailf:display-when "not(../../../../../../ncs:module) or ../../../../../../ncs:module[ncs:name='Cisco-IOS-XE-isis']";
      }
      refine hello-interval {
        tailf:ncs-device-type "netconf";
        tailf:display-when "not(../../../../../../ncs:module) or ../../../../../../ncs:module[ncs:name='Cisco-IOS-XE-isis']";
      }
      refine hello {
        tailf:ncs-device-type "netconf";
        tailf:display-when "not(../../../../../../ncs:module) or ../../../../../../ncs:module[ncs:name='Cisco-IOS-XE-isis']";
      }
      refine csnp-interval {
        tailf:ncs-device-type "netconf";
        tailf:display-when "not(../../../../../../ncs:module) or ../../../../../../ncs:module[ncs:name='Cisco-IOS-XE-isis']";
      }
      refine circuit-type {
        tailf:ncs-device-type "netconf";
        tailf:display-when "not(../../../../../../ncs:module) or ../../../../../../ncs:module[ncs:name='Cisco-IOS-XE-isis']";
      }
      refine authentication {
        tailf:ncs-device-type "netconf";
        tailf:display-when "not(../../../../../../ncs:module) or ../../../../../../ncs:module[ncs:name='Cisco-IOS-XE-isis']";
      }
      refine advertise {
        tailf:ncs-device-type "netconf";
        tailf:display-when "not(../../../../../../ncs:module) or ../../../../../../ncs:module[ncs:name='Cisco-IOS-XE-isis']";
      }
      refine adjacency-filter {
        tailf:ncs-device-type "netconf";
        tailf:display-when "not(../../../../../../ncs:module) or ../../../../../../ncs:module[ncs:name='Cisco-IOS-XE-isis']";
      }
    }
  }
  augment "/ncs:devices/ncs:template/ncs:config/ios:native/ios:interface/ios:Tunnel/ios:isis" {
    uses ncs_template_config-interface-isis-grouping;
  }
  augment "/ncs:devices/ncs:device/ncs:live-status/ios:native/ios:interface/ios:Tunnel/ios:isis" {
    uses live_ncs_config-interface-isis-grouping {
      refine three-way-handshake {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine tag {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-throttle-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine protocol {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine priority {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine password {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine network {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine metric {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine mesh-group {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine lsp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine ipv6 {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-multiplier {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine csnp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine circuit-type {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine authentication {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine advertise {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine adjacency-filter {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
    }
  }
  augment "/ncs:devices/ncs:device/ncs:config/ios:native/ios:interface/ios:Tunnel/ios:isis" {
    uses config-interface-isis-grouping {
      refine three-way-handshake {
        tailf:ncs-device-type "netconf";
        tailf:display-when "not(../../../../../../ncs:module) or ../../../../../../ncs:module[ncs:name='Cisco-IOS-XE-isis']";
      }
      refine tag {
        tailf:ncs-device-type "netconf";
        tailf:display-when "not(../../../../../../ncs:module) or ../../../../../../ncs:module[ncs:name='Cisco-IOS-XE-isis']";
      }
      refine retransmit-throttle-interval {
        tailf:ncs-device-type "netconf";
        tailf:display-when "not(../../../../../../ncs:module) or ../../../../../../ncs:module[ncs:name='Cisco-IOS-XE-isis']";
      }
      refine retransmit-interval {
        tailf:ncs-device-type "netconf";
        tailf:display-when "not(../../../../../../ncs:module) or ../../../../../../ncs:module[ncs:name='Cisco-IOS-XE-isis']";
      }
      refine protocol {
        tailf:ncs-device-type "netconf";
        tailf:display-when "not(../../../../../../ncs:module) or ../../../../../../ncs:module[ncs:name='Cisco-IOS-XE-isis']";
      }
      refine priority {
        tailf:ncs-device-type "netconf";
        tailf:display-when "not(../../../../../../ncs:module) or ../../../../../../ncs:module[ncs:name='Cisco-IOS-XE-isis']";
      }
      refine password {
        tailf:ncs-device-type "netconf";
        tailf:display-when "not(../../../../../../ncs:module) or ../../../../../../ncs:module[ncs:name='Cisco-IOS-XE-isis']";
      }
      refine network {
        tailf:ncs-device-type "netconf";
        tailf:display-when "not(../../../../../../ncs:module) or ../../../../../../ncs:module[ncs:name='Cisco-IOS-XE-isis']";
      }
      refine metric {
        tailf:ncs-device-type "netconf";
        tailf:display-when "not(../../../../../../ncs:module) or ../../../../../../ncs:module[ncs:name='Cisco-IOS-XE-isis']";
      }
      refine mesh-group {
        tailf:ncs-device-type "netconf";
        tailf:display-when "not(../../../../../../ncs:module) or ../../../../../../ncs:module[ncs:name='Cisco-IOS-XE-isis']";
      }
      refine lsp-interval {
        tailf:ncs-device-type "netconf";
        tailf:display-when "not(../../../../../../ncs:module) or ../../../../../../ncs:module[ncs:name='Cisco-IOS-XE-isis']";
      }
      refine ipv6 {
        tailf:ncs-device-type "netconf";
        tailf:display-when "not(../../../../../../ncs:module) or ../../../../../../ncs:module[ncs:name='Cisco-IOS-XE-isis']";
      }
      refine hello-multiplier {
        tailf:ncs-device-type "netconf";
        tailf:display-when "not(../../../../../../ncs:module) or ../../../../../../ncs:module[ncs:name='Cisco-IOS-XE-isis']";
      }
      refine hello-interval {
        tailf:ncs-device-type "netconf";
        tailf:display-when "not(../../../../../../ncs:module) or ../../../../../../ncs:module[ncs:name='Cisco-IOS-XE-isis']";
      }
      refine hello {
        tailf:ncs-device-type "netconf";
        tailf:display-when "not(../../../../../../ncs:module) or ../../../../../../ncs:module[ncs:name='Cisco-IOS-XE-isis']";
      }
      refine csnp-interval {
        tailf:ncs-device-type "netconf";
        tailf:display-when "not(../../../../../../ncs:module) or ../../../../../../ncs:module[ncs:name='Cisco-IOS-XE-isis']";
      }
      refine circuit-type {
        tailf:ncs-device-type "netconf";
        tailf:display-when "not(../../../../../../ncs:module) or ../../../../../../ncs:module[ncs:name='Cisco-IOS-XE-isis']";
      }
      refine authentication {
        tailf:ncs-device-type "netconf";
        tailf:display-when "not(../../../../../../ncs:module) or ../../../../../../ncs:module[ncs:name='Cisco-IOS-XE-isis']";
      }
      refine advertise {
        tailf:ncs-device-type "netconf";
        tailf:display-when "not(../../../../../../ncs:module) or ../../../../../../ncs:module[ncs:name='Cisco-IOS-XE-isis']";
      }
      refine adjacency-filter {
        tailf:ncs-device-type "netconf";
        tailf:display-when "not(../../../../../../ncs:module) or ../../../../../../ncs:module[ncs:name='Cisco-IOS-XE-isis']";
      }
    }
  }
  augment "/ncs:devices/ncs:template/ncs:config/ios:native/ios:interface/ios:Vlan/ios:isis" {
    uses ncs_template_config-interface-isis-grouping;
  }
  augment "/ncs:devices/ncs:device/ncs:live-status/ios:native/ios:interface/ios:Vlan/ios:isis" {
    uses live_ncs_config-interface-isis-grouping {
      refine three-way-handshake {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine tag {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-throttle-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine protocol {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine priority {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine password {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine network {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine metric {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine mesh-group {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine lsp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine ipv6 {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-multiplier {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine csnp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine circuit-type {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine authentication {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine advertise {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine adjacency-filter {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
    }
  }
  augment "/ncs:devices/ncs:device/ncs:config/ios:native/ios:interface/ios:Vlan/ios:isis" {
    uses config-interface-isis-grouping {
      refine three-way-handshake {
        tailf:ncs-device-type "netconf";
        tailf:display-when "not(../../../../../../ncs:module) or ../../../../../../ncs:module[ncs:name='Cisco-IOS-XE-isis']";
      }
      refine tag {
        tailf:ncs-device-type "netconf";
        tailf:display-when "not(../../../../../../ncs:module) or ../../../../../../ncs:module[ncs:name='Cisco-IOS-XE-isis']";
      }
      refine retransmit-throttle-interval {
        tailf:ncs-device-type "netconf";
        tailf:display-when "not(../../../../../../ncs:module) or ../../../../../../ncs:module[ncs:name='Cisco-IOS-XE-isis']";
      }
      refine retransmit-interval {
        tailf:ncs-device-type "netconf";
        tailf:display-when "not(../../../../../../ncs:module) or ../../../../../../ncs:module[ncs:name='Cisco-IOS-XE-isis']";
      }
      refine protocol {
        tailf:ncs-device-type "netconf";
        tailf:display-when "not(../../../../../../ncs:module) or ../../../../../../ncs:module[ncs:name='Cisco-IOS-XE-isis']";
      }
      refine priority {
        tailf:ncs-device-type "netconf";
        tailf:display-when "not(../../../../../../ncs:module) or ../../../../../../ncs:module[ncs:name='Cisco-IOS-XE-isis']";
      }
      refine password {
        tailf:ncs-device-type "netconf";
        tailf:display-when "not(../../../../../../ncs:module) or ../../../../../../ncs:module[ncs:name='Cisco-IOS-XE-isis']";
      }
      refine network {
        tailf:ncs-device-type "netconf";
        tailf:display-when "not(../../../../../../ncs:module) or ../../../../../../ncs:module[ncs:name='Cisco-IOS-XE-isis']";
      }
      refine metric {
        tailf:ncs-device-type "netconf";
        tailf:display-when "not(../../../../../../ncs:module) or ../../../../../../ncs:module[ncs:name='Cisco-IOS-XE-isis']";
      }
      refine mesh-group {
        tailf:ncs-device-type "netconf";
        tailf:display-when "not(../../../../../../ncs:module) or ../../../../../../ncs:module[ncs:name='Cisco-IOS-XE-isis']";
      }
      refine lsp-interval {
        tailf:ncs-device-type "netconf";
        tailf:display-when "not(../../../../../../ncs:module) or ../../../../../../ncs:module[ncs:name='Cisco-IOS-XE-isis']";
      }
      refine ipv6 {
        tailf:ncs-device-type "netconf";
        tailf:display-when "not(../../../../../../ncs:module) or ../../../../../../ncs:module[ncs:name='Cisco-IOS-XE-isis']";
      }
      refine hello-multiplier {
        tailf:ncs-device-type "netconf";
        tailf:display-when "not(../../../../../../ncs:module) or ../../../../../../ncs:module[ncs:name='Cisco-IOS-XE-isis']";
      }
      refine hello-interval {
        tailf:ncs-device-type "netconf";
        tailf:display-when "not(../../../../../../ncs:module) or ../../../../../../ncs:module[ncs:name='Cisco-IOS-XE-isis']";
      }
      refine hello {
        tailf:ncs-device-type "netconf";
        tailf:display-when "not(../../../../../../ncs:module) or ../../../../../../ncs:module[ncs:name='Cisco-IOS-XE-isis']";
      }
      refine csnp-interval {
        tailf:ncs-device-type "netconf";
        tailf:display-when "not(../../../../../../ncs:module) or ../../../../../../ncs:module[ncs:name='Cisco-IOS-XE-isis']";
      }
      refine circuit-type {
        tailf:ncs-device-type "netconf";
        tailf:display-when "not(../../../../../../ncs:module) or ../../../../../../ncs:module[ncs:name='Cisco-IOS-XE-isis']";
      }
      refine authentication {
        tailf:ncs-device-type "netconf";
        tailf:display-when "not(../../../../../../ncs:module) or ../../../../../../ncs:module[ncs:name='Cisco-IOS-XE-isis']";
      }
      refine advertise {
        tailf:ncs-device-type "netconf";
        tailf:display-when "not(../../../../../../ncs:module) or ../../../../../../ncs:module[ncs:name='Cisco-IOS-XE-isis']";
      }
      refine adjacency-filter {
        tailf:ncs-device-type "netconf";
        tailf:display-when "not(../../../../../../ncs:module) or ../../../../../../ncs:module[ncs:name='Cisco-IOS-XE-isis']";
      }
    }
  }
  augment "/ncs:devices/ncs:template/ncs:config/ios:native/ios:interface/ios:LISP/ios:isis" {
    uses ncs_template_config-interface-isis-grouping;
  }
  augment "/ncs:devices/ncs:device/ncs:live-status/ios:native/ios:interface/ios:LISP/ios:isis" {
    uses live_ncs_config-interface-isis-grouping {
      refine three-way-handshake {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine tag {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-throttle-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine protocol {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine priority {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine password {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine network {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine metric {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine mesh-group {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine lsp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine ipv6 {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-multiplier {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine csnp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine circuit-type {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine authentication {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine advertise {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine adjacency-filter {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
    }
  }
  augment "/ncs:devices/ncs:device/ncs:config/ios:native/ios:interface/ios:LISP/ios:isis" {
    uses config-interface-isis-grouping {
      refine three-way-handshake {
        tailf:ncs-device-type "netconf";
        tailf:display-when "not(../../../../../../ncs:module) or ../../../../../../ncs:module[ncs:name='Cisco-IOS-XE-isis']";
      }
      refine tag {
        tailf:ncs-device-type "netconf";
        tailf:display-when "not(../../../../../../ncs:module) or ../../../../../../ncs:module[ncs:name='Cisco-IOS-XE-isis']";
      }
      refine retransmit-throttle-interval {
        tailf:ncs-device-type "netconf";
        tailf:display-when "not(../../../../../../ncs:module) or ../../../../../../ncs:module[ncs:name='Cisco-IOS-XE-isis']";
      }
      refine retransmit-interval {
        tailf:ncs-device-type "netconf";
        tailf:display-when "not(../../../../../../ncs:module) or ../../../../../../ncs:module[ncs:name='Cisco-IOS-XE-isis']";
      }
      refine protocol {
        tailf:ncs-device-type "netconf";
        tailf:display-when "not(../../../../../../ncs:module) or ../../../../../../ncs:module[ncs:name='Cisco-IOS-XE-isis']";
      }
      refine priority {
        tailf:ncs-device-type "netconf";
        tailf:display-when "not(../../../../../../ncs:module) or ../../../../../../ncs:module[ncs:name='Cisco-IOS-XE-isis']";
      }
      refine password {
        tailf:ncs-device-type "netconf";
        tailf:display-when "not(../../../../../../ncs:module) or ../../../../../../ncs:module[ncs:name='Cisco-IOS-XE-isis']";
      }
      refine network {
        tailf:ncs-device-type "netconf";
        tailf:display-when "not(../../../../../../ncs:module) or ../../../../../../ncs:module[ncs:name='Cisco-IOS-XE-isis']";
      }
      refine metric {
        tailf:ncs-device-type "netconf";
        tailf:display-when "not(../../../../../../ncs:module) or ../../../../../../ncs:module[ncs:name='Cisco-IOS-XE-isis']";
      }
      refine mesh-group {
        tailf:ncs-device-type "netconf";
        tailf:display-when "not(../../../../../../ncs:module) or ../../../../../../ncs:module[ncs:name='Cisco-IOS-XE-isis']";
      }
      refine lsp-interval {
        tailf:ncs-device-type "netconf";
        tailf:display-when "not(../../../../../../ncs:module) or ../../../../../../ncs:module[ncs:name='Cisco-IOS-XE-isis']";
      }
      refine ipv6 {
        tailf:ncs-device-type "netconf";
        tailf:display-when "not(../../../../../../ncs:module) or ../../../../../../ncs:module[ncs:name='Cisco-IOS-XE-isis']";
      }
      refine hello-multiplier {
        tailf:ncs-device-type "netconf";
        tailf:display-when "not(../../../../../../ncs:module) or ../../../../../../ncs:module[ncs:name='Cisco-IOS-XE-isis']";
      }
      refine hello-interval {
        tailf:ncs-device-type "netconf";
        tailf:display-when "not(../../../../../../ncs:module) or ../../../../../../ncs:module[ncs:name='Cisco-IOS-XE-isis']";
      }
      refine hello {
        tailf:ncs-device-type "netconf";
        tailf:display-when "not(../../../../../../ncs:module) or ../../../../../../ncs:module[ncs:name='Cisco-IOS-XE-isis']";
      }
      refine csnp-interval {
        tailf:ncs-device-type "netconf";
        tailf:display-when "not(../../../../../../ncs:module) or ../../../../../../ncs:module[ncs:name='Cisco-IOS-XE-isis']";
      }
      refine circuit-type {
        tailf:ncs-device-type "netconf";
        tailf:display-when "not(../../../../../../ncs:module) or ../../../../../../ncs:module[ncs:name='Cisco-IOS-XE-isis']";
      }
      refine authentication {
        tailf:ncs-device-type "netconf";
        tailf:display-when "not(../../../../../../ncs:module) or ../../../../../../ncs:module[ncs:name='Cisco-IOS-XE-isis']";
      }
      refine advertise {
        tailf:ncs-device-type "netconf";
        tailf:display-when "not(../../../../../../ncs:module) or ../../../../../../ncs:module[ncs:name='Cisco-IOS-XE-isis']";
      }
      refine adjacency-filter {
        tailf:ncs-device-type "netconf";
        tailf:display-when "not(../../../../../../ncs:module) or ../../../../../../ncs:module[ncs:name='Cisco-IOS-XE-isis']";
      }
    }
  }
  augment "/ncs:devices/ncs:template/ncs:config/ios:native/ios:interface/ios:Virtual-Template/ios:isis" {
    uses ncs_template_config-interface-isis-grouping;
  }
  augment "/ncs:devices/ncs:device/ncs:live-status/ios:native/ios:interface/ios:Virtual-Template/ios:isis" {
    uses live_ncs_config-interface-isis-grouping {
      refine three-way-handshake {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine tag {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-throttle-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine retransmit-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine protocol {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine priority {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine password {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine network {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine metric {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine mesh-group {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine lsp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine ipv6 {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-multiplier {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine hello {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine csnp-interval {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine circuit-type {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine authentication {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine advertise {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
      refine adjacency-filter {
        tailf:ncs-device-type "netconf";
        tailf:display-when "not(../../../../../../ncs:module) or ../../../../../../ncs:module[ncs:name='Cisco-IOS-XE-isis'] or (../../../../../../ncs:live-status-protocol[not(ncs:capability)]) or (../../../../../../ncs:live-status-protocol/ncs:capability/ncs:module[.='Cisco-IOS-XE-isis'])";
      }
    }
  }
  augment "/ncs:devices/ncs:device/ncs:config/ios:native/ios:interface/ios:Virtual-Template/ios:isis" {
    uses config-interface-isis-grouping {
      refine three-way-handshake {
        tailf:ncs-device-type "netconf";
        tailf:display-when "not(../../../../../../ncs:module) or ../../../../../../ncs:module[ncs:name='Cisco-IOS-XE-isis']";
      }
      refine tag {
        tailf:ncs-device-type "netconf";
        tailf:display-when "not(../../../../../../ncs:module) or ../../../../../../ncs:module[ncs:name='Cisco-IOS-XE-isis']";
      }
      refine retransmit-throttle-interval {
        tailf:ncs-device-type "netconf";
        tailf:display-when "not(../../../../../../ncs:module) or ../../../../../../ncs:module[ncs:name='Cisco-IOS-XE-isis']";
      }
      refine retransmit-interval {
        tailf:ncs-device-type "netconf";
        tailf:display-when "not(../../../../../../ncs:module) or ../../../../../../ncs:module[ncs:name='Cisco-IOS-XE-isis']";
      }
      refine protocol {
        tailf:ncs-device-type "netconf";
        tailf:display-when "not(../../../../../../ncs:module) or ../../../../../../ncs:module[ncs:name='Cisco-IOS-XE-isis']";
      }
      refine priority {
        tailf:ncs-device-type "netconf";
        tailf:display-when "not(../../../../../../ncs:module) or ../../../../../../ncs:module[ncs:name='Cisco-IOS-XE-isis']";
      }
      refine password {
        tailf:ncs-device-type "netconf";
        tailf:display-when "not(../../../../../../ncs:module) or ../../../../../../ncs:module[ncs:name='Cisco-IOS-XE-isis']";
      }
      refine network {
        tailf:ncs-device-type "netconf";
        tailf:display-when "not(../../../../../../ncs:module) or ../../../../../../ncs:module[ncs:name='Cisco-IOS-XE-isis']";
      }
      refine metric {
        tailf:ncs-device-type "netconf";
        tailf:display-when "not(../../../../../../ncs:module) or ../../../../../../ncs:module[ncs:name='Cisco-IOS-XE-isis']";
      }
      refine mesh-group {
        tailf:ncs-device-type "netconf";
        tailf:display-when "not(../../../../../../ncs:module) or ../../../../../../ncs:module[ncs:name='Cisco-IOS-XE-isis']";
      }
      refine lsp-interval {
        tailf:ncs-device-type "netconf";
        tailf:display-when "not(../../../../../../ncs:module) or ../../../../../../ncs:module[ncs:name='Cisco-IOS-XE-isis']";
      }
      refine ipv6 {
        tailf:ncs-device-type "netconf";
        tailf:display-when "not(../../../../../../ncs:module) or ../../../../../../ncs:module[ncs:name='Cisco-IOS-XE-isis']";
      }
      refine hello-multiplier {
        tailf:ncs-device-type "netconf";
        tailf:display-when "not(../../../../../../ncs:module) or ../../../../../../ncs:module[ncs:name='Cisco-IOS-XE-isis']";
      }
      refine hello-interval {
        tailf:ncs-device-type "netconf";
        tailf:display-when "not(../../../../../../ncs:module) or ../../../../../../ncs:module[ncs:name='Cisco-IOS-XE-isis']";
      }
      refine hello {
        tailf:ncs-device-type "netconf";
        tailf:display-when "not(../../../../../../ncs:module) or ../../../../../../ncs:module[ncs:name='Cisco-IOS-XE-isis']";
      }
      refine csnp-interval {
        tailf:ncs-device-type "netconf";
        tailf:display-when "not(../../../../../../ncs:module) or ../../../../../../ncs:module[ncs:name='Cisco-IOS-XE-isis']";
      }
      refine circuit-type {
        tailf:ncs-device-type "netconf";
        tailf:display-when "not(../../../../../../ncs:module) or ../../../../../../ncs:module[ncs:name='Cisco-IOS-XE-isis']";
      }
      refine authentication {
        tailf:ncs-device-type "netconf";
        tailf:display-when "not(../../../../../../ncs:module) or ../../../../../../ncs:module[ncs:name='Cisco-IOS-XE-isis']";
      }
      refine advertise {
        tailf:ncs-device-type "netconf";
        tailf:display-when "not(../../../../../../ncs:module) or ../../../../../../ncs:module[ncs:name='Cisco-IOS-XE-isis']";
      }
      refine adjacency-filter {
        tailf:ncs-device-type "netconf";
        tailf:display-when "not(../../../../../../ncs:module) or ../../../../../../ncs:module[ncs:name='Cisco-IOS-XE-isis']";
      }
    }
  }
}
