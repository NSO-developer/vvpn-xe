module Cisco-IOS-XE-l3vpn {
  // Generated by yanger -t ncs
  tailf:ncs-device-type "netconf";

  namespace "http://cisco.com/ns/yang/Cisco-IOS-XE-l3vpn";
  prefix ios-l3vpn;

  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Layer 3 Virtual Private Network (L2VPN) Yang model.
     Copyright (c) 2016 by Cisco Systems, Inc.
     All rights reserved.";

  revision 2017-02-07 {
    description
      "Initial revision";
  }

  grouping ncs_template_config-l3vpn-grouping {
    container encapsulation {
      description
        "l3vpn encapsulation ip";
      list ip {
        // NCS patched for predictable order
        ordered-by user;
        description
          "l3vpn encapsulation ip";
        key "profile-name";
        leaf profile-name {
          type string;
        }
        container transport {
          description
            "transport mode";
          container ipv4 {
            description
              "transport ipv4 mode";
            presence "true";
            leaf source {
              description
                "transport source";
              type string;
            }
          }
        }
        container protocol {
          description
            "protocol mode";
          container gre {
            description
              "protocol gre";
            presence "true";
            leaf key {
              description
                "gre key";
              type string;
            }
          }
        }
        container mpls {
          description
            "Configure MPLS interface parameters";
          leaf mtu {
            description
              "Set MPLS Maximum Transmission Unit";
            type string;
          }
        }
      }
    }
  }

  grouping ncs_rpc_notif_config-l3vpn-grouping {
    container encapsulation {
      description
        "l3vpn encapsulation ip";
      list ip {
        description
          "l3vpn encapsulation ip";
        key "profile-name";
        leaf profile-name {
          type string;
        }
        container transport {
          description
            "transport mode";
          container ipv4 {
            description
              "transport ipv4 mode";
            presence "true";
            leaf source {
              description
                "transport source";
              type string;
            }
          }
        }
        container protocol {
          description
            "protocol mode";
          container gre {
            description
              "protocol gre";
            presence "true";
            leaf key {
              description
                "gre key";
              type uint32 {
                range "0..4294967295";
              }
            }
          }
        }
        container mpls {
          description
            "Configure MPLS interface parameters";
          leaf mtu {
            description
              "Set MPLS Maximum Transmission Unit";
            type union {
              type uint32 {
                range "64..17916";
              }
              type enumeration {
                enum "max";
              }
            }
          }
        }
      }
    }
  }

  grouping live_ncs_config-l3vpn-grouping {
    container encapsulation {
      description
        "l3vpn encapsulation ip";
      list ip {
        description
          "l3vpn encapsulation ip";
        key "profile-name";
        leaf profile-name {
          type string;
        }
        container transport {
          description
            "transport mode";
          container ipv4 {
            description
              "transport ipv4 mode";
            presence "true";
            leaf source {
              description
                "transport source";
              type string;
            }
          }
        }
        container protocol {
          description
            "protocol mode";
          container gre {
            description
              "protocol gre";
            presence "true";
            leaf key {
              description
                "gre key";
              type uint32 {
                range "0..4294967295";
              }
            }
          }
        }
        container mpls {
          description
            "Configure MPLS interface parameters";
          leaf mtu {
            description
              "Set MPLS Maximum Transmission Unit";
            type union {
              type uint32 {
                range "64..17916";
              }
              type enumeration {
                enum "max";
              }
            }
          }
        }
      }
    }
  }

  grouping config-l3vpn-grouping {
    container encapsulation {
      description
        "l3vpn encapsulation ip";
      list ip {
        description
          "l3vpn encapsulation ip";
        key "profile-name";
        leaf profile-name {
          type string;
        }
        container transport {
          description
            "transport mode";
          container ipv4 {
            description
              "transport ipv4 mode";
            presence "true";
            leaf source {
              description
                "transport source";
              type string;
            }
          }
        }
        container protocol {
          description
            "protocol mode";
          container gre {
            description
              "protocol gre";
            presence "true";
            leaf key {
              description
                "gre key";
              type uint32 {
                range "0..4294967295";
              }
            }
          }
        }
        container mpls {
          description
            "Configure MPLS interface parameters";
          leaf mtu {
            description
              "Set MPLS Maximum Transmission Unit";
            type union {
              type uint32 {
                range "64..17916";
              }
              type enumeration {
                enum "max";
              }
            }
          }
        }
      }
    }
  }

  augment "/ncs:devices/ncs:template/ncs:config/ios:native/ios:l3vpn" {
    uses ncs_template_config-l3vpn-grouping;
  }
  augment "/ncs:devices/ncs:device/ncs:live-status/ios:native/ios:l3vpn" {
    uses live_ncs_config-l3vpn-grouping {
      refine encapsulation {
        tailf:ncs-device-type "netconf";
        tailf:display-when "not(../../../../ncs:module) or ../../../../ncs:module[ncs:name='Cisco-IOS-XE-l3vpn'] or (../../../../ncs:live-status-protocol[not(ncs:capability)]) or (../../../../ncs:live-status-protocol/ncs:capability/ncs:module[.='Cisco-IOS-XE-l3vpn'])";
      }
    }
  }
  augment "/ncs:devices/ncs:device/ncs:config/ios:native/ios:l3vpn" {
    uses config-l3vpn-grouping {
      refine encapsulation {
        tailf:ncs-device-type "netconf";
        tailf:display-when "not(../../../../ncs:module) or ../../../../ncs:module[ncs:name='Cisco-IOS-XE-l3vpn']";
      }
    }
  }
}
