submodule Cisco-IOS-XE-logging {
  // Generated by yanger -t ncs
  belongs-to Cisco-IOS-XE-native {
    prefix ios;
  }

  import ietf-inet-types {
    prefix inet;
  }
  import Cisco-IOS-XE-types {
    prefix ios-types;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Logging Yang Model.
     Copyright (c) 2016-2017 by Cisco Systems, Inc.
     All rights reserved.";

  revision 2017-06-02 {
    description
      "logging host ipv6 more support";
  }
  revision 2017-03-01 {
    description
      "logging host/source-interface fix & enhancement";
  }
  revision 2017-02-07 {
    description
      "Initial revision";
  }

  typedef logging-level-type {
    type union {
      type uint16 {
        range "0..7";
      }
      type enumeration {
        enum "alerts";
        enum "critical";
        enum "debugging";
        enum "emergencies";
        enum "errors";
        enum "informational";
        enum "notifications";
        enum "warnings";
        enum "bogus";
      }
    }
  }

  grouping ncs_template_logging-host-option-group {
    leaf discriminator {
      description
        "Specify a message discriminator identifier for this logging session";
      type string;
    }
  }

  grouping ncs_template_logging-host-transport-group {
    container transport {
      container udp {
        leaf-list port {
          // NCS patched for predictable order
          ordered-by user;
          type string;
        }
      }
      container tcp {
        leaf-list port {
          // NCS patched for predictable order
          ordered-by user;
          type string;
        }
      }
    }
  }

  grouping ncs_template_logging-rate-limit-common-group {
    list ranges {
      // NCS patched for predictable order
      ordered-by user;
      key "range";
      leaf range {
        description
          "Messages per second";
        type string;
      }
      container except {
        description
          "Messages of this severity or higher";
        presence "true";
        leaf range {
          description
            "Logging severity level";
          type string;
        }
      }
    }
  }

  grouping ncs_template_config-logging-grouping {
    container logging {
      description
        "Modify message logging facilities";
      list discriminator {
        // NCS patched for predictable order
        ordered-by user;
        description
          "Create or modify a message discriminator";
        key "name";
        leaf name {
          type string;
        }
        container msg-body {
          description
            "Msg-body pattern for messsage filtering";
          leaf drops {
            description
              "To drop messages including the specified regular expression string";
            type string;
          }
          leaf includes {
            description
              "To deliver messages including the specified regular expression string";
            type string;
          }
        }
      }
      container persistent {
        description
          "Set persistent logging parameters";
        presence "true";
        container file {
          leaf url {
            description
              "URL to store logging messages";
            type string;
          }
          leaf size {
            description
              "Set disk space for writing log messages";
            type string;
          }
          leaf threshold {
            description
              "Set threshold for logging persistent";
            type string;
          }
          leaf protected {
            description
              "Eliminates manipulation on logging-persistent files";
            type empty;
          }
        }
      }
      container monitor-conf {
        leaf monitor {
          type string;
        }
      }
      container monitor {
        description
          "Set terminal line (monitor) logging parameters";
        presence "true";
        leaf severity {
          type string;
        }
        list discriminator {
          // NCS patched for predictable order
          ordered-by user;
          description
            "Establish MD-Console association";
          key "name";
          leaf name {
            type string;
          }
          leaf severity {
            type string;
          }
        }
      }
      leaf alarm {
        description
          "Configure syslog for alarms";
        type string;
      }
      container buffered {
        description
          "Set buffered logging parameters";
        presence "true";
        choice buffered-param {
          case discriminator-param {
            list discriminator {
              // NCS patched for predictable order
              ordered-by user;
              key "name";
              leaf name {
                type string;
              }
              leaf size-value {
                type string;
              }
              leaf severity {
                type string;
              }
            }
          }
          case size-param {
            container size {
              leaf size-value {
                type string;
              }
              leaf severity {
                type string;
                // NCS drop default statement
              }
            }
          }
          case severity-level {
            leaf severity {
              type string;
            }
          }
          case xxml-buffer {
            leaf xxml {
              description
                "Enable logging in XML to XML logging buffer";
              type string;
            }
          }
        }
      }
      container console-conf {
        leaf console {
          description
            "Set console logging parameters";
          type string;
        }
      }
      container console {
        description
          "Set console logging parameters";
        presence "true";
        list discriminator {
          // NCS patched for predictable order
          ordered-by user;
          description
            "Establish MD-Console association";
          key "name";
          leaf name {
            type string;
          }
          leaf severity {
            type string;
          }
        }
        leaf filtered {
          description
            "Enable filtered logging";
          type empty;
        }
        leaf guaranteed {
          description
            "Guarantee console messages";
          type empty;
        }
        leaf xxml {
          description
            "Enable logging in XML";
          type string;
        }
        leaf severity {
          type string;
        }
      }
      container event {
        description
          "Global interface events";
        container link-status {
          description
            "Globally enable/disable link UPDOWN message";
          leaf boot {
            description
              "Supress/Allow link UPDOWN messages during boot";
            type empty;
          }
          leaf global {
            type empty;
          }
          leaf default {
            description
              "Link UPDOWN messages for all interfaces";
            type empty;
          }
        }
      }
      container esm {
        description
          "Set ESM filter restrictions";
        leaf config {
          description
            "Permit/Deny configuration changes from ESM filters";
          type empty;
        }
      }
      leaf facility {
        description
          "Facility parameter for syslog messages";
        type string;
      }
      container history {
        description
          "Configure syslog history table";
        leaf size {
          description
            "Set history table size";
          type string;
        }
        leaf severity-level {
          type string;
        }
      }
      container host {
        description
          "Set syslog server IP address and parameters";
        list ipv4-host-list {
          // NCS patched for predictable order
          ordered-by user;
          key "ipv4-host";
          leaf ipv4-host {
            type string;
          }
        }
        list ipv4-host-transport-list {
          // NCS patched for predictable order
          ordered-by user;
          key "ipv4-host";
          leaf ipv4-host {
            type string;
          }
          uses ncs_template_logging-host-transport-group;
          uses ncs_template_logging-host-option-group;
        }
        list ipv4-host-vrf-list {
          // NCS patched for predictable order
          ordered-by user;
          key "ipv4-host vrf";
          leaf ipv4-host {
            type string;
          }
          leaf vrf {
            description
              "Set VRF option";
            type string;
          }
          uses ncs_template_logging-host-option-group;
        }
        list ipv4-host-vrf-transport-list {
          // NCS patched for predictable order
          ordered-by user;
          key "ipv4-host vrf";
          leaf ipv4-host {
            type string;
          }
          leaf vrf {
            description
              "Set VRF option";
            type string;
          }
          uses ncs_template_logging-host-transport-group;
          uses ncs_template_logging-host-option-group;
        }
        container ipv6 {
          description
            "Set syslog server IPv6 address";
          list ipv6-host-list {
            // NCS patched for predictable order
            ordered-by user;
            key "ipv6-host";
            leaf ipv6-host {
              type string;
            }
          }
          list ipv6-host-transport-list {
            // NCS patched for predictable order
            ordered-by user;
            key "ipv6-host";
            leaf ipv6-host {
              type string;
            }
            uses ncs_template_logging-host-transport-group;
            uses ncs_template_logging-host-option-group;
          }
          list ipv6-host-vrf-list {
            // NCS patched for predictable order
            ordered-by user;
            key "ipv6-host vrf";
            leaf ipv6-host {
              type string;
            }
            leaf vrf {
              description
                "Set VRF option";
              type string;
            }
            uses ncs_template_logging-host-option-group;
          }
          list ipv6-host-vrf-transport-list {
            // NCS patched for predictable order
            ordered-by user;
            key "ipv6-host vrf";
            leaf ipv6-host {
              type string;
            }
            leaf vrf {
              description
                "Set VRF option";
              type string;
            }
            uses ncs_template_logging-host-transport-group;
            uses ncs_template_logging-host-option-group;
          }
        }
      }
      container origin-id {
        description
          "Add origin ID to syslog messages";
        choice origin-choice {
          case origin-type {
            leaf type-value {
              description
                "Use origin hostname/ip/ipv6 as ID";
              type string;
            }
          }
          case origin-name {
            leaf string {
              description
                "Define a unique text string as ID";
              type string;
            }
          }
        }
      }
      container rate-limit-conf {
        leaf rate-limit {
          type string;
        }
      }
      container rate-limit {
        description
          "Set messages per second limit";
        presence "true";
        uses ncs_template_logging-rate-limit-common-group;
        container console {
          description
            "Rate limit only console messages";
          uses ncs_template_logging-rate-limit-common-group;
          container all {
            description
              "all";
            uses ncs_template_logging-rate-limit-common-group;
          }
        }
        container all {
          description
            "Rate limit only console messages";
          uses ncs_template_logging-rate-limit-common-group;
        }
      }
      list source-interface {
        // NCS patched for predictable order
        ordered-by user;
        description
          "Specify interface for source address in logging transactions";
        key "interface-name";
        leaf interface-name {
          type string;
        }
        leaf vrf {
          description
            "Specify the vrf of source interface for logging transactions";
          type string;
        }
      }
      container snmp-trap {
        description
          "Set SNMP trap logging level";
        leaf alerts {
          description
            "Immediate action needed           (severity=1)";
          type empty;
        }
        leaf critical {
          description
            "Critical conditions               (severity=2)";
          type empty;
        }
        leaf debugging {
          description
            "Debugging messages                (severity=7)";
          type empty;
        }
        leaf emergencies {
          description
            "System is unusable                (severity=0)";
          type empty;
        }
        leaf errors {
          description
            "Error conditions                  (severity=3)";
          type empty;
        }
        leaf informational {
          description
            "Informational messages            (severity=6)";
          type empty;
        }
        leaf notifications {
          description
            "Normal but significant conditions (severity=5)";
          type empty;
        }
        leaf warnings {
          description
            "Warning conditions                (severity=4)";
          type empty;
        }
      }
      container trap {
        description
          "Set trap server logging level";
        presence "true";
        choice level {
          case set-default {
            leaf trap-default {
              type empty;
            }
          }
          case set-level {
            leaf severity {
              type string;
              // NCS drop default statement
            }
          }
        }
      }
      leaf hostip {
        type string;
      }
      container file {
        description
          "Set logging file parameters";
        leaf name {
          type string;
        }
        leaf max-size {
          type string;
        }
        leaf min-size {
          type string;
        }
        leaf severity {
          type string;
        }
      }
      leaf snmp-authfail {
        type empty;
      }
      leaf buginf {
        description
          "Enable buginf logging for debugging";
        type empty;
      }
      leaf userinfo {
        description
          "Enable logging of user info on privileged mode enabling";
        type empty;
      }
    }
  }

  grouping ncs_rpc_notif_logging-host-option-group {
    leaf discriminator {
      description
        "Specify a message discriminator identifier for this logging session";
      type string;
    }
  }

  grouping ncs_rpc_notif_logging-host-transport-group {
    container transport {
      container udp {
        leaf-list port {
          type uint16;
        }
      }
      container tcp {
        leaf-list port {
          type uint16;
        }
      }
    }
  }

  grouping ncs_rpc_notif_logging-rate-limit-common-group {
    list ranges {
      key "range";
      leaf range {
        description
          "Messages per second";
        type uint16 {
          range "1..10000";
        }
      }
      container except {
        description
          "Messages of this severity or higher";
        presence "true";
        leaf range {
          description
            "Logging severity level";
          type logging-level-type;
        }
      }
    }
  }

  grouping ncs_rpc_notif_config-logging-grouping {
    container logging {
      description
        "Modify message logging facilities";
      list discriminator {
        description
          "Create or modify a message discriminator";
        key "name";
        leaf name {
          type string;
        }
        container msg-body {
          description
            "Msg-body pattern for messsage filtering";
          leaf drops {
            description
              "To drop messages including the specified regular expression string";
            type string;
          }
          leaf includes {
            description
              "To deliver messages including the specified regular expression string";
            type string;
          }
        }
      }
      container persistent {
        description
          "Set persistent logging parameters";
        presence "true";
        container file {
          leaf url {
            description
              "URL to store logging messages";
            type string;
          }
          leaf size {
            description
              "Set disk space for writing log messages";
            type string;
          }
          leaf threshold {
            description
              "Set threshold for logging persistent";
            type string;
          }
          leaf protected {
            description
              "Eliminates manipulation on logging-persistent files";
            type empty;
          }
        }
      }
      container monitor-conf {
        leaf monitor {
          type boolean;
        }
      }
      container monitor {
        description
          "Set terminal line (monitor) logging parameters";
        presence "true";
        leaf severity {
          type logging-level-type;
        }
        list discriminator {
          description
            "Establish MD-Console association";
          key "name";
          leaf name {
            type string;
          }
          leaf severity {
            type logging-level-type;
          }
        }
      }
      leaf alarm {
        description
          "Configure syslog for alarms";
        type union {
          type uint8 {
            range "1..4";
          }
          type enumeration {
            enum "critical";
            enum "informational";
            enum "major";
            enum "minor";
          }
        }
      }
      container buffered {
        description
          "Set buffered logging parameters";
        presence "true";
        choice buffered-param {
          case discriminator-param {
            list discriminator {
              key "name";
              leaf name {
                type string;
              }
              leaf size-value {
                type uint32 {
                  range "4096..2147483647";
                }
              }
              leaf severity {
                type logging-level-type;
              }
            }
          }
          case size-param {
            container size {
              leaf size-value {
                type uint32 {
                  range "4096..2147483647";
                }
              }
              leaf severity {
                type logging-level-type;
                default "debugging";
              }
            }
          }
          case severity-level {
            leaf severity {
              type logging-level-type;
            }
          }
          case xxml-buffer {
            leaf xxml {
              description
                "Enable logging in XML to XML logging buffer";
              type uint32 {
                range "4096..2147483647";
              }
            }
          }
        }
      }
      container console-conf {
        leaf console {
          description
            "Set console logging parameters";
          type boolean;
        }
      }
      container console {
        description
          "Set console logging parameters";
        presence "true";
        list discriminator {
          description
            "Establish MD-Console association";
          key "name";
          leaf name {
            type string;
          }
          leaf severity {
            type logging-level-type;
          }
        }
        leaf filtered {
          description
            "Enable filtered logging";
          type empty;
        }
        leaf guaranteed {
          description
            "Guarantee console messages";
          type empty;
        }
        leaf xxml {
          description
            "Enable logging in XML";
          type logging-level-type;
        }
        leaf severity {
          type logging-level-type;
        }
      }
      container event {
        description
          "Global interface events";
        container link-status {
          description
            "Globally enable/disable link UPDOWN message";
          leaf boot {
            description
              "Supress/Allow link UPDOWN messages during boot";
            type empty;
          }
          leaf global {
            type empty;
          }
          leaf default {
            description
              "Link UPDOWN messages for all interfaces";
            type empty;
          }
        }
      }
      container esm {
        description
          "Set ESM filter restrictions";
        leaf config {
          description
            "Permit/Deny configuration changes from ESM filters";
          type empty;
        }
      }
      leaf facility {
        description
          "Facility parameter for syslog messages";
        type enumeration {
          enum "auth";
          enum "cron";
          enum "daemon";
          enum "kern";
          enum "local0";
          enum "local1";
          enum "local2";
          enum "local3";
          enum "local4";
          enum "local5";
          enum "local6";
          enum "local7";
          enum "lpr";
          enum "mail";
          enum "news";
          enum "sys10";
          enum "sys11";
          enum "sys12";
          enum "sys13";
          enum "sys14";
          enum "sys9";
          enum "syslog";
          enum "user";
          enum "uucp";
        }
      }
      container history {
        description
          "Configure syslog history table";
        leaf size {
          description
            "Set history table size";
          type uint16;
        }
        leaf severity-level {
          type union {
            type uint8 {
              range "0..7";
            }
            type enumeration {
              enum "alerts";
              enum "critical";
              enum "debugging";
              enum "emergencies";
              enum "errors";
              enum "informational";
              enum "notifications";
              enum "warnings";
            }
          }
        }
      }
      container host {
        description
          "Set syslog server IP address and parameters";
        list ipv4-host-list {
          key "ipv4-host";
          leaf ipv4-host {
            type inet:host;
          }
        }
        list ipv4-host-transport-list {
          key "ipv4-host";
          leaf ipv4-host {
            type inet:host;
          }
          uses ncs_rpc_notif_logging-host-transport-group;
          uses ncs_rpc_notif_logging-host-option-group;
        }
        list ipv4-host-vrf-list {
          key "ipv4-host vrf";
          leaf ipv4-host {
            type inet:host;
          }
          leaf vrf {
            description
              "Set VRF option";
            type string;
          }
          uses ncs_rpc_notif_logging-host-option-group;
        }
        list ipv4-host-vrf-transport-list {
          key "ipv4-host vrf";
          leaf ipv4-host {
            type inet:host;
          }
          leaf vrf {
            description
              "Set VRF option";
            type string;
          }
          uses ncs_rpc_notif_logging-host-transport-group;
          uses ncs_rpc_notif_logging-host-option-group;
        }
        container ipv6 {
          description
            "Set syslog server IPv6 address";
          list ipv6-host-list {
            key "ipv6-host";
            leaf ipv6-host {
              type ios-types:ipv6-host;
            }
          }
          list ipv6-host-transport-list {
            key "ipv6-host";
            leaf ipv6-host {
              type ios-types:ipv6-host;
            }
            uses ncs_rpc_notif_logging-host-transport-group;
            uses ncs_rpc_notif_logging-host-option-group;
          }
          list ipv6-host-vrf-list {
            key "ipv6-host vrf";
            leaf ipv6-host {
              type ios-types:ipv6-host;
            }
            leaf vrf {
              description
                "Set VRF option";
              type string;
            }
            uses ncs_rpc_notif_logging-host-option-group;
          }
          list ipv6-host-vrf-transport-list {
            key "ipv6-host vrf";
            leaf ipv6-host {
              type ios-types:ipv6-host;
            }
            leaf vrf {
              description
                "Set VRF option";
              type string;
            }
            uses ncs_rpc_notif_logging-host-transport-group;
            uses ncs_rpc_notif_logging-host-option-group;
          }
        }
      }
      container origin-id {
        description
          "Add origin ID to syslog messages";
        choice origin-choice {
          case origin-type {
            leaf type-value {
              description
                "Use origin hostname/ip/ipv6 as ID";
              type enumeration {
                enum "hostname";
                enum "ip";
                enum "ipv6";
              }
            }
          }
          case origin-name {
            leaf string {
              description
                "Define a unique text string as ID";
              type string;
            }
          }
        }
      }
      container rate-limit-conf {
        leaf rate-limit {
          type boolean;
        }
      }
      container rate-limit {
        description
          "Set messages per second limit";
        presence "true";
        uses ncs_rpc_notif_logging-rate-limit-common-group;
        container console {
          description
            "Rate limit only console messages";
          uses ncs_rpc_notif_logging-rate-limit-common-group;
          container all {
            description
              "all";
            uses ncs_rpc_notif_logging-rate-limit-common-group;
          }
        }
        container all {
          description
            "Rate limit only console messages";
          uses ncs_rpc_notif_logging-rate-limit-common-group;
        }
      }
      list source-interface {
        description
          "Specify interface for source address in logging transactions";
        key "interface-name";
        leaf interface-name {
          type string;
        }
        leaf vrf {
          description
            "Specify the vrf of source interface for logging transactions";
          type string;
        }
      }
      container snmp-trap {
        description
          "Set SNMP trap logging level";
        leaf alerts {
          description
            "Immediate action needed           (severity=1)";
          type empty;
        }
        leaf critical {
          description
            "Critical conditions               (severity=2)";
          type empty;
        }
        leaf debugging {
          description
            "Debugging messages                (severity=7)";
          type empty;
        }
        leaf emergencies {
          description
            "System is unusable                (severity=0)";
          type empty;
        }
        leaf errors {
          description
            "Error conditions                  (severity=3)";
          type empty;
        }
        leaf informational {
          description
            "Informational messages            (severity=6)";
          type empty;
        }
        leaf notifications {
          description
            "Normal but significant conditions (severity=5)";
          type empty;
        }
        leaf warnings {
          description
            "Warning conditions                (severity=4)";
          type empty;
        }
      }
      container trap {
        description
          "Set trap server logging level";
        presence "true";
        choice level {
          case set-default {
            leaf trap-default {
              type empty;
            }
          }
          case set-level {
            leaf severity {
              type union {
                type uint8 {
                  range "0..7";
                }
                type enumeration {
                  enum "alerts";
                  enum "critical";
                  enum "debugging";
                  enum "emergencies";
                  enum "errors";
                  enum "informational";
                  enum "notifications";
                  enum "warnings";
                }
              }
              default "informational";
            }
          }
        }
      }
      leaf hostip {
        type inet:host;
      }
      container file {
        description
          "Set logging file parameters";
        leaf name {
          type string;
        }
        leaf max-size {
          type uint32;
        }
        leaf min-size {
          type uint32;
        }
        leaf severity {
          type logging-level-type;
        }
      }
      leaf snmp-authfail {
        type empty;
      }
      leaf buginf {
        description
          "Enable buginf logging for debugging";
        type empty;
      }
      leaf userinfo {
        description
          "Enable logging of user info on privileged mode enabling";
        type empty;
      }
    }
  }

  grouping live_ncs_logging-host-option-group {
    leaf discriminator {
      description
        "Specify a message discriminator identifier for this logging session";
      type string;
    }
  }

  grouping live_ncs_logging-host-transport-group {
    container transport {
      container udp {
        leaf-list port {
          type uint16;
        }
      }
      container tcp {
        leaf-list port {
          type uint16;
        }
      }
    }
  }

  grouping live_ncs_logging-rate-limit-common-group {
    list ranges {
      key "range";
      leaf range {
        description
          "Messages per second";
        type uint16 {
          range "1..10000";
        }
      }
      container except {
        description
          "Messages of this severity or higher";
        presence "true";
        leaf range {
          description
            "Logging severity level";
          type logging-level-type;
        }
      }
    }
  }

  grouping live_ncs_config-logging-grouping {
    container logging {
      description
        "Modify message logging facilities";
      list discriminator {
        description
          "Create or modify a message discriminator";
        key "name";
        leaf name {
          type string;
        }
        container msg-body {
          description
            "Msg-body pattern for messsage filtering";
          leaf drops {
            description
              "To drop messages including the specified regular expression string";
            type string;
          }
          leaf includes {
            description
              "To deliver messages including the specified regular expression string";
            type string;
          }
        }
      }
      container persistent {
        description
          "Set persistent logging parameters";
        presence "true";
        container file {
          leaf url {
            description
              "URL to store logging messages";
            type string;
          }
          leaf size {
            description
              "Set disk space for writing log messages";
            type string;
          }
          leaf threshold {
            description
              "Set threshold for logging persistent";
            type string;
          }
          leaf protected {
            description
              "Eliminates manipulation on logging-persistent files";
            type empty;
          }
        }
      }
      container monitor-conf {
        leaf monitor {
          type boolean;
        }
      }
      container monitor {
        description
          "Set terminal line (monitor) logging parameters";
        presence "true";
        leaf severity {
          type logging-level-type;
        }
        list discriminator {
          description
            "Establish MD-Console association";
          key "name";
          leaf name {
            type string;
          }
          leaf severity {
            type logging-level-type;
          }
        }
      }
      leaf alarm {
        description
          "Configure syslog for alarms";
        type union {
          type uint8 {
            range "1..4";
          }
          type enumeration {
            enum "critical";
            enum "informational";
            enum "major";
            enum "minor";
          }
        }
      }
      container buffered {
        description
          "Set buffered logging parameters";
        presence "true";
        choice buffered-param {
          case discriminator-param {
            list discriminator {
              key "name";
              leaf name {
                type string;
              }
              leaf size-value {
                type uint32 {
                  range "4096..2147483647";
                }
              }
              leaf severity {
                type logging-level-type;
              }
            }
          }
          case size-param {
            container size {
              leaf size-value {
                type uint32 {
                  range "4096..2147483647";
                }
              }
              leaf severity {
                type logging-level-type;
                // NCS drop default statement
              }
            }
          }
          case severity-level {
            leaf severity {
              type logging-level-type;
            }
          }
          case xxml-buffer {
            leaf xxml {
              description
                "Enable logging in XML to XML logging buffer";
              type uint32 {
                range "4096..2147483647";
              }
            }
          }
        }
      }
      container console-conf {
        leaf console {
          description
            "Set console logging parameters";
          type boolean;
        }
      }
      container console {
        description
          "Set console logging parameters";
        presence "true";
        list discriminator {
          description
            "Establish MD-Console association";
          key "name";
          leaf name {
            type string;
          }
          leaf severity {
            type logging-level-type;
          }
        }
        leaf filtered {
          description
            "Enable filtered logging";
          type empty;
        }
        leaf guaranteed {
          description
            "Guarantee console messages";
          type empty;
        }
        leaf xxml {
          description
            "Enable logging in XML";
          type logging-level-type;
        }
        leaf severity {
          type logging-level-type;
        }
      }
      container event {
        description
          "Global interface events";
        container link-status {
          description
            "Globally enable/disable link UPDOWN message";
          leaf boot {
            description
              "Supress/Allow link UPDOWN messages during boot";
            type empty;
          }
          leaf global {
            type empty;
          }
          leaf default {
            description
              "Link UPDOWN messages for all interfaces";
            type empty;
          }
        }
      }
      container esm {
        description
          "Set ESM filter restrictions";
        leaf config {
          description
            "Permit/Deny configuration changes from ESM filters";
          type empty;
        }
      }
      leaf facility {
        description
          "Facility parameter for syslog messages";
        type enumeration {
          enum "auth";
          enum "cron";
          enum "daemon";
          enum "kern";
          enum "local0";
          enum "local1";
          enum "local2";
          enum "local3";
          enum "local4";
          enum "local5";
          enum "local6";
          enum "local7";
          enum "lpr";
          enum "mail";
          enum "news";
          enum "sys10";
          enum "sys11";
          enum "sys12";
          enum "sys13";
          enum "sys14";
          enum "sys9";
          enum "syslog";
          enum "user";
          enum "uucp";
        }
      }
      container history {
        description
          "Configure syslog history table";
        leaf size {
          description
            "Set history table size";
          type uint16;
        }
        leaf severity-level {
          type union {
            type uint8 {
              range "0..7";
            }
            type enumeration {
              enum "alerts";
              enum "critical";
              enum "debugging";
              enum "emergencies";
              enum "errors";
              enum "informational";
              enum "notifications";
              enum "warnings";
            }
          }
        }
      }
      container host {
        description
          "Set syslog server IP address and parameters";
        list ipv4-host-list {
          key "ipv4-host";
          leaf ipv4-host {
            type inet:host;
          }
        }
        list ipv4-host-transport-list {
          key "ipv4-host";
          leaf ipv4-host {
            type inet:host;
          }
          uses live_ncs_logging-host-transport-group;
          uses live_ncs_logging-host-option-group;
        }
        list ipv4-host-vrf-list {
          key "ipv4-host vrf";
          leaf ipv4-host {
            type inet:host;
          }
          leaf vrf {
            description
              "Set VRF option";
            type string;
          }
          uses live_ncs_logging-host-option-group;
        }
        list ipv4-host-vrf-transport-list {
          key "ipv4-host vrf";
          leaf ipv4-host {
            type inet:host;
          }
          leaf vrf {
            description
              "Set VRF option";
            type string;
          }
          uses live_ncs_logging-host-transport-group;
          uses live_ncs_logging-host-option-group;
        }
        container ipv6 {
          description
            "Set syslog server IPv6 address";
          list ipv6-host-list {
            key "ipv6-host";
            leaf ipv6-host {
              type ios-types:ipv6-host;
            }
          }
          list ipv6-host-transport-list {
            key "ipv6-host";
            leaf ipv6-host {
              type ios-types:ipv6-host;
            }
            uses live_ncs_logging-host-transport-group;
            uses live_ncs_logging-host-option-group;
          }
          list ipv6-host-vrf-list {
            key "ipv6-host vrf";
            leaf ipv6-host {
              type ios-types:ipv6-host;
            }
            leaf vrf {
              description
                "Set VRF option";
              type string;
            }
            uses live_ncs_logging-host-option-group;
          }
          list ipv6-host-vrf-transport-list {
            key "ipv6-host vrf";
            leaf ipv6-host {
              type ios-types:ipv6-host;
            }
            leaf vrf {
              description
                "Set VRF option";
              type string;
            }
            uses live_ncs_logging-host-transport-group;
            uses live_ncs_logging-host-option-group;
          }
        }
      }
      container origin-id {
        description
          "Add origin ID to syslog messages";
        choice origin-choice {
          case origin-type {
            leaf type-value {
              description
                "Use origin hostname/ip/ipv6 as ID";
              type enumeration {
                enum "hostname";
                enum "ip";
                enum "ipv6";
              }
            }
          }
          case origin-name {
            leaf string {
              description
                "Define a unique text string as ID";
              type string;
            }
          }
        }
      }
      container rate-limit-conf {
        leaf rate-limit {
          type boolean;
        }
      }
      container rate-limit {
        description
          "Set messages per second limit";
        presence "true";
        uses live_ncs_logging-rate-limit-common-group;
        container console {
          description
            "Rate limit only console messages";
          uses live_ncs_logging-rate-limit-common-group;
          container all {
            description
              "all";
            uses live_ncs_logging-rate-limit-common-group;
          }
        }
        container all {
          description
            "Rate limit only console messages";
          uses live_ncs_logging-rate-limit-common-group;
        }
      }
      list source-interface {
        description
          "Specify interface for source address in logging transactions";
        key "interface-name";
        leaf interface-name {
          type string;
        }
        leaf vrf {
          description
            "Specify the vrf of source interface for logging transactions";
          type string;
        }
      }
      container snmp-trap {
        description
          "Set SNMP trap logging level";
        leaf alerts {
          description
            "Immediate action needed           (severity=1)";
          type empty;
        }
        leaf critical {
          description
            "Critical conditions               (severity=2)";
          type empty;
        }
        leaf debugging {
          description
            "Debugging messages                (severity=7)";
          type empty;
        }
        leaf emergencies {
          description
            "System is unusable                (severity=0)";
          type empty;
        }
        leaf errors {
          description
            "Error conditions                  (severity=3)";
          type empty;
        }
        leaf informational {
          description
            "Informational messages            (severity=6)";
          type empty;
        }
        leaf notifications {
          description
            "Normal but significant conditions (severity=5)";
          type empty;
        }
        leaf warnings {
          description
            "Warning conditions                (severity=4)";
          type empty;
        }
      }
      container trap {
        description
          "Set trap server logging level";
        presence "true";
        choice level {
          case set-default {
            leaf trap-default {
              type empty;
            }
          }
          case set-level {
            leaf severity {
              type union {
                type uint8 {
                  range "0..7";
                }
                type enumeration {
                  enum "alerts";
                  enum "critical";
                  enum "debugging";
                  enum "emergencies";
                  enum "errors";
                  enum "informational";
                  enum "notifications";
                  enum "warnings";
                }
              }
              // NCS drop default statement
            }
          }
        }
      }
      leaf hostip {
        type inet:host;
      }
      container file {
        description
          "Set logging file parameters";
        leaf name {
          type string;
        }
        leaf max-size {
          type uint32;
        }
        leaf min-size {
          type uint32;
        }
        leaf severity {
          type logging-level-type;
        }
      }
      leaf snmp-authfail {
        type empty;
      }
      leaf buginf {
        description
          "Enable buginf logging for debugging";
        type empty;
      }
      leaf userinfo {
        description
          "Enable logging of user info on privileged mode enabling";
        type empty;
      }
    }
  }

  grouping logging-host-option-group {
    leaf discriminator {
      description
        "Specify a message discriminator identifier for this logging session";
      type string;
    }
  }

  grouping logging-host-transport-group {
    container transport {
      container udp {
        leaf-list port {
          type uint16;
        }
      }
      container tcp {
        leaf-list port {
          type uint16;
        }
      }
    }
  }

  grouping logging-rate-limit-common-group {
    list ranges {
      key "range";
      leaf range {
        description
          "Messages per second";
        type uint16 {
          range "1..10000";
        }
      }
      container except {
        description
          "Messages of this severity or higher";
        presence "true";
        leaf range {
          description
            "Logging severity level";
          type logging-level-type;
        }
      }
    }
  }

  grouping config-logging-grouping {
    container logging {
      description
        "Modify message logging facilities";
      list discriminator {
        description
          "Create or modify a message discriminator";
        key "name";
        leaf name {
          type string;
        }
        container msg-body {
          description
            "Msg-body pattern for messsage filtering";
          leaf drops {
            description
              "To drop messages including the specified regular expression string";
            type string;
          }
          leaf includes {
            description
              "To deliver messages including the specified regular expression string";
            type string;
          }
        }
      }
      container persistent {
        description
          "Set persistent logging parameters";
        presence "true";
        container file {
          leaf url {
            description
              "URL to store logging messages";
            type string;
          }
          leaf size {
            description
              "Set disk space for writing log messages";
            type string;
          }
          leaf threshold {
            description
              "Set threshold for logging persistent";
            type string;
          }
          leaf protected {
            description
              "Eliminates manipulation on logging-persistent files";
            type empty;
          }
        }
      }
      container monitor-conf {
        leaf monitor {
          type boolean;
        }
      }
      container monitor {
        description
          "Set terminal line (monitor) logging parameters";
        presence "true";
        leaf severity {
          type logging-level-type;
        }
        list discriminator {
          description
            "Establish MD-Console association";
          key "name";
          leaf name {
            type string;
          }
          leaf severity {
            type logging-level-type;
          }
        }
      }
      leaf alarm {
        description
          "Configure syslog for alarms";
        type union {
          type uint8 {
            range "1..4";
          }
          type enumeration {
            enum "critical";
            enum "informational";
            enum "major";
            enum "minor";
          }
        }
      }
      container buffered {
        description
          "Set buffered logging parameters";
        presence "true";
        choice buffered-param {
          case discriminator-param {
            list discriminator {
              key "name";
              leaf name {
                type string;
              }
              leaf size-value {
                type uint32 {
                  range "4096..2147483647";
                }
              }
              leaf severity {
                type logging-level-type;
              }
            }
          }
          case size-param {
            container size {
              leaf size-value {
                type uint32 {
                  range "4096..2147483647";
                }
              }
              leaf severity {
                type logging-level-type;
                default "debugging";
              }
            }
          }
          case severity-level {
            leaf severity {
              type logging-level-type;
            }
          }
          case xxml-buffer {
            leaf xxml {
              description
                "Enable logging in XML to XML logging buffer";
              type uint32 {
                range "4096..2147483647";
              }
            }
          }
        }
      }
      container console-conf {
        leaf console {
          description
            "Set console logging parameters";
          type boolean;
        }
      }
      container console {
        description
          "Set console logging parameters";
        presence "true";
        list discriminator {
          description
            "Establish MD-Console association";
          key "name";
          leaf name {
            type string;
          }
          leaf severity {
            type logging-level-type;
          }
        }
        leaf filtered {
          description
            "Enable filtered logging";
          type empty;
        }
        leaf guaranteed {
          description
            "Guarantee console messages";
          type empty;
        }
        leaf xxml {
          description
            "Enable logging in XML";
          type logging-level-type;
        }
        leaf severity {
          type logging-level-type;
        }
      }
      container event {
        description
          "Global interface events";
        container link-status {
          description
            "Globally enable/disable link UPDOWN message";
          leaf boot {
            description
              "Supress/Allow link UPDOWN messages during boot";
            type empty;
          }
          leaf global {
            type empty;
          }
          leaf default {
            description
              "Link UPDOWN messages for all interfaces";
            type empty;
          }
        }
      }
      container esm {
        description
          "Set ESM filter restrictions";
        leaf config {
          description
            "Permit/Deny configuration changes from ESM filters";
          type empty;
        }
      }
      leaf facility {
        description
          "Facility parameter for syslog messages";
        type enumeration {
          enum "auth";
          enum "cron";
          enum "daemon";
          enum "kern";
          enum "local0";
          enum "local1";
          enum "local2";
          enum "local3";
          enum "local4";
          enum "local5";
          enum "local6";
          enum "local7";
          enum "lpr";
          enum "mail";
          enum "news";
          enum "sys10";
          enum "sys11";
          enum "sys12";
          enum "sys13";
          enum "sys14";
          enum "sys9";
          enum "syslog";
          enum "user";
          enum "uucp";
        }
      }
      container history {
        description
          "Configure syslog history table";
        leaf size {
          description
            "Set history table size";
          type uint16;
        }
        leaf severity-level {
          type union {
            type uint8 {
              range "0..7";
            }
            type enumeration {
              enum "alerts";
              enum "critical";
              enum "debugging";
              enum "emergencies";
              enum "errors";
              enum "informational";
              enum "notifications";
              enum "warnings";
            }
          }
        }
      }
      container host {
        description
          "Set syslog server IP address and parameters";
        list ipv4-host-list {
          key "ipv4-host";
          leaf ipv4-host {
            type inet:host;
          }
        }
        list ipv4-host-transport-list {
          key "ipv4-host";
          leaf ipv4-host {
            type inet:host;
          }
          uses logging-host-transport-group;
          uses logging-host-option-group;
        }
        list ipv4-host-vrf-list {
          key "ipv4-host vrf";
          leaf ipv4-host {
            type inet:host;
          }
          leaf vrf {
            description
              "Set VRF option";
            type string;
          }
          uses logging-host-option-group;
        }
        list ipv4-host-vrf-transport-list {
          key "ipv4-host vrf";
          leaf ipv4-host {
            type inet:host;
          }
          leaf vrf {
            description
              "Set VRF option";
            type string;
          }
          uses logging-host-transport-group;
          uses logging-host-option-group;
        }
        container ipv6 {
          description
            "Set syslog server IPv6 address";
          list ipv6-host-list {
            key "ipv6-host";
            leaf ipv6-host {
              type ios-types:ipv6-host;
            }
          }
          list ipv6-host-transport-list {
            key "ipv6-host";
            leaf ipv6-host {
              type ios-types:ipv6-host;
            }
            uses logging-host-transport-group;
            uses logging-host-option-group;
          }
          list ipv6-host-vrf-list {
            key "ipv6-host vrf";
            leaf ipv6-host {
              type ios-types:ipv6-host;
            }
            leaf vrf {
              description
                "Set VRF option";
              type string;
            }
            uses logging-host-option-group;
          }
          list ipv6-host-vrf-transport-list {
            key "ipv6-host vrf";
            leaf ipv6-host {
              type ios-types:ipv6-host;
            }
            leaf vrf {
              description
                "Set VRF option";
              type string;
            }
            uses logging-host-transport-group;
            uses logging-host-option-group;
          }
        }
      }
      container origin-id {
        description
          "Add origin ID to syslog messages";
        choice origin-choice {
          case origin-type {
            leaf type-value {
              description
                "Use origin hostname/ip/ipv6 as ID";
              type enumeration {
                enum "hostname";
                enum "ip";
                enum "ipv6";
              }
            }
          }
          case origin-name {
            leaf string {
              description
                "Define a unique text string as ID";
              type string;
            }
          }
        }
      }
      container rate-limit-conf {
        leaf rate-limit {
          type boolean;
        }
      }
      container rate-limit {
        description
          "Set messages per second limit";
        presence "true";
        uses logging-rate-limit-common-group;
        container console {
          description
            "Rate limit only console messages";
          uses logging-rate-limit-common-group;
          container all {
            description
              "all";
            uses logging-rate-limit-common-group;
          }
        }
        container all {
          description
            "Rate limit only console messages";
          uses logging-rate-limit-common-group;
        }
      }
      list source-interface {
        description
          "Specify interface for source address in logging transactions";
        key "interface-name";
        leaf interface-name {
          type string;
        }
        leaf vrf {
          description
            "Specify the vrf of source interface for logging transactions";
          type string;
        }
      }
      container snmp-trap {
        description
          "Set SNMP trap logging level";
        leaf alerts {
          description
            "Immediate action needed           (severity=1)";
          type empty;
        }
        leaf critical {
          description
            "Critical conditions               (severity=2)";
          type empty;
        }
        leaf debugging {
          description
            "Debugging messages                (severity=7)";
          type empty;
        }
        leaf emergencies {
          description
            "System is unusable                (severity=0)";
          type empty;
        }
        leaf errors {
          description
            "Error conditions                  (severity=3)";
          type empty;
        }
        leaf informational {
          description
            "Informational messages            (severity=6)";
          type empty;
        }
        leaf notifications {
          description
            "Normal but significant conditions (severity=5)";
          type empty;
        }
        leaf warnings {
          description
            "Warning conditions                (severity=4)";
          type empty;
        }
      }
      container trap {
        description
          "Set trap server logging level";
        presence "true";
        choice level {
          case set-default {
            leaf trap-default {
              type empty;
            }
          }
          case set-level {
            leaf severity {
              type union {
                type uint8 {
                  range "0..7";
                }
                type enumeration {
                  enum "alerts";
                  enum "critical";
                  enum "debugging";
                  enum "emergencies";
                  enum "errors";
                  enum "informational";
                  enum "notifications";
                  enum "warnings";
                }
              }
              default "informational";
            }
          }
        }
      }
      leaf hostip {
        type inet:host;
      }
      container file {
        description
          "Set logging file parameters";
        leaf name {
          type string;
        }
        leaf max-size {
          type uint32;
        }
        leaf min-size {
          type uint32;
        }
        leaf severity {
          type logging-level-type;
        }
      }
      leaf snmp-authfail {
        type empty;
      }
      leaf buginf {
        description
          "Enable buginf logging for debugging";
        type empty;
      }
      leaf userinfo {
        description
          "Enable logging of user info on privileged mode enabling";
        type empty;
      }
    }
  }
}
