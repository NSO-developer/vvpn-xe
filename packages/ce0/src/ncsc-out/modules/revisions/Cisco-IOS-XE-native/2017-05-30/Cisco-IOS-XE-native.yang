module Cisco-IOS-XE-native {
  // Generated by yanger -t ncs
  tailf:ncs-device-type "netconf";

  namespace "http://cisco.com/ns/yang/Cisco-IOS-XE-native";
  prefix ios-native;

  import ietf-inet-types {
    prefix inet;
  }
  import Cisco-IOS-XE-types {
    prefix ios-types;
  }
  import Cisco-IOS-XE-features {
    prefix ios-features;
  }
  import Cisco-IOS-XE-interface-common {
    prefix ios-ifc;
  }
  include Cisco-IOS-XE-parser;
  include Cisco-IOS-XE-license;
  include Cisco-IOS-XE-line;
  include Cisco-IOS-XE-logging;
  include Cisco-IOS-XE-ip;
  include Cisco-IOS-XE-ipv6;
  include Cisco-IOS-XE-interfaces;
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "NED YANG module for IOS-XE
     Copyright (c) 2016-2017 by Cisco Systems, Inc.
     All rights reserved.";

  revision 2017-05-30 {
    description
      "add default crypto ikev2 policy and proposal";
  }
  revision 2017-03-24 {
    description
      "Removed banner";
  }
  revision 2017-02-07 {
    description
      "Initial revision";
  }

  augment "/ncs:devices/ncs:device/ncs:config" {
    container native {
      tailf:ncs-device-type "netconf";
      tailf:display-when "not(../../ncs:module) or ../../ncs:module[ncs:name='Cisco-IOS-XE-native']";
      container default {
        description
          "Set a command to its defaults";
        container crypto {
          description
            "Encryption module";
          container ikev2 {
            description
              "Configure IKEv2 Options";
            leaf proposal {
              description
                "Define IKEV2 proposals";
              type empty;
            }
            leaf policy {
              description
                "Define IKEV2 policies";
              type empty;
            }
          }
        }
      }
      container bfd {
        description
          "BFD configuration commands";
      }
      leaf version {
        description
          "Version";
        type string;
      }
      leaf boot-start-marker {
        type empty;
      }
      container boot {
        description
          "Modify boot system parameters";
        container system {
          description
            "System Image";
          leaf tftp-path {
            description
              "Example: 192.x.x.x/<path to image>";
            type string;
          }
          leaf tftp {
            description
              "Example 192.168.x.x/<image-path>";
            type string;
          }
          container bootfile {
            description
              "WORD - boot filename";
            list filename-list {
              key "filename";
              leaf filename {
                description
                  "WORD - TFTP filename or URL";
                type string;
              }
            }
          }
          container flash {
            description
              "flash - Boot from flash memory";
            list flash-list {
              key "flash-leaf";
              leaf flash-leaf {
                type string;
              }
            }
          }
        }
      }
      leaf boot-end-marker {
        type empty;
      }
      leaf captive-portal-bypass {
        description
          "Enable Captive portal bypass for apple devices";
        type empty;
      }
      container memory {
        description
          "Configure memory management";
        container statistics {
          description
            "Configure statistics history table";
          container history {
            description
              "Configure statistics history table";
            leaf table {
              description
                "Configure statistics history table";
              type uint8 {
                range "12..72";
              }
            }
          }
        }
        container chunk {
          description
            "chunk related configuration";
          container siblings {
            description
              "chunk siblings related configuration";
            leaf threshold {
              description
                "Default is platform dependent";
              type uint32 {
                range "2..4294967295";
              }
            }
          }
        }
        container free {
          description
            "free memory low water mark";
          container low-watermark {
            description
              "low water mark for notifications";
            leaf IO {
              description
                "low water mark of memory in KB";
              type uint32 {
                range "1..3994575";
              }
            }
            leaf processor {
              description
                "low water mark of memory in KB";
              type uint32 {
                range "1..3994575";
              }
            }
          }
        }
        leaf lite {
          description
            "Enable/disable memory lite";
          type empty;
        }
        container reserve {
          description
            "reserve memory";
          container critical {
            description
              "Reserve Critical Memory";
            presence "true";
            leaf memory-range {
              description
                "total amount of memory to be reserved in kilobytes";
              type uint32 {
                range "1..4294967295";
              }
            }
          }
        }
        container sanity {
          description
            "Enable memory sanity";
          presence "true";
          leaf all {
            description
              "Enable memory sanity all";
            type empty;
          }
          leaf buffer {
            description
              "Enable memory sanity buffer";
            type empty;
          }
          leaf queue {
            type empty;
          }
        }
      }
      container location {
        description
          "Global location configuration commands";
        container civic-location {
          description
            "Civic location information";
          list identifier {
            description
              "Set the identifier";
            key "identifier";
            leaf identifier {
              type string;
            }
            leaf building {
              description
                "Building information";
              type string;
            }
            leaf floor {
              description
                "Floor number";
              type string;
            }
            leaf landmark {
              description
                "Landmark";
              type string;
            }
            leaf name {
              description
                "Resident name";
              type string;
            }
            leaf number {
              description
                "Street number";
              type string;
            }
          }
        }
      }
      container call-home {
        description
          "Enter call-home configuration mode";
        presence "true";
      }
      container hw-module {
        description
          "Control of individual components in the system";
        container uplink {
          description
            "Uplink control";
          leaf select {
            description
              "Select uplink interface";
            type string;
          }
          leaf mode {
            description
              "Uplink mode";
            type enumeration {
              enum "shared-backplane";
            }
          }
        }
        leaf sm {
          type uint8;
        }
        leaf pvdm {
          type string;
        }
      }
      container cisp {
        description
          "Set CISP parameters";
        leaf enable {
          description
            "Enable CISP";
          type empty;
        }
      }
      container module {
        description
          "Module";
      }
      list domain {
        description
          "Domain Configuration Commands";
        key "name";
        leaf name {
          type string;
        }
        list vrf {
          description
            "Specify vrf for domain";
          key "name";
          leaf name {
            type string;
          }
          container border {
            description
              "Enter border router configuration submode";
            container source-interface {
              description
                "Source Interface for border";
              leaf Loopback {
                description
                  "Loopback interface";
                type uint32;
              }
            }
            leaf master {
              description
                "Specify IP address of Domain master controller";
              type union {
                type inet:ipv4-address;
                type enumeration {
                  enum "local";
                }
              }
            }
            container password {
              description
                "MD5 password to be used with MC";
              leaf encryption {
                type enumeration {
                  enum "0";
                  enum "7";
                }
              }
              leaf clear-key {
                type string;
              }
            }
          }
          container master {
            description
              "Enter master controller configuration submode";
            choice master-type {
              case branch {
                leaf branch {
                  description
                    "Set master type as branch hub";
                  type empty;
                }
              }
              case hub {
                leaf hub {
                  description
                    "Set master type as hub";
                  type empty;
                }
              }
              case transit {
                leaf transit {
                  description
                    "Set master type as transit";
                  type empty;
                }
              }
            }
            container advanced {
              description
                "Advanced configuration submode";
              leaf byte-loss-threshold {
                description
                  "Specify minimum byte loss calculation threshold";
                type uint16 {
                  range "0..5600";
                }
              }
              leaf channel-unreachable-timer {
                description
                  "Unreach interval detection";
                type uint16 {
                  range "1..65535";
                }
              }
              leaf load-sharing {
                description
                  "Enable load-sharing";
                type empty;
              }
              leaf minimum-mask-length {
                description
                  "Specify minimum mask length";
                type uint8 {
                  range "1..32";
                }
              }
              leaf mitigation-mode {
                description
                  "Enable brownout detection in domain";
                type enumeration {
                  enum "aggressive";
                }
              }
              leaf packet-loss-threshold {
                description
                  "Specify minimum packet loss calculation threshold";
                type uint8 {
                  range "1..100";
                }
              }
              container smart-probes {
                description
                  "Smart probes configuration";
                leaf destination-port {
                  description
                    "Specify smart probes destination port number";
                  type uint16 {
                    range "1..65535";
                  }
                }
                leaf source-port {
                  description
                    "Specify smart probes source port number";
                  type uint16 {
                    range "1..65535";
                  }
                }
              }
              container syslog {
                description
                  "Specify syslog minimim time between tca";
                leaf tca-time-min {
                  description
                    "Specify time between syslog tcas in seconds";
                  type uint32 {
                    range "30..36000";
                  }
                }
              }
              container tcp {
                description
                  "Specify tcp port numbers for mc-br communication";
                leaf mc-port {
                  description
                    "Specify tcp MC self port for mc-br communication";
                  type uint16 {
                    range "1..65535";
                  }
                }
              }
              leaf threshold-variance {
                description
                  "Policy decision Threshold variance";
                type uint8 {
                  range "0..100";
                }
              }
              container traffic-class-ageout-timer {
                description
                  "Traffic-class DB age timer";
                leaf interval {
                  description
                    "Specify new timer interval value mins/hours";
                  type uint16 {
                    range "5..65535";
                  }
                }
                leaf interval-unit {
                  type enumeration {
                    enum "hours";
                    enum "minutes";
                  }
                }
              }
              leaf transit-site-affinity {
                description
                  "Enable Transit Site Affinity";
                type empty;
              }
            }
            container collector {
              description
                "NMS/v9 collector configuration";
              leaf ip {
                type inet:ipv4-address;
              }
              leaf port {
                description
                  "Specify collector port number";
                type uint16;
              }
            }
            container enterprise-prefix {
              description
                "Enterprise prefix configuration";
              leaf prefix-list {
                description
                  "Specify prefix-list with static site targets";
                type string;
              }
            }
            container load-balance {
              description
                "load balance non-policy traffic";
              presence "true";
              leaf advanced {
                description
                  "Load balancing configuration mode";
                type empty;
              }
            }
            container password {
              description
                "MD5 password to be used with BRs";
              leaf encryption {
                type enumeration {
                  enum "0";
                  enum "7";
                }
              }
              leaf clear-key {
                type string;
              }
            }
            container site-prefixes {
              description
                "site-prefixes configuration";
              leaf prefix-list {
                description
                  "Specify prefix-list with static site targets";
                type string;
              }
            }
            container source-interface {
              description
                "Source Interface for master controller";
              leaf Loopback {
                description
                  "Loopback interface";
                type uint32;
              }
            }
            list class {
              description
                "Create domain class and enter domain class command mode";
              key "name sequence";
              leaf name {
                type string;
              }
              leaf sequence {
                description
                  "Set the Sequence for the class";
                type uint16;
              }
              container match {
                description
                  "Specify the applications the policy applies to";
                list dscp {
                  description
                    "specify DSCP";
                  key "value";
                  leaf value {
                    type ios-types:dscp-type;
                  }
                  leaf policy {
                    description
                      "Specify the policy (user defined/predefined)";
                    type enumeration {
                      enum "best-effort";
                      enum "bulk-data";
                      enum "custom";
                      enum "low-latency-data";
                      enum "real-time-video";
                      enum "scavenger";
                      enum "voice";
                    }
                  }
                }
              }
              container path-preference {
                description
                  "Specify the preferred provider";
                leaf-list primary {
                  description
                    "Primary service provider";
                  ordered-by user;
                  type string;
                }
                leaf-list fallback {
                  description
                    "Specify the fallback provider";
                  ordered-by user;
                  type string;
                }
              }
            }
            leaf hub-ip {
              type inet:ipv4-address;
            }
          }
        }
      }
      uses config-parser-grouping;
      container service {
        description
          "Modify use of network based services";
        leaf internal {
          description
            "Enable/Disable Internal commands";
          type empty;
        }
        container pad-conf {
          leaf pad {
            description
              "Enable PAD commands";
            type boolean;
          }
        }
        container pad {
          description
            "Enable PAD commands";
          presence "true";
          leaf cmns {
            description
              "Enable PAD over CMNS connections";
            type empty;
          }
          leaf from-xot {
            description
              "Accept XOT to PAD connections";
            type empty;
          }
          leaf to-xot {
            description
              "Allow outgoing PAD over XOT connections";
            type empty;
          }
        }
        leaf password-encryption {
          description
            "Encrypt system passwords";
          type empty;
        }
        leaf password-recovery {
          description
            "Enable password recovery";
          type boolean;
        }
        container timestamps {
          description
            "Timestamp debug/log messages";
          presence "true";
          container debug {
            description
              "Timestamp debug messages";
            container datetime {
              description
                "Timestamp with date and time";
              presence "true";
              container localtime {
                description
                  "Use local time zone for timestamps";
                presence "true";
                container msec {
                  description
                    "Include milliseconds in timestamp";
                  presence "true";
                  uses service-timestamp-show-timezone-and-year;
                }
                container show-timezone {
                  description
                    "Add time zone information to timestamp";
                  presence "true";
                  uses service-timestamp-msec-and-year;
                }
                container year {
                  description
                    "Include year in timestamp";
                  presence "true";
                  uses service-timestamp-msec-and-show-timezone;
                }
              }
              container msec {
                description
                  "Include milliseconds in timestamp";
                presence "true";
                container localtime {
                  description
                    "Use local time zone for timestamps";
                  presence "true";
                  uses service-timestamp-show-timezone-and-year;
                }
                container show-timezone {
                  description
                    "Add time zone information to timestamp";
                  presence "true";
                  uses service-timestamp-local-time-and-year;
                }
                container year {
                  description
                    "Include year in timestamp";
                  presence "true";
                  uses service-timestamp-local-time-and-show-timezone;
                }
              }
              container show-timezone {
                description
                  "Add time zone information to timestamp";
                presence "true";
                container localtime {
                  description
                    "Use local time zone for timestamps";
                  presence "true";
                  uses service-timestamp-msec-and-year;
                }
                container msec {
                  description
                    "Include milliseconds in timestamp";
                  presence "true";
                  uses service-timestamp-local-time-and-year;
                }
                container year {
                  description
                    "Include year in timestamp";
                  presence "true";
                  uses service-timestamp-local-time-and-msec;
                }
              }
              container year {
                description
                  "Include year in timestamp";
                presence "true";
                container localtime {
                  description
                    "Use local time zone for timestamps";
                  presence "true";
                  uses service-timestamp-msec-and-show-timezone;
                }
                container msec {
                  description
                    "Include milliseconds in timestamp";
                  presence "true";
                  uses service-timestamp-local-time-and-show-timezone;
                }
                container show-timezone {
                  description
                    "Add time zone information to timestamp";
                  presence "true";
                  uses service-timestamp-local-time-and-msec;
                }
              }
            }
            leaf uptime {
              description
                "Timestamp with system uptime";
              type empty;
            }
          }
          container log {
            description
              "Timestamp log messages";
            container datetime {
              description
                "Timestamp with date and time";
              presence "true";
              leaf msec {
                description
                  "Include milliseconds in timestamp";
                type empty;
              }
              leaf localtime {
                description
                  "Use local time zone for timestamps";
                type empty;
              }
              leaf show-timezone {
                description
                  "Add time zone information to timestamp";
                type empty;
              }
              leaf year {
                description
                  "Include year in timestamp";
                type empty;
              }
            }
            leaf uptime {
              description
                "Timestamp with system uptime";
              type empty;
            }
          }
        }
        container alignment {
          description
            "Control alignment correction and logging";
          leaf detection {
            description
              "Enable detection of alignment issues";
            type empty;
          }
          leaf logging {
            description
              "Enable logging of alignment issues";
            type empty;
          }
        }
        leaf call-home {
          description
            "Enable call-home service";
          type empty;
        }
        leaf compress-config {
          description
            "Compress the configuration file";
          type empty;
        }
        leaf config {
          description
            "TFTP load config files";
          type empty;
        }
        container counters {
          description
            "Control aging of interface counters";
          container max {
            description
              "Maximum counter aging threshold";
            leaf age {
              description
                "Aging threshold";
              type uint8 {
                range "0..60";
              }
            }
          }
        }
        leaf dhcp {
          description
            "Enable DHCP server and relay agent";
          type empty;
        }
        leaf disable-ip-fast-frag {
          description
            "Disable IP particle-based fast fragmentation";
          type empty;
        }
        leaf exec-callback {
          description
            "Enable exec callback";
          type empty;
        }
        leaf exec-wait {
          description
            "Delay EXEC startup on noisy lines";
          type empty;
        }
        leaf finger {
          description
            "Allow responses to finger requests";
          type empty;
        }
        container heartbeat {
          description
            "Enable heartbeat processing";
          leaf fatal-count {
            description
              "Set heartbeat fatal count";
            type uint8 {
              range "1..60";
            }
          }
          leaf interrupt-interval {
            description
              "Set heartbeat interrupt test interval";
            type uint8 {
              range "0..60";
            }
          }
          leaf interrupt-max {
            description
              "Set maximum message count from interrupt test";
            type uint8 {
              range "0..60";
            }
          }
          leaf transmit-interval {
            description
              "Set heartbeat transmit interval";
            type uint8 {
              range "1..30";
            }
          }
          leaf warning-timeout {
            description
              "Set heartbeat warning timeout interval";
            type uint8 {
              range "5..60";
            }
          }
        }
        leaf hide-telnet-addresses {
          description
            "Hide destination addresses in telnet command";
          type empty;
        }
        leaf linenumber {
          description
            "enable line number banner for each exec";
          type empty;
        }
        leaf log-hidden {
          description
            "Enable syslog msgs for hidden/internal commands";
          type empty;
        }
        leaf nagle {
          description
            "Enable Nagle's congestion control algorithm";
          type empty;
        }
        leaf old-slip-prompts {
          description
            "Allow old scripts to operate with slip/ppp";
          type empty;
        }
        container prompt {
          description
            "Enable mode specific prompt";
          leaf config {
            description
              "Enable configuration mode prompt";
            type empty;
          }
        }
        leaf pt-vty-logging {
          description
            "Log significant VTY-Async events";
          type empty;
        }
        leaf sequence-numbers {
          description
            "Stamp logger messages with a sequence number";
          type empty;
        }
        leaf slave-log {
          description
            "Enable log capability of slave IPs";
          type empty;
        }
        leaf tcp-keepalives-in {
          description
            "Generate keepalives on idle incoming network connections";
          type empty;
        }
        leaf tcp-keepalives-out {
          description
            "Generate keepalives on idle outgoing network connections";
          type empty;
        }
        leaf telnet-zeroidle {
          description
            "Set TCP window 0 when connection is idle";
          type empty;
        }
        leaf tcp-small-servers {
          description
            "Enable small TCP servers (e.g., ECHO)";
          type empty;
        }
        leaf udp-small-servers {
          description
            "Enable small UDP servers (e.g., ECHO)";
          type empty;
        }
        leaf unsupported-transceiver {
          description
            "Enable support for third-party transceivers";
          type empty;
        }
      }
      container platform {
        description
          "platform specific configuration";
      }
      leaf hostname {
        description
          "Set system's network name";
        type string;
      }
      container enable {
        description
          "Modify enable password parameters";
        container password {
          description
            "Assign the privileged level password (MAX of 25 characters)";
          uses password-07-grouping;
        }
        leaf last-resort {
          description
            "Define enable action if no TACACS servers respond";
          type enumeration {
            enum "password";
            enum "succeed";
          }
        }
        container secret {
          description
            "Assign the privileged level secret";
          leaf level {
            description
              "Set exec level password";
            type uint8;
          }
          leaf type {
            type enumeration {
              enum "0";
              enum "4";
              enum "5";
            }
          }
          leaf secret {
            type string;
          }
        }
        leaf use-tacacs {
          description
            "Use TACACS to check enable passwords";
          type empty;
        }
      }
      container password {
        description
          "Configure encryption password (key)";
        container encryption {
          description
            "Encrypt system passwords";
          leaf aes {
            description
              "Enable stronger (AES) password encryption";
            type empty;
          }
        }
      }
      container eap {
        description
          "Configure EAP authenticator parameters";
        list profile {
          description
            "EAP authenticator profile configuration";
          key "name";
          leaf name {
            description
              "WORD;;EAP authenticator profile name";
            type string;
          }
          container method {
            description
              "Add an allowed method";
            leaf fast {
              description
                "EAP-FAST method allowed";
              type empty;
            }
            leaf gtc {
              description
                "EAP-GTC method allowed";
              type empty;
            }
            leaf leap {
              description
                "EAP-LEAP method allowed";
              type empty;
            }
            leaf mschapv2 {
              description
                "EAP-MSCHAPV2 method allowed";
              type empty;
            }
            leaf peap {
              description
                "EAP-PEAP method allowed";
              type empty;
            }
            leaf md5 {
              description
                "EAP-MD5 method allowed";
              type empty;
            }
            leaf tls {
              description
                "EAP-TLS method allowed";
              type empty;
            }
          }
          leaf pki-trustpoint {
            description
              "Set the default pki trustpoint";
            type string;
          }
        }
      }
      container archive {
        description
          "Archive the configuration";
        container log {
          description
            "Logging commands";
          container config {
            description
              "Logging changes to the running configuration";
            leaf hidekeys {
              description
                "suppress output (e.g. passwords) when displaying logged commands";
              type empty;
            }
            container logging {
              description
                "Modify config logging parameters";
              leaf enable {
                description
                  "Enable the config logger";
                type empty;
              }
              leaf size {
                description
                  "Maximum number of logged commands that will be kept by the config log";
                type uint16 {
                  range "1..1000";
                }
              }
              container persistent {
                description
                  "Log configuration persistent";
                presence "true";
                leaf auto {
                  description
                    "Log configuration commands automatically";
                  type empty;
                }
                leaf reload {
                  description
                    "Apply persisted commands on reload";
                  type empty;
                }
              }
            }
            container notify {
              description
                "Send logged commands to target applications";
              container syslog {
                description
                  "Send logged commands as syslog messages";
                presence "true";
                leaf contenttype {
                  description
                    "Type of the syslog message content";
                  type enumeration {
                    enum "plaintext";
                    enum "xml";
                  }
                }
              }
            }
          }
        }
        leaf path {
          description
            "path for backups";
          type union {
            type enumeration {
              enum "bootflash:";
              enum "flash:";
              enum "ftp:";
              enum "harddisk:";
              enum "http:";
              enum "https:";
              enum "pram:";
              enum "rcp:";
              enum "scp:";
              enum "tftp:";
            }
            type string;
          }
        }
        leaf maximum {
          description
            "maximum number of backup copies";
          type uint8 {
            range "1..14";
          }
        }
        leaf write-memory {
          description
            "Enable automatic backup generation during write memory";
          type empty;
        }
        leaf time-period {
          description
            "Period of time in minutes to automatically archive the running-config";
          type uint32 {
            range "1..525600";
          }
        }
      }
      list username {
        description
          "Establish User Name Authentication";
        key "name";
        leaf name {
          type string;
        }
        leaf privilege {
          description
            "Set user privilege level";
          type uint8 {
            range "0..15";
          }
        }
        leaf one-time {
          description
            "Specify that the username/password is valid for only one time";
          type empty;
        }
        container password {
          description
            "Specify the password for the user";
          leaf encryption {
            type enumeration {
              enum "0";
              enum "7";
            }
          }
          leaf password {
            type string;
          }
        }
        container secret {
          description
            "Specify the secret for the user";
          leaf encryption {
            type enumeration {
              enum "0";
              enum "5";
            }
          }
          leaf secret {
            type string;
          }
        }
      }
      container controller {
        description
          "Configure controller";
      }
      leaf aqm-register-fnf {
        description
          "Export audio/video stats to flow record";
        type empty;
      }
      uses config-vrf-definition-grouping;
      container rmon {
        description
          "Remote Monitoring";
        list alarm {
          description
            "Configure an RMON alarm";
          key "number";
          leaf number {
            type uint16;
          }
          leaf mib-object {
            type string;
          }
          leaf sample-interval {
            type uint32;
          }
          leaf test-mode {
            type enumeration {
              enum "absolute";
              enum "delta";
            }
          }
          leaf rising-threshold {
            description
              "Configure the rising threshold";
            type int32;
          }
          leaf rising-event {
            type uint16;
          }
          leaf falling-threshold {
            description
              "Configure the falling threshold";
            type int32;
          }
          leaf falling-event {
            type uint16;
          }
          leaf owner {
            description
              "Specify an owner for the alarm";
            type string;
          }
        }
        list event {
          description
            "Configure an RMON event";
          key "number";
          leaf number {
            type uint16;
          }
          container log {
            description
              "Generate RMON log when the event fires";
            presence "true";
            leaf trap {
              description
                "Generate SNMP trap when the event fires";
              type string;
            }
            leaf description {
              description
                "Specify a description of the event";
              type string;
            }
            leaf owner {
              description
                "Specify an owner for the event";
              type string;
            }
          }
        }
      }
      list sampler {
        description
          "Define a Sampler";
        key "name";
        leaf name {
          type string;
        }
      }
      container flow {
        description
          "Global Flow configuration subcommands";
      }
      uses config-ip-grouping;
      container mka {
        description
          "MACsec Key Agreement (MKA) configuration";
      }
      container macro {
        description
          "Macro configuration";
        container global {
          description
            "Enter global macro configuration";
          leaf description {
            description
              "Macro description of this device";
            type string;
          }
        }
        container auto {
          description
            "Macro autoexecution settings";
        }
      }
      uses config-ipv6-grouping;
      container vlan {
        description
          "Global vlan configuration";
      }
      container cdp {
        description
          "Global CDP configuration subcommands";
      }
      container policy;
      uses config-interface-grouping;
      list route-map {
        description
          "Route map tag";
        key "name";
        leaf name {
          description
            "WORD;;Route map tag";
          type string;
        }
      }
      container route-tag;
      list table-map {
        description
          "Configure Table Map";
        key "name";
        leaf name {
          type string;
        }
      }
      container sdm {
        description
          "Switch database management";
      }
      container mls {
        description
          "mls global commands";
      }
      container object-group {
        description
          "Configure Object group";
      }
      list pseudowire-class {
        description
          "Pseudowire-class configuration";
        key "name";
        leaf name {
          type string;
        }
      }
      container control-plane {
        description
          "Configure control plane services";
        presence "true";
      }
      container control-plane-host {
        container control-plane {
          description
            "Configure control plane services";
          container host {
            presence "true";
            list management-interface {
              description
                "Configure interface for receiving network management traffic";
              key "interface-name";
              leaf interface-name {
                type string;
              }
              container allow {
                description
                  "Allowed network management protocols on selected interface";
                leaf beep {
                  description
                    "Beep Protocol";
                  type empty;
                }
                leaf ftp {
                  description
                    "File Transfer Protocol";
                  type empty;
                }
                leaf http {
                  description
                    "HTTP Protocol";
                  type empty;
                }
                leaf https {
                  description
                    "HTTPS Protocol";
                  type empty;
                }
                leaf snmp {
                  description
                    "Simple Network Management Protocol";
                  type empty;
                }
                leaf ssh {
                  description
                    "Secure Shell Protocol";
                  type empty;
                }
                leaf telnet {
                  description
                    "Telnet Protocol";
                  type empty;
                }
                leaf tftp {
                  description
                    "Trivial File Transfer Protocol";
                  type empty;
                }
                leaf tl1 {
                  description
                    "Transaction Language Session Protocol";
                  type empty;
                }
              }
            }
          }
        }
      }
      leaf config-register {
        description
          "Define the configuration register";
        type string {
          pattern '[0-9xXa-fA-F].*';
        }
      }
      container clock {
        description
          "Configure time-of-day clock";
        container calendar-valid {
          description
            "Calendar time is authoritative";
          presence "true";
        }
        container summer-time {
          description
            "Configure summer (daylight savings) time";
          leaf zone {
            type string;
          }
          choice summer-choice {
            case date-case {
              leaf date {
                description
                  "Configure absolute summer time";
                type empty;
              }
              leaf start-day {
                type uint8 {
                  range "1..31";
                }
              }
              leaf start-month {
                type ios-types:month-type;
              }
              leaf start-year {
                type uint32 {
                  range "1993..2035";
                }
              }
              leaf start-time {
                type ios-types:hhmm-type;
              }
              leaf date-end-day {
                type uint8 {
                  range "1..31";
                }
              }
              leaf date-end-month {
                type ios-types:month-type;
              }
              leaf date-end-year {
                type uint32 {
                  range "1993..2035";
                }
              }
              leaf date-end-time {
                type ios-types:hhmm-type;
              }
              leaf offset {
                type uint16 {
                  range "1..1440";
                }
              }
            }
            case recurring-case {
              leaf recurring {
                description
                  "Configure recurring summer time";
                type empty;
              }
              leaf recurring-start {
                type union {
                  type uint8 {
                    range "1..4";
                  }
                  type enumeration {
                    enum "first";
                    enum "last";
                  }
                }
              }
              leaf recurring-start-day {
                type ios-types:weekday-type;
              }
              leaf recurring-start-month {
                type ios-types:month-type;
              }
              leaf recurring-start-time {
                type ios-types:hhmm-type;
              }
              leaf recurring-end {
                type union {
                  type uint8 {
                    range "1..4";
                  }
                  type enumeration {
                    enum "first";
                    enum "last";
                  }
                }
              }
              leaf recurring-end-day {
                type ios-types:weekday-type;
              }
              leaf recurring-end-month {
                type ios-types:month-type;
              }
              leaf recurring-end-time {
                type ios-types:hhmm-type;
              }
              leaf recurring-offset {
                type uint16 {
                  range "1..1440";
                }
              }
            }
          }
        }
        container timezone {
          description
            "Configure time zone";
          leaf zone {
            type string;
          }
          leaf offset {
            type enumeration {
              enum "+";
              enum "-";
            }
          }
          leaf hours {
            type int8 {
              range "-23..23";
            }
          }
          leaf minutes {
            type int8 {
              range "0..59";
            }
          }
        }
      }
      uses config-logging-grouping;
      container aaa {
        description
          "Authentication, Authorization and Accounting.";
      }
      uses config-privilege-grouping;
      container login {
        description
          "Enable secure login checking";
        leaf delay {
          description
            "Set delay between successive fail login";
          type uint8 {
            range "1..10";
          }
        }
        container on-failure {
          description
            "Set options for failed login attempt";
          presence "true";
          container log {
            description
              "Generate syslogs on failure logins";
            presence "true";
            leaf every {
              description
                "Periodicity for logs generated";
              type uint16 {
                range "1..65535";
              }
            }
          }
        }
        container on-success {
          description
            "Set options for successful login attempt";
          presence "true";
          container log {
            description
              "Generate syslogs on successful logins";
            presence "true";
            leaf every {
              description
                "Periodicity for logs generated";
              type uint16 {
                range "1..65535";
              }
            }
          }
        }
      }
      container multilink {
        description
          "PPP multilink global configuration";
      }
      container mac-address-table {
        description
          "Configure the MAC address table";
        container evc-xconnect {
          description
            "All ethernet virtual connections xconnect";
          leaf l2pt-forward-all {
            description
              "Layer 2 Protocol Forward All";
            type empty;
          }
        }
        container limit {
          description
            "Enter parameters for mac limit feature";
          list bdomain {
            description
              "bdomain number for  mac limit feature";
            key "number";
            leaf number {
              type uint16 {
                range "1..4095";
              }
            }
            leaf action {
              description
                "Enter action";
              type enumeration {
                enum "warning";
                enum "limit";
                enum "shutdown";
              }
            }
            leaf maximum {
              description
                "Enter max allowed entries";
              type uint32 {
                range "0..16000";
              }
            }
          }
        }
        container learning {
          description
            "Enable a MAC table learning feature";
          list vlan {
            description
              "Layer 2 table learning per VLAN";
            key "id";
            leaf id {
              type uint16 {
                range "1..4094";
              }
            }
            leaf module {
              description
                "Layer 2 table learning per VLAN per module";
              type uint8 {
                range "1..9";
              }
            }
          }
        }
      }
      container redundancy {
        description
          "Enter redundancy mode";
        presence "true";
        leaf maintenance-mode {
          description
            "Enable/Disable maintenance mode ";
          type empty;
        }
        container main-cpu {
          description
            "Enter main-cpu mode";
          presence "true";
          container auto-sync {
            leaf running-config {
              type empty;
            }
            leaf config-register {
              type empty;
            }
            leaf bootvar {
              type empty;
            }
            leaf standard {
              type empty;
            }
          }
          container standby {
            description
              "Standby";
            container console {
              description
                "Console";
              leaf enable {
                description
                  "Enable";
                type empty;
              }
            }
            container initialization {
              description
                "Initialization";
              container delay {
                description
                  "Delay";
                leaf second {
                  description
                    "Delay value in seconds";
                  type uint16 {
                    range "30..1800";
                  }
                }
                leaf boot-only {
                  description
                    "Delay effective only on system boot";
                  type empty;
                }
              }
            }
          }
        }
        leaf mode {
          description
            "redundancy mode for this chassis";
          type enumeration {
            enum "rpr";
            enum "rpr-plus";
            enum "sso";
            enum "none";
          }
        }
        container policy {
          description
            "redundancy policy enforcement";
          container config-sync {
            description
              "config sync parameters";
            container bulk {
              description
                "bulk configuration mode";
              container prc {
                description
                  "prc policy enforcement";
                leaf reload {
                  description
                    "reload standby";
                  type boolean;
                }
              }
            }
            container lbl {
              description
                "line-by-line configuration mode";
              container prc {
                description
                  "prc policy enforcement";
                leaf reload {
                  description
                    "reload standby";
                  type boolean;
                }
              }
            }
          }
        }
        container timer {
          description
            "Select a timer to configure";
          leaf rpso {
            description
              "Delay value in seconds";
            type uint16 {
              range "120..1200";
            }
          }
        }
        container interchassis {
          description
            "Enter interchassis mode";
          list group {
            description
              "Enter the redundancy group number";
            key "group-number";
            leaf group-number {
              type uint64 {
                range "1..4294967295";
              }
            }
            container monitor {
              description
                "define the peer monitoring method";
              leaf peer {
                description
                  "the peer method";
                type empty;
              }
              leaf bfd {
                description
                  "set peer monitoring method to bfd";
                type empty;
              }
            }
            container member {
              description
                "specify a redundancy group member";
              leaf ip {
                description
                  "specify the redundancy group member using an ip address";
                type inet:ipv4-address;
              }
            }
            container backbone {
              description
                "specify a redundancy group member";
              container interface {
                uses ios-ifc:interface-grouping;
              }
            }
          }
        }
      }
      container scheduler {
        description
          "Scheduler parameters";
        container runtime {
          description
            "Process runtime controls";
          leaf netinput {
            description
              "Process-switching run time (in milliseconds)";
            type uint16 {
              range "100..40000";
            }
          }
        }
        container allocate {
          description
            "Guarantee CPU time for processes";
          leaf interrupt-time {
            type uint16 {
              range "400..60000";
            }
          }
          leaf process-time {
            type uint16 {
              range "100..4000";
            }
          }
        }
      }
      container epm {
        description
          "EPM Global Configuration Commands";
        leaf logging {
          description
            "Enable EPM logging";
          type empty;
        }
      }
      container spanning-tree {
        description
          "Spanning Tree Subsystem";
      }
      container subscriber {
        description
          "Subscriber configuration";
        leaf templating {
          description
            "Configure subscriber templating";
          type empty;
        }
      }
      container track {
        description
          "Object tracking configuration commands";
      }
      container dot1x {
        description
          "IEEE 802.1X Global Configuration Commands";
      }
      container fallback {
        description
          "Fallback configuration commands";
      }
      list parameter-map {
        description
          "parameter map";
        key "name";
        leaf name {
          description
            "cws_tunnel global parameter-map";
          type union {
            type string;
            type enumeration {
              enum "global";
              enum "gtp";
            }
          }
        }
        leaf type {
          description
            "parameter map type";
          type enumeration {
            enum "cws-tunnel";
            enum "inspect";
            enum "inspect-global";
            enum "webauth";
            enum "inspect-vrf";
            enum "inspect-zone";
            enum "regex";
            enum "authbypass";
          }
        }
        leaf parameter-map-type {
          description
            "type - web-auth, consent or both";
          type enumeration {
            enum "webauth";
            enum "authbypass";
          }
        }
      }
      container ppp {
        description
          "PPP global configuration";
      }
      container mac {
        description
          "Global MAC configuration subcommands";
        container address-table {
          description
            "Configure the MAC address table";
          container aging-time {
            description
              "Set MAC address table entry maximum age";
            leaf val {
              type uint32 {
                range "0 | 10..1000000";
              }
            }
            leaf routed-mac {
              description
                "Set RM Aging interval";
              type empty;
            }
            leaf vlan {
              description
                "VLAN Keyword";
              type uint16 {
                range "1..4094";
              }
            }
          }
          leaf control-packet-learn {
            description
              "Enable/Disable learning from Control Packets";
            type empty;
          }
          container learning {
            description
              "Enable MAC table learning feature";
            leaf vlan {
              description
                "<1-4094>;;VLAN id to enable MAC Address learning";
              type uint16 {
                range "1..4094";
              }
            }
          }
          container notification {
            description
              "Enable/Disable MAC Notification on the switch";
            container change {
              description
                "Enable/Disable MAC Notification feature on the switch";
              presence "true";
              leaf history-size {
                description
                  "Number of entries in history table (0-500)";
                type uint16 {
                  range "0..500";
                }
              }
              leaf interval {
                description
                  "Notification interval in seconds (0-2147483647)";
                type uint32 {
                  range "0..2147483647";
                }
              }
            }
            leaf mac-move {
              description
                "Enable Mac Move Notification";
              type empty;
            }
            container threshold {
              description
                "Configure L2 Table monitoring";
              presence "true";
              leaf interval {
                description
                  "<120-1000000> Interval time in seconds";
                type uint32 {
                  range "120..1000000";
                }
              }
              container limit {
                description
                  "Limit percentage";
                leaf percentage {
                  description
                    "Percentage (0-100)";
                  type uint8 {
                    range "0..100";
                  }
                }
                leaf interval {
                  description
                    "<120-1000000> Interval time in seconds";
                  type uint32 {
                    range "120..1000000";
                  }
                }
              }
            }
          }
          container static {
            description
              "Static MAC entry";
            leaf mac-address {
              description
                "xxxx.xxxx.xxxx 48 bit mac address";
              type ios-types:cisco-mac-address-type;
            }
            leaf vlan {
              description
                "<1-4094> VLAN id of mac address table (1-4094)";
              type uint16 {
                range "1..4094";
              }
            }
            leaf drop {
              description
                "drop frames";
              type empty;
            }
            leaf interface {
              description
                "Output interface exact long name";
              type string;
            }
          }
        }
      }
      container tacacs {
        description
          "TACACS server configuration command";
      }
      container tacacs-server {
        description
          "Modify TACACS query parameters";
      }
      container software {
        description
          "Configure software installation parameters";
        container auto-upgrade {
          description
            "Configure software auto upgrade parameters";
          leaf enable {
            description
              "Enable the auto upgrade installation feature";
            type empty;
          }
        }
      }
      container upgrade {
        description
          "Global upgrade configuration subcommands";
        container fpd {
          description
            "Configure field programmable devices upgrade options";
          leaf auto {
            description
              "Auto upgrade all FPD images";
            type empty;
          }
          leaf path {
            description
              "Set path to locate the FPD image package file for auto upgrade";
            type string;
          }
        }
      }
      container vtp {
        description
          "Configure global VTP state";
      }
      container xconnect;
      container fabric {
        description
          "Catalyst 6000 crossbar fabric configuration commands";
        container switching-mode {
          description
            "Switching mode settings";
          container allow {
            description
              "Allow settings";
            choice allow-choice {
              leaf bus-mode {
                description
                  "Allow switching in bus mode for modules";
                type empty;
              }
              container truncated {
                description
                  "Truncated switching mode";
                presence "true";
                leaf threshold {
                  description
                    "Number of SFM-capable modules for truncated switching mode. Switch applies the threshold only when the mode is disallowed. Switch ignores the threshold when the truncated mode is allowed";
                  type uint8 {
                    range "1..9";
                  }
                }
              }
            }
          }
          container force {
            description
              "Force modules to different switching modes";
            leaf bus-mode {
              description
                "Switching mode of service modules will be forced to bus-mode by powercycling it.";
              type empty;
            }
          }
        }
      }
      container port-channel {
        description
          "EtherChannel configuration";
      }
      container key {
        description
          "Key management";
      }
      container l2 {
        description
          "Layer 2 configuration";
        leaf router-id {
          description
            "Configure a layer 2 identifier";
          type inet:ipv4-address;
        }
      }
      container system {
        description
          "Set the system configuration";
      }
      container errdisable {
        description
          "Error disable";
        container detect {
          description
            "Error disable detection";
          container cause {
            description
              "Enable error disable detection for application";
            leaf all {
              description
                "Enable error detection on all cases";
              type empty;
            }
            leaf arp-inspection {
              description
                "Enable error detection for arp inspection";
              type empty;
            }
            leaf bpduguard {
              description
                "Enable error detection on bpdu-guard";
              type empty;
            }
            leaf dhcp-rate-limit {
              description
                "Enable error detection on dhcp-rate-limit";
              type empty;
            }
            leaf dtp-flap {
              description
                "Enable error detection on dtp-flapping";
              type empty;
            }
            leaf gbic-invalid {
              description
                "Enable error detection on gbic-invalid";
              type empty;
            }
            leaf inline-power {
              description
                "Enable error detection for inline-power";
              type empty;
            }
            leaf l2ptguard {
              description
                "Enable timer to recover from l2protocol-tunnel error disable state";
              type empty;
            }
            leaf link-flap {
              description
                "Enable error detection on linkstate-flapping";
              type empty;
            }
            leaf loopback {
              description
                "Enable error detection on loopback";
              type empty;
            }
            leaf mlacp-minlink {
              type empty;
            }
            leaf pagp-flap {
              description
                "Enable error detection on pagp-flapping";
              type empty;
            }
            leaf pppoe-ia-rate-limit {
              description
                "Enable error detection on PPPoE IA rate-limit";
              type empty;
            }
            container security-violation {
              description
                "Enable error detection on 802.1x-guard";
              container shutdown {
                description
                  "Specify error disable shutdown mode for 802.1x-guard";
                leaf vlan {
                  description
                    "Shutdown vlan on 802.1x-guard violation";
                  type empty;
                }
              }
            }
            leaf sfp-config-mismatch {
              description
                "Enable error detection on SFP config mismatch";
              type empty;
            }
            leaf small-frame {
              description
                "Enable error detection on small_frame";
              type empty;
            }
          }
        }
        container flap-setting {
          description
            "Error disable flap detection setting";
          container cause {
            description
              "Set error disable flap parameters for application";
            container dtp-flap {
              description
                "Set the variables related to detection of dtp flaps";
              leaf max-flaps {
                description
                  "maximum flaps allowed before setting to errdisable";
                type uint8 {
                  range "1..100";
                }
              }
              leaf time {
                description
                  "time period the flaps are counted";
                type uint8 {
                  range "1..120";
                }
              }
            }
            container link-flap {
              description
                "Set the variables related to detection of link flaps";
              leaf max-flaps {
                description
                  "maximum flaps allowed before setting to errdisable";
                type uint8 {
                  range "1..100";
                }
              }
              leaf time {
                description
                  "time period the flaps are counted";
                type uint8 {
                  range "1..120";
                }
              }
            }
            container pagp-flap {
              description
                "Set the variables related to detection of pagp flaps";
              leaf max-flaps {
                description
                  "maximum flaps allowed before setting to errdisable";
                type uint8 {
                  range "1..100";
                }
              }
              leaf time {
                description
                  "time period the flaps are counted";
                type uint8 {
                  range "1..120";
                }
              }
            }
          }
        }
        container recovery {
          description
            "Error disable recovery";
          container cause {
            description
              "Enable error disable recovery for application";
            leaf all {
              description
                "Enable timer to recover from all error causes";
              type empty;
            }
            leaf arp-inspection {
              description
                "Enable timer to recover from arp inspection error disable state";
              type empty;
            }
            leaf bpduguard {
              description
                "Enable timer to recover from BPDU Guard error";
              type empty;
            }
            leaf channel-misconfig {
              description
                "(STP)  Enable timer to recover from channel misconfig error";
              type empty;
            }
            leaf dhcp-rate-limit {
              description
                "Enable timer to recover from dhcp-rate-limit error";
              type empty;
            }
            leaf dtp-flap {
              description
                "Enable timer to recover from dtp-flap error";
              type empty;
            }
            leaf gbic-invalid {
              description
                "Enable timer to recover from invalid GBIC error";
              type empty;
            }
            leaf inline-power {
              description
                "Enable timer to recover from inline-power error";
              type empty;
            }
            leaf l2ptguard {
              description
                "Enable timer to recover from l2protocol-tunnel error disable state";
              type empty;
            }
            leaf link-flap {
              description
                "Enable timer to recover from link-flap error";
              type empty;
            }
            leaf link-monitor-failure {
              type empty;
            }
            leaf loopback {
              description
                "Enable timer to recover from loopback error";
              type empty;
            }
            leaf mac-limit {
              description
                "Enable timer to recover from mac limit disable state";
              type empty;
            }
            leaf mlacp-minlink {
              type empty;
            }
            container oam-remote-failure {
              presence "true";
              leaf critical-event {
                type empty;
              }
              leaf dying-gasp {
                type empty;
              }
              leaf link-fault {
                type empty;
              }
            }
            leaf pagp-flap {
              description
                "Enable timer to recover from pagp-flap error";
              type empty;
            }
            leaf port-mode-failure {
              description
                "Enable timer to recover from port mode change failure";
              type empty;
            }
            leaf pppoe-ia-rate-limit {
              description
                "Enable timer to recover from PPPoE IA rate-limit error";
              type empty;
            }
            leaf psp {
              type empty;
            }
            leaf psecure-violation {
              description
                "Enable timer to recover from psecure violation error";
              type empty;
            }
            leaf security-violation {
              description
                "Enable timer to recover from 802.1x violation error";
              type empty;
            }
            leaf sfp-config-mismatch {
              description
                "Enable timer to recover from SFP config mismatch error";
              type empty;
            }
            leaf small-frame {
              description
                "Enable timer to recover from small frame error";
              type empty;
            }
            leaf storm-control {
              description
                "Enable timer to recover from storm-control error";
              type empty;
            }
            leaf udld {
              description
                "Enable timer to recover from udld error";
              type empty;
            }
            leaf unicast-flood {
              type empty;
            }
            leaf vmps {
              description
                "Enable timer to recover from vmps shutdown error";
              type empty;
            }
          }
          leaf interval {
            description
              "Error disable recovery timer value";
            type uint32 {
              range "30..86400";
            }
          }
        }
      }
      container identity {
        description
          "Identity Configuration Commands";
        container profile {
          description
            "Create an Identity profile";
          leaf dot1x {
            description
              "Service type for 802.1x";
            type empty;
          }
          leaf default {
            description
              "Service type default";
            type empty;
          }
        }
      }
      container monitor {
        description
          "Monitoring different system events";
        container event-trace {
          description
            "Tracing of system events";
        }
        list session {
          description
            "Configure a SPAN session";
          key "id";
          leaf id {
            type uint8 {
              range "1..66";
            }
          }
          container destination {
            description
              "SPAN destination interface or VLAN";
            list interface {
              description
                "SPAN destination interface";
              key "name";
              leaf name {
                description
                  "Interface Name";
                type string;
              }
              leaf encapsulation {
                description
                  "Set encapsulation for destination interface";
                type enumeration {
                  enum "dot1q";
                  enum "isl";
                  enum "replicate";
                }
              }
              leaf ingress {
                description
                  "Enable ingress traffic forwarding";
                type empty;
              }
              leaf ingress-encap {
                when "../ingress" {
                  tailf:xpath-root 3;
                }
                type enumeration {
                  enum "dot1q";
                  enum "isl";
                  enum "untagged";
                }
              }
              leaf vlan {
                description
                  "Set default VLAN for untagged ingress traffic";
                when "../ingress" {
                  tailf:xpath-root 3;
                }
                type uint16 {
                  range "1..4094";
                }
              }
            }
            container remote {
              description
                "SPAN destination Remote";
              leaf vlan {
                description
                  "Remote SPAN destination RSPAN VLAN";
                type uint16 {
                  range "1006..4094";
                }
              }
            }
          }
          container filter {
            description
              "SPAN filter VLAN";
            container packet-type {
              leaf status {
                type enumeration {
                  enum "good";
                  enum "bad";
                }
              }
              leaf direction {
                type enumeration {
                  enum "rx";
                  enum "tx";
                }
              }
            }
            container ip {
              description
                "Specify IP Access control rules";
              container access-group {
                description
                  "Specify access control group";
                leaf acl-name {
                  description
                    "Access-list name";
                  type string;
                }
              }
            }
          }
          container source {
            description
              "SPAN source interface, VLAN ";
            list interface {
              description
                "SPAN source interface";
              key "name";
              leaf name {
                description
                  "Interface Name";
                type string;
              }
              leaf direction {
                type enumeration {
                  enum "both";
                  enum "rx";
                  enum "tx";
                }
              }
            }
            container vlan {
              description
                "SPAN source VLAN";
              leaf vlan {
                type uint16 {
                  range "1..4094";
                }
              }
              leaf direction {
                type enumeration {
                  enum "both";
                  enum "rx";
                  enum "tx";
                }
              }
            }
            container remote {
              description
                "SPAN source Remote";
              leaf vlan {
                description
                  "Remote SPAN source RSPAN VLAN <1-1001>|<1006-4094>";
                type uint16 {
                  range "1..1001 | 1006..4094";
                }
              }
            }
          }
        }
      }
      list tftp-server {
        description
          "Provide TFTP service for netload requests";
        key "name";
        leaf name {
          type string;
        }
      }
      container radius-server {
        description
          "Modify RADIUS query parameters";
      }
      container radius {
        description
          "RADIUS server configuration command";
      }
      container zone {
        description
          "FW with zoning";
      }
      container zone-pair {
        description
          "Zone pair command";
      }
      list alarm-contact {
        key "name";
        leaf name {
          type uint8 {
            range "1..4";
          }
        }
        leaf description {
          type string {
            length "1..80";
          }
        }
        leaf severity {
          type enumeration {
            enum "critical";
            enum "major";
            enum "minor";
          }
        }
        leaf trigger {
          type enumeration {
            enum "open";
            enum "closed";
          }
        }
      }
      container ethernet {
        description
          "Ethernet configuration";
      }
      container access-list {
        description
          "Add an access list entry";
      }
      container bridge-domain {
        description
          "Bridge-domain global configuration commands";
      }
      container crypto {
        description
          "Encryption module";
      }
      container cts {
        description
          "Configures Cisco TrustSec";
      }
      container bfd-template {
        description
          "BFD-template";
      }
      container pfr {
        description
          "Performance Routing configuration submodes";
      }
      list pfr-map {
        description
          "Create pfr-map and enter pfr-map command mode";
        key "pfr-tg";
        leaf pfr-tg {
          description
            "pfr-map tag";
          type string;
        }
      }
      container facility-alarm {
        description
          "Configure facility alarms";
        leaf severity {
          type enumeration {
            enum "critical";
          }
        }
        leaf exceed-action {
          description
            "Behavior on critical threshold exceed";
          type enumeration {
            enum "shutdown";
          }
        }
      }
      container setup {
        description
          "Configure setup options";
      }
      container tod-clock {
        tailf:display-when "not(../../ncs:module) or boolean(/ncs:devices/ncs:device[ncs:name=current()/../../ncs:name]/capability/feature='ios-features:tod-clock')";
        description
          "Tod clock config commands";
        container input-source {
          description
            "Synchronization Input Source";
          leaf priority {
            type uint8 {
              range "1..250";
            }
          }
          container ptp {
            leaf domain {
              type uint8;
            }
          }
        }
      }
      container network-clock {
        description
          "Network clock config commands";
        container synchronization {
          description
            "Network clock synchronization selection process";
          leaf automatic {
            description
              "ITU-T G.781/Telcordia standard based";
            type empty;
          }
          leaf mode {
            description
              "synchronization networking mode";
            type enumeration {
              enum "QL-enabled";
            }
          }
        }
        container wait-to-restore {
          description
            "Wait-to-Restore timer";
          leaf time {
            description
              "Wait-to-Restore time";
            type uint32 {
              range "0..86400";
            }
          }
          leaf global {
            description
              "Global";
            type empty;
          }
        }
        container input-source {
          description
            "Synchronization Input Source";
          leaf priority {
            type uint8 {
              range "1..250";
            }
          }
          container interface {
            uses ios-ifc:interface-grouping;
          }
          container ptp {
            leaf domain {
              type uint8;
            }
          }
        }
      }
      container l2vpn {
        description
          "Layer2 VPN commands";
      }
      container l2vpn-config;
      container l3vpn {
        description
          "l3vpn encapsulation ip commands";
      }
      container mpls {
        description
          "Configure MPLS parameters";
      }
      container router;
      container service-chain {
        description
          "Service Chain mode";
      }
      container performance {
        description
          "Global Performance monitor configuration";
      }
      container otv {
        description
          "Configure OTV information";
      }
      container remote-management {
        description
          "Enable the remote managment";
        leaf dmi {
          description
            "data-model-interface";
          type empty;
        }
        leaf restful-api {
          description
            "RESTful API";
          type boolean;
        }
      }
      list virtual-service {
        description
          "Configure virtual service";
        key "name";
        leaf name {
          type string {
            length "1..63";
          }
        }
      }
      container snmp {
        description
          "Modify SNMP interface parameters";
      }
      container snmp-server {
        description
          "Modify SNMP engine parameters";
      }
      container segment-routing {
        description
          "Enter Segment Routing Mode";
      }
      uses config-license-grouping;
      leaf disable-eadi {
        type empty;
      }
      container memory-size {
        tailf:display-when "not(../../ncs:module) or boolean(/ncs:devices/ncs:device[ncs:name=current()/../../ncs:name]/capability/feature='ios-features:mem-size')";
        description
          "Adjust memory size by percentage";
        leaf iomem {
          description
            "I/O memory";
          type uint8 {
            range "5..25";
          }
        }
      }
      container transceiver {
        tailf:display-when "not(../../ncs:module) or boolean(/ncs:devices/ncs:device[ncs:name=current()/../../ncs:name]/capability/feature='ios-features:transceiver')";
        description
          "Select from transceiver configuration commands";
        container type {
          description
            "type keyword";
          container all {
            container monitoring {
              description
                "Enable/disable monitoring";
              presence "true";
              leaf interval {
                description
                  "Set interval for monitoring";
                type uint16 {
                  range "300..3600";
                }
              }
            }
          }
        }
      }
      container service-insertion {
        description
          "Service Insertion mode";
      }
      container udld {
        description
          "Configure global UDLD setting";
      }
      container wireless {
        description
          "Configure wireless parameters";
        leaf mdns-bridging {
          description
            "Enable Ethernet mDNS Support";
          type boolean;
        }
      }
      container qos {
        description
          "Global QoS configuration commands";
        presence "true";
      }
      list time-range {
        description
          "Define time range entries";
        key "word";
        leaf word {
          type string;
        }
        container absolute {
          description
            "absolute time and date";
          container start {
            description
              "starting time and date";
            leaf start-time {
              description
                "Starting time";
              type string;
            }
            leaf day-of-month {
              description
                "<1-31>  Day of the month";
              type uint8;
            }
            leaf month {
              description
                "Month of the year [eg: Jan for January, Jun for June]";
              type string;
            }
            leaf year {
              description
                "Year";
              type uint16 {
                range "1993..2035";
              }
            }
          }
        }
      }
      container device-tracking {
        description
          "Device tracking configuration commands";
      }
      container fhrp {
        description
          "Configure First Hop Redundancy Protocols";
        container version {
          description
            "Configure which FHRP version is allowed to run";
          leaf vrrp {
            description
              "Configure Virtual Router Rendundancy Protocol";
            type enumeration {
              enum "v2";
              enum "v3";
            }
          }
        }
      }
      container metadata {
        description
          "Metadata Application";
        container flow {
          description
            "Enable Metadata Flow Handling";
          presence "true";
          leaf transmit {
            description
              "Enable Metadata Flow Transmit ";
            type empty;
          }
        }
      }
      container profile {
        description
          "MSP Profile";
        leaf flow {
          description
            "MSP Profile Flow";
          type empty;
        }
      }
      container alias {
        description
          "Create command alias";
        container exec {
          description
            "Exec mode";
          leaf alias-name {
            type string;
          }
          leaf new-alias-name {
            type string;
          }
        }
      }
      uses config-line-grouping;
      container ntp {
        description
          "Configure NTP";
      }
      container wsma {
        description
          "Configure Web Services Management Agents";
      }
      container event {
        description
          "Event related configuration commands";
      }
      container template {
        description
          "template";
      }

      grouping service-timestamp-show-timezone-and-year {
        leaf show-timezone {
          description
            "Add time zone information to timestamp";
          type empty;
        }
        leaf year {
          description
            "Include year in timestamp";
          type empty;
        }
      }

      grouping service-timestamp-msec-and-year {
        leaf msec {
          description
            "Include milliseconds in timestamp";
          type empty;
        }
        leaf year {
          description
            "Include year in timestamp";
          type empty;
        }
      }

      grouping service-timestamp-msec-and-show-timezone {
        leaf msec {
          description
            "Include milliseconds in timestamp";
          type empty;
        }
        leaf show-timezone {
          description
            "Add time zone information to timestamp";
          type empty;
        }
      }

      grouping service-timestamp-local-time-and-year {
        leaf localtime {
          description
            "Use local time zone for timestamps";
          type empty;
        }
        leaf year {
          description
            "Include year in timestamp";
          type empty;
        }
      }

      grouping service-timestamp-local-time-and-show-timezone {
        leaf localtime {
          description
            "Use local time zone for timestamps";
          type empty;
        }
        leaf show-timezone {
          description
            "Add time zone information to timestamp";
          type empty;
        }
      }

      grouping service-timestamp-local-time-and-msec {
        leaf localtime {
          description
            "Use local time zone for timestamps";
          type empty;
        }
        leaf msec {
          description
            "Include milliseconds in timestamp";
          type empty;
        }
      }

      grouping process-rising-grouping {
        container rising {
          description
            "rising threshold";
          list cpu-range {
            key "cpu-range";
            leaf cpu-range {
              type uint8 {
                range "1..100";
              }
            }
            container interval {
              description
                "observation interval";
              list cpu-range {
                key "cpu-range";
                leaf cpu-range {
                  type uint32 {
                    range "5..86400";
                  }
                }
                container falling {
                  description
                    "falling threshold";
                  list cpu-range {
                    key "cpu-range";
                    leaf cpu-range {
                      type uint8 {
                        range "1..100";
                      }
                    }
                    leaf interval {
                      description
                        "observation interval";
                      type uint32 {
                        range "5..86400";
                      }
                    }
                  }
                }
              }
            }
          }
        }
      }
      container process {
        description
          "Configure process";
        container cpu {
          description
            "Configure cpu parameters";
          container threshold {
            description
              "cpu threshold parameters";
            container type {
              description
                "cpu threshold type";
              container interrupt {
                description
                  "interrupt level utilization";
                uses process-rising-grouping;
              }
              container process {
                description
                  "process level utilization";
                uses process-rising-grouping;
              }
              container total {
                description
                  "total cpu utilization";
                uses process-rising-grouping;
              }
            }
          }
        }
      }
      container exception {
        description
          "help";
        container crashinfo {
          description
            "Crashinfo collection";
          presence "true";
          leaf buffersize {
            description
              "buffer size in Kbytes 256K or less (default is 32K)";
            type uint16 {
              range "32..256";
            }
          }
        }
      }
      container iox {
        description
          "Configure IOx services";
        presence "true";
      }
    }
  }
  augment "/ncs:devices/ncs:device/ncs:live-status" {
    container native {
      tailf:ncs-device-type "netconf";
      tailf:display-when "not(../../ncs:module) or ../../ncs:module[ncs:name='Cisco-IOS-XE-native'] or (../../ncs:live-status-protocol[not(ncs:capability)]) or (../../ncs:live-status-protocol/ncs:capability/ncs:module[.='Cisco-IOS-XE-native'])";
      container default {
        description
          "Set a command to its defaults";
        container crypto {
          description
            "Encryption module";
          container ikev2 {
            description
              "Configure IKEv2 Options";
            leaf proposal {
              description
                "Define IKEV2 proposals";
              type empty;
            }
            leaf policy {
              description
                "Define IKEV2 policies";
              type empty;
            }
          }
        }
      }
      container bfd {
        description
          "BFD configuration commands";
      }
      leaf version {
        description
          "Version";
        type string;
      }
      leaf boot-start-marker {
        type empty;
      }
      container boot {
        description
          "Modify boot system parameters";
        container system {
          description
            "System Image";
          leaf tftp-path {
            description
              "Example: 192.x.x.x/<path to image>";
            type string;
          }
          leaf tftp {
            description
              "Example 192.168.x.x/<image-path>";
            type string;
          }
          container bootfile {
            description
              "WORD - boot filename";
            list filename-list {
              key "filename";
              leaf filename {
                description
                  "WORD - TFTP filename or URL";
                type string;
              }
            }
          }
          container flash {
            description
              "flash - Boot from flash memory";
            list flash-list {
              key "flash-leaf";
              leaf flash-leaf {
                type string;
              }
            }
          }
        }
      }
      leaf boot-end-marker {
        type empty;
      }
      leaf captive-portal-bypass {
        description
          "Enable Captive portal bypass for apple devices";
        type empty;
      }
      container memory {
        description
          "Configure memory management";
        container statistics {
          description
            "Configure statistics history table";
          container history {
            description
              "Configure statistics history table";
            leaf table {
              description
                "Configure statistics history table";
              type uint8 {
                range "12..72";
              }
            }
          }
        }
        container chunk {
          description
            "chunk related configuration";
          container siblings {
            description
              "chunk siblings related configuration";
            leaf threshold {
              description
                "Default is platform dependent";
              type uint32 {
                range "2..4294967295";
              }
            }
          }
        }
        container free {
          description
            "free memory low water mark";
          container low-watermark {
            description
              "low water mark for notifications";
            leaf IO {
              description
                "low water mark of memory in KB";
              type uint32 {
                range "1..3994575";
              }
            }
            leaf processor {
              description
                "low water mark of memory in KB";
              type uint32 {
                range "1..3994575";
              }
            }
          }
        }
        leaf lite {
          description
            "Enable/disable memory lite";
          type empty;
        }
        container reserve {
          description
            "reserve memory";
          container critical {
            description
              "Reserve Critical Memory";
            presence "true";
            leaf memory-range {
              description
                "total amount of memory to be reserved in kilobytes";
              type uint32 {
                range "1..4294967295";
              }
            }
          }
        }
        container sanity {
          description
            "Enable memory sanity";
          presence "true";
          leaf all {
            description
              "Enable memory sanity all";
            type empty;
          }
          leaf buffer {
            description
              "Enable memory sanity buffer";
            type empty;
          }
          leaf queue {
            type empty;
          }
        }
      }
      container location {
        description
          "Global location configuration commands";
        container civic-location {
          description
            "Civic location information";
          list identifier {
            description
              "Set the identifier";
            key "identifier";
            leaf identifier {
              type string;
            }
            leaf building {
              description
                "Building information";
              type string;
            }
            leaf floor {
              description
                "Floor number";
              type string;
            }
            leaf landmark {
              description
                "Landmark";
              type string;
            }
            leaf name {
              description
                "Resident name";
              type string;
            }
            leaf number {
              description
                "Street number";
              type string;
            }
          }
        }
      }
      container call-home {
        description
          "Enter call-home configuration mode";
        presence "true";
      }
      container hw-module {
        description
          "Control of individual components in the system";
        container uplink {
          description
            "Uplink control";
          leaf select {
            description
              "Select uplink interface";
            type string;
          }
          leaf mode {
            description
              "Uplink mode";
            type enumeration {
              enum "shared-backplane";
            }
          }
        }
        leaf sm {
          type uint8;
        }
        leaf pvdm {
          type string;
        }
      }
      container cisp {
        description
          "Set CISP parameters";
        leaf enable {
          description
            "Enable CISP";
          type empty;
        }
      }
      container module {
        description
          "Module";
      }
      list domain {
        description
          "Domain Configuration Commands";
        key "name";
        leaf name {
          type string;
        }
        list vrf {
          description
            "Specify vrf for domain";
          key "name";
          leaf name {
            type string;
          }
          container border {
            description
              "Enter border router configuration submode";
            container source-interface {
              description
                "Source Interface for border";
              leaf Loopback {
                description
                  "Loopback interface";
                type uint32;
              }
            }
            leaf master {
              description
                "Specify IP address of Domain master controller";
              type union {
                type inet:ipv4-address;
                type enumeration {
                  enum "local";
                }
              }
            }
            container password {
              description
                "MD5 password to be used with MC";
              leaf encryption {
                type enumeration {
                  enum "0";
                  enum "7";
                }
              }
              leaf clear-key {
                type string;
              }
            }
          }
          container master {
            description
              "Enter master controller configuration submode";
            choice master-type {
              case branch {
                leaf branch {
                  description
                    "Set master type as branch hub";
                  type empty;
                }
              }
              case hub {
                leaf hub {
                  description
                    "Set master type as hub";
                  type empty;
                }
              }
              case transit {
                leaf transit {
                  description
                    "Set master type as transit";
                  type empty;
                }
              }
            }
            container advanced {
              description
                "Advanced configuration submode";
              leaf byte-loss-threshold {
                description
                  "Specify minimum byte loss calculation threshold";
                type uint16 {
                  range "0..5600";
                }
              }
              leaf channel-unreachable-timer {
                description
                  "Unreach interval detection";
                type uint16 {
                  range "1..65535";
                }
              }
              leaf load-sharing {
                description
                  "Enable load-sharing";
                type empty;
              }
              leaf minimum-mask-length {
                description
                  "Specify minimum mask length";
                type uint8 {
                  range "1..32";
                }
              }
              leaf mitigation-mode {
                description
                  "Enable brownout detection in domain";
                type enumeration {
                  enum "aggressive";
                }
              }
              leaf packet-loss-threshold {
                description
                  "Specify minimum packet loss calculation threshold";
                type uint8 {
                  range "1..100";
                }
              }
              container smart-probes {
                description
                  "Smart probes configuration";
                leaf destination-port {
                  description
                    "Specify smart probes destination port number";
                  type uint16 {
                    range "1..65535";
                  }
                }
                leaf source-port {
                  description
                    "Specify smart probes source port number";
                  type uint16 {
                    range "1..65535";
                  }
                }
              }
              container syslog {
                description
                  "Specify syslog minimim time between tca";
                leaf tca-time-min {
                  description
                    "Specify time between syslog tcas in seconds";
                  type uint32 {
                    range "30..36000";
                  }
                }
              }
              container tcp {
                description
                  "Specify tcp port numbers for mc-br communication";
                leaf mc-port {
                  description
                    "Specify tcp MC self port for mc-br communication";
                  type uint16 {
                    range "1..65535";
                  }
                }
              }
              leaf threshold-variance {
                description
                  "Policy decision Threshold variance";
                type uint8 {
                  range "0..100";
                }
              }
              container traffic-class-ageout-timer {
                description
                  "Traffic-class DB age timer";
                leaf interval {
                  description
                    "Specify new timer interval value mins/hours";
                  type uint16 {
                    range "5..65535";
                  }
                }
                leaf interval-unit {
                  type enumeration {
                    enum "hours";
                    enum "minutes";
                  }
                }
              }
              leaf transit-site-affinity {
                description
                  "Enable Transit Site Affinity";
                type empty;
              }
            }
            container collector {
              description
                "NMS/v9 collector configuration";
              leaf ip {
                type inet:ipv4-address;
              }
              leaf port {
                description
                  "Specify collector port number";
                type uint16;
              }
            }
            container enterprise-prefix {
              description
                "Enterprise prefix configuration";
              leaf prefix-list {
                description
                  "Specify prefix-list with static site targets";
                type string;
              }
            }
            container load-balance {
              description
                "load balance non-policy traffic";
              presence "true";
              leaf advanced {
                description
                  "Load balancing configuration mode";
                type empty;
              }
            }
            container password {
              description
                "MD5 password to be used with BRs";
              leaf encryption {
                type enumeration {
                  enum "0";
                  enum "7";
                }
              }
              leaf clear-key {
                type string;
              }
            }
            container site-prefixes {
              description
                "site-prefixes configuration";
              leaf prefix-list {
                description
                  "Specify prefix-list with static site targets";
                type string;
              }
            }
            container source-interface {
              description
                "Source Interface for master controller";
              leaf Loopback {
                description
                  "Loopback interface";
                type uint32;
              }
            }
            list class {
              description
                "Create domain class and enter domain class command mode";
              key "name sequence";
              leaf name {
                type string;
              }
              leaf sequence {
                description
                  "Set the Sequence for the class";
                type uint16;
              }
              container match {
                description
                  "Specify the applications the policy applies to";
                list dscp {
                  description
                    "specify DSCP";
                  key "value";
                  leaf value {
                    type ios-types:dscp-type;
                  }
                  leaf policy {
                    description
                      "Specify the policy (user defined/predefined)";
                    type enumeration {
                      enum "best-effort";
                      enum "bulk-data";
                      enum "custom";
                      enum "low-latency-data";
                      enum "real-time-video";
                      enum "scavenger";
                      enum "voice";
                    }
                  }
                }
              }
              container path-preference {
                description
                  "Specify the preferred provider";
                leaf-list primary {
                  description
                    "Primary service provider";
                  ordered-by user;
                  type string;
                }
                leaf-list fallback {
                  description
                    "Specify the fallback provider";
                  ordered-by user;
                  type string;
                }
              }
            }
            leaf hub-ip {
              type inet:ipv4-address;
            }
          }
        }
      }
      uses live_ncs_config-parser-grouping;
      container service {
        description
          "Modify use of network based services";
        leaf internal {
          description
            "Enable/Disable Internal commands";
          type empty;
        }
        container pad-conf {
          leaf pad {
            description
              "Enable PAD commands";
            type boolean;
          }
        }
        container pad {
          description
            "Enable PAD commands";
          presence "true";
          leaf cmns {
            description
              "Enable PAD over CMNS connections";
            type empty;
          }
          leaf from-xot {
            description
              "Accept XOT to PAD connections";
            type empty;
          }
          leaf to-xot {
            description
              "Allow outgoing PAD over XOT connections";
            type empty;
          }
        }
        leaf password-encryption {
          description
            "Encrypt system passwords";
          type empty;
        }
        leaf password-recovery {
          description
            "Enable password recovery";
          type boolean;
        }
        container timestamps {
          description
            "Timestamp debug/log messages";
          presence "true";
          container debug {
            description
              "Timestamp debug messages";
            container datetime {
              description
                "Timestamp with date and time";
              presence "true";
              container localtime {
                description
                  "Use local time zone for timestamps";
                presence "true";
                container msec {
                  description
                    "Include milliseconds in timestamp";
                  presence "true";
                  uses service-timestamp-show-timezone-and-year;
                }
                container show-timezone {
                  description
                    "Add time zone information to timestamp";
                  presence "true";
                  uses service-timestamp-msec-and-year;
                }
                container year {
                  description
                    "Include year in timestamp";
                  presence "true";
                  uses service-timestamp-msec-and-show-timezone;
                }
              }
              container msec {
                description
                  "Include milliseconds in timestamp";
                presence "true";
                container localtime {
                  description
                    "Use local time zone for timestamps";
                  presence "true";
                  uses service-timestamp-show-timezone-and-year;
                }
                container show-timezone {
                  description
                    "Add time zone information to timestamp";
                  presence "true";
                  uses service-timestamp-local-time-and-year;
                }
                container year {
                  description
                    "Include year in timestamp";
                  presence "true";
                  uses service-timestamp-local-time-and-show-timezone;
                }
              }
              container show-timezone {
                description
                  "Add time zone information to timestamp";
                presence "true";
                container localtime {
                  description
                    "Use local time zone for timestamps";
                  presence "true";
                  uses service-timestamp-msec-and-year;
                }
                container msec {
                  description
                    "Include milliseconds in timestamp";
                  presence "true";
                  uses service-timestamp-local-time-and-year;
                }
                container year {
                  description
                    "Include year in timestamp";
                  presence "true";
                  uses service-timestamp-local-time-and-msec;
                }
              }
              container year {
                description
                  "Include year in timestamp";
                presence "true";
                container localtime {
                  description
                    "Use local time zone for timestamps";
                  presence "true";
                  uses service-timestamp-msec-and-show-timezone;
                }
                container msec {
                  description
                    "Include milliseconds in timestamp";
                  presence "true";
                  uses service-timestamp-local-time-and-show-timezone;
                }
                container show-timezone {
                  description
                    "Add time zone information to timestamp";
                  presence "true";
                  uses service-timestamp-local-time-and-msec;
                }
              }
            }
            leaf uptime {
              description
                "Timestamp with system uptime";
              type empty;
            }
          }
          container log {
            description
              "Timestamp log messages";
            container datetime {
              description
                "Timestamp with date and time";
              presence "true";
              leaf msec {
                description
                  "Include milliseconds in timestamp";
                type empty;
              }
              leaf localtime {
                description
                  "Use local time zone for timestamps";
                type empty;
              }
              leaf show-timezone {
                description
                  "Add time zone information to timestamp";
                type empty;
              }
              leaf year {
                description
                  "Include year in timestamp";
                type empty;
              }
            }
            leaf uptime {
              description
                "Timestamp with system uptime";
              type empty;
            }
          }
        }
        container alignment {
          description
            "Control alignment correction and logging";
          leaf detection {
            description
              "Enable detection of alignment issues";
            type empty;
          }
          leaf logging {
            description
              "Enable logging of alignment issues";
            type empty;
          }
        }
        leaf call-home {
          description
            "Enable call-home service";
          type empty;
        }
        leaf compress-config {
          description
            "Compress the configuration file";
          type empty;
        }
        leaf config {
          description
            "TFTP load config files";
          type empty;
        }
        container counters {
          description
            "Control aging of interface counters";
          container max {
            description
              "Maximum counter aging threshold";
            leaf age {
              description
                "Aging threshold";
              type uint8 {
                range "0..60";
              }
            }
          }
        }
        leaf dhcp {
          description
            "Enable DHCP server and relay agent";
          type empty;
        }
        leaf disable-ip-fast-frag {
          description
            "Disable IP particle-based fast fragmentation";
          type empty;
        }
        leaf exec-callback {
          description
            "Enable exec callback";
          type empty;
        }
        leaf exec-wait {
          description
            "Delay EXEC startup on noisy lines";
          type empty;
        }
        leaf finger {
          description
            "Allow responses to finger requests";
          type empty;
        }
        container heartbeat {
          description
            "Enable heartbeat processing";
          leaf fatal-count {
            description
              "Set heartbeat fatal count";
            type uint8 {
              range "1..60";
            }
          }
          leaf interrupt-interval {
            description
              "Set heartbeat interrupt test interval";
            type uint8 {
              range "0..60";
            }
          }
          leaf interrupt-max {
            description
              "Set maximum message count from interrupt test";
            type uint8 {
              range "0..60";
            }
          }
          leaf transmit-interval {
            description
              "Set heartbeat transmit interval";
            type uint8 {
              range "1..30";
            }
          }
          leaf warning-timeout {
            description
              "Set heartbeat warning timeout interval";
            type uint8 {
              range "5..60";
            }
          }
        }
        leaf hide-telnet-addresses {
          description
            "Hide destination addresses in telnet command";
          type empty;
        }
        leaf linenumber {
          description
            "enable line number banner for each exec";
          type empty;
        }
        leaf log-hidden {
          description
            "Enable syslog msgs for hidden/internal commands";
          type empty;
        }
        leaf nagle {
          description
            "Enable Nagle's congestion control algorithm";
          type empty;
        }
        leaf old-slip-prompts {
          description
            "Allow old scripts to operate with slip/ppp";
          type empty;
        }
        container prompt {
          description
            "Enable mode specific prompt";
          leaf config {
            description
              "Enable configuration mode prompt";
            type empty;
          }
        }
        leaf pt-vty-logging {
          description
            "Log significant VTY-Async events";
          type empty;
        }
        leaf sequence-numbers {
          description
            "Stamp logger messages with a sequence number";
          type empty;
        }
        leaf slave-log {
          description
            "Enable log capability of slave IPs";
          type empty;
        }
        leaf tcp-keepalives-in {
          description
            "Generate keepalives on idle incoming network connections";
          type empty;
        }
        leaf tcp-keepalives-out {
          description
            "Generate keepalives on idle outgoing network connections";
          type empty;
        }
        leaf telnet-zeroidle {
          description
            "Set TCP window 0 when connection is idle";
          type empty;
        }
        leaf tcp-small-servers {
          description
            "Enable small TCP servers (e.g., ECHO)";
          type empty;
        }
        leaf udp-small-servers {
          description
            "Enable small UDP servers (e.g., ECHO)";
          type empty;
        }
        leaf unsupported-transceiver {
          description
            "Enable support for third-party transceivers";
          type empty;
        }
      }
      container platform {
        description
          "platform specific configuration";
      }
      leaf hostname {
        description
          "Set system's network name";
        type string;
      }
      container enable {
        description
          "Modify enable password parameters";
        container password {
          description
            "Assign the privileged level password (MAX of 25 characters)";
          uses live_ncs_password-07-grouping;
        }
        leaf last-resort {
          description
            "Define enable action if no TACACS servers respond";
          type enumeration {
            enum "password";
            enum "succeed";
          }
        }
        container secret {
          description
            "Assign the privileged level secret";
          leaf level {
            description
              "Set exec level password";
            type uint8;
          }
          leaf type {
            type enumeration {
              enum "0";
              enum "4";
              enum "5";
            }
          }
          leaf secret {
            type string;
          }
        }
        leaf use-tacacs {
          description
            "Use TACACS to check enable passwords";
          type empty;
        }
      }
      container password {
        description
          "Configure encryption password (key)";
        container encryption {
          description
            "Encrypt system passwords";
          leaf aes {
            description
              "Enable stronger (AES) password encryption";
            type empty;
          }
        }
      }
      container eap {
        description
          "Configure EAP authenticator parameters";
        list profile {
          description
            "EAP authenticator profile configuration";
          key "name";
          leaf name {
            description
              "WORD;;EAP authenticator profile name";
            type string;
          }
          container method {
            description
              "Add an allowed method";
            leaf fast {
              description
                "EAP-FAST method allowed";
              type empty;
            }
            leaf gtc {
              description
                "EAP-GTC method allowed";
              type empty;
            }
            leaf leap {
              description
                "EAP-LEAP method allowed";
              type empty;
            }
            leaf mschapv2 {
              description
                "EAP-MSCHAPV2 method allowed";
              type empty;
            }
            leaf peap {
              description
                "EAP-PEAP method allowed";
              type empty;
            }
            leaf md5 {
              description
                "EAP-MD5 method allowed";
              type empty;
            }
            leaf tls {
              description
                "EAP-TLS method allowed";
              type empty;
            }
          }
          leaf pki-trustpoint {
            description
              "Set the default pki trustpoint";
            type string;
          }
        }
      }
      container archive {
        description
          "Archive the configuration";
        container log {
          description
            "Logging commands";
          container config {
            description
              "Logging changes to the running configuration";
            leaf hidekeys {
              description
                "suppress output (e.g. passwords) when displaying logged commands";
              type empty;
            }
            container logging {
              description
                "Modify config logging parameters";
              leaf enable {
                description
                  "Enable the config logger";
                type empty;
              }
              leaf size {
                description
                  "Maximum number of logged commands that will be kept by the config log";
                type uint16 {
                  range "1..1000";
                }
              }
              container persistent {
                description
                  "Log configuration persistent";
                presence "true";
                leaf auto {
                  description
                    "Log configuration commands automatically";
                  type empty;
                }
                leaf reload {
                  description
                    "Apply persisted commands on reload";
                  type empty;
                }
              }
            }
            container notify {
              description
                "Send logged commands to target applications";
              container syslog {
                description
                  "Send logged commands as syslog messages";
                presence "true";
                leaf contenttype {
                  description
                    "Type of the syslog message content";
                  type enumeration {
                    enum "plaintext";
                    enum "xml";
                  }
                }
              }
            }
          }
        }
        leaf path {
          description
            "path for backups";
          type union {
            type enumeration {
              enum "bootflash:";
              enum "flash:";
              enum "ftp:";
              enum "harddisk:";
              enum "http:";
              enum "https:";
              enum "pram:";
              enum "rcp:";
              enum "scp:";
              enum "tftp:";
            }
            type string;
          }
        }
        leaf maximum {
          description
            "maximum number of backup copies";
          type uint8 {
            range "1..14";
          }
        }
        leaf write-memory {
          description
            "Enable automatic backup generation during write memory";
          type empty;
        }
        leaf time-period {
          description
            "Period of time in minutes to automatically archive the running-config";
          type uint32 {
            range "1..525600";
          }
        }
      }
      list username {
        description
          "Establish User Name Authentication";
        key "name";
        leaf name {
          type string;
        }
        leaf privilege {
          description
            "Set user privilege level";
          type uint8 {
            range "0..15";
          }
        }
        leaf one-time {
          description
            "Specify that the username/password is valid for only one time";
          type empty;
        }
        container password {
          description
            "Specify the password for the user";
          leaf encryption {
            type enumeration {
              enum "0";
              enum "7";
            }
          }
          leaf password {
            type string;
          }
        }
        container secret {
          description
            "Specify the secret for the user";
          leaf encryption {
            type enumeration {
              enum "0";
              enum "5";
            }
          }
          leaf secret {
            type string;
          }
        }
      }
      container controller {
        description
          "Configure controller";
      }
      leaf aqm-register-fnf {
        description
          "Export audio/video stats to flow record";
        type empty;
      }
      uses live_ncs_config-vrf-definition-grouping;
      container rmon {
        description
          "Remote Monitoring";
        list alarm {
          description
            "Configure an RMON alarm";
          key "number";
          leaf number {
            type uint16;
          }
          leaf mib-object {
            type string;
          }
          leaf sample-interval {
            type uint32;
          }
          leaf test-mode {
            type enumeration {
              enum "absolute";
              enum "delta";
            }
          }
          leaf rising-threshold {
            description
              "Configure the rising threshold";
            type int32;
          }
          leaf rising-event {
            type uint16;
          }
          leaf falling-threshold {
            description
              "Configure the falling threshold";
            type int32;
          }
          leaf falling-event {
            type uint16;
          }
          leaf owner {
            description
              "Specify an owner for the alarm";
            type string;
          }
        }
        list event {
          description
            "Configure an RMON event";
          key "number";
          leaf number {
            type uint16;
          }
          container log {
            description
              "Generate RMON log when the event fires";
            presence "true";
            leaf trap {
              description
                "Generate SNMP trap when the event fires";
              type string;
            }
            leaf description {
              description
                "Specify a description of the event";
              type string;
            }
            leaf owner {
              description
                "Specify an owner for the event";
              type string;
            }
          }
        }
      }
      list sampler {
        description
          "Define a Sampler";
        key "name";
        leaf name {
          type string;
        }
      }
      container flow {
        description
          "Global Flow configuration subcommands";
      }
      uses live_ncs_config-ip-grouping;
      container mka {
        description
          "MACsec Key Agreement (MKA) configuration";
      }
      container macro {
        description
          "Macro configuration";
        container global {
          description
            "Enter global macro configuration";
          leaf description {
            description
              "Macro description of this device";
            type string;
          }
        }
        container auto {
          description
            "Macro autoexecution settings";
        }
      }
      uses live_ncs_config-ipv6-grouping;
      container vlan {
        description
          "Global vlan configuration";
      }
      container cdp {
        description
          "Global CDP configuration subcommands";
      }
      container policy;
      uses live_ncs_config-interface-grouping;
      list route-map {
        description
          "Route map tag";
        key "name";
        leaf name {
          description
            "WORD;;Route map tag";
          type string;
        }
      }
      container route-tag;
      list table-map {
        description
          "Configure Table Map";
        key "name";
        leaf name {
          type string;
        }
      }
      container sdm {
        description
          "Switch database management";
      }
      container mls {
        description
          "mls global commands";
      }
      container object-group {
        description
          "Configure Object group";
      }
      list pseudowire-class {
        description
          "Pseudowire-class configuration";
        key "name";
        leaf name {
          type string;
        }
      }
      container control-plane {
        description
          "Configure control plane services";
        presence "true";
      }
      container control-plane-host {
        container control-plane {
          description
            "Configure control plane services";
          container host {
            presence "true";
            list management-interface {
              description
                "Configure interface for receiving network management traffic";
              key "interface-name";
              leaf interface-name {
                type string;
              }
              container allow {
                description
                  "Allowed network management protocols on selected interface";
                leaf beep {
                  description
                    "Beep Protocol";
                  type empty;
                }
                leaf ftp {
                  description
                    "File Transfer Protocol";
                  type empty;
                }
                leaf http {
                  description
                    "HTTP Protocol";
                  type empty;
                }
                leaf https {
                  description
                    "HTTPS Protocol";
                  type empty;
                }
                leaf snmp {
                  description
                    "Simple Network Management Protocol";
                  type empty;
                }
                leaf ssh {
                  description
                    "Secure Shell Protocol";
                  type empty;
                }
                leaf telnet {
                  description
                    "Telnet Protocol";
                  type empty;
                }
                leaf tftp {
                  description
                    "Trivial File Transfer Protocol";
                  type empty;
                }
                leaf tl1 {
                  description
                    "Transaction Language Session Protocol";
                  type empty;
                }
              }
            }
          }
        }
      }
      leaf config-register {
        description
          "Define the configuration register";
        type string {
          pattern '[0-9xXa-fA-F].*';
        }
      }
      container clock {
        description
          "Configure time-of-day clock";
        container calendar-valid {
          description
            "Calendar time is authoritative";
          presence "true";
        }
        container summer-time {
          description
            "Configure summer (daylight savings) time";
          leaf zone {
            type string;
          }
          choice summer-choice {
            case date-case {
              leaf date {
                description
                  "Configure absolute summer time";
                type empty;
              }
              leaf start-day {
                type uint8 {
                  range "1..31";
                }
              }
              leaf start-month {
                type ios-types:month-type;
              }
              leaf start-year {
                type uint32 {
                  range "1993..2035";
                }
              }
              leaf start-time {
                type ios-types:hhmm-type;
              }
              leaf date-end-day {
                type uint8 {
                  range "1..31";
                }
              }
              leaf date-end-month {
                type ios-types:month-type;
              }
              leaf date-end-year {
                type uint32 {
                  range "1993..2035";
                }
              }
              leaf date-end-time {
                type ios-types:hhmm-type;
              }
              leaf offset {
                type uint16 {
                  range "1..1440";
                }
              }
            }
            case recurring-case {
              leaf recurring {
                description
                  "Configure recurring summer time";
                type empty;
              }
              leaf recurring-start {
                type union {
                  type uint8 {
                    range "1..4";
                  }
                  type enumeration {
                    enum "first";
                    enum "last";
                  }
                }
              }
              leaf recurring-start-day {
                type ios-types:weekday-type;
              }
              leaf recurring-start-month {
                type ios-types:month-type;
              }
              leaf recurring-start-time {
                type ios-types:hhmm-type;
              }
              leaf recurring-end {
                type union {
                  type uint8 {
                    range "1..4";
                  }
                  type enumeration {
                    enum "first";
                    enum "last";
                  }
                }
              }
              leaf recurring-end-day {
                type ios-types:weekday-type;
              }
              leaf recurring-end-month {
                type ios-types:month-type;
              }
              leaf recurring-end-time {
                type ios-types:hhmm-type;
              }
              leaf recurring-offset {
                type uint16 {
                  range "1..1440";
                }
              }
            }
          }
        }
        container timezone {
          description
            "Configure time zone";
          leaf zone {
            type string;
          }
          leaf offset {
            type enumeration {
              enum "+";
              enum "-";
            }
          }
          leaf hours {
            type int8 {
              range "-23..23";
            }
          }
          leaf minutes {
            type int8 {
              range "0..59";
            }
          }
        }
      }
      uses live_ncs_config-logging-grouping;
      container aaa {
        description
          "Authentication, Authorization and Accounting.";
      }
      uses live_ncs_config-privilege-grouping;
      container login {
        description
          "Enable secure login checking";
        leaf delay {
          description
            "Set delay between successive fail login";
          type uint8 {
            range "1..10";
          }
        }
        container on-failure {
          description
            "Set options for failed login attempt";
          presence "true";
          container log {
            description
              "Generate syslogs on failure logins";
            presence "true";
            leaf every {
              description
                "Periodicity for logs generated";
              type uint16 {
                range "1..65535";
              }
            }
          }
        }
        container on-success {
          description
            "Set options for successful login attempt";
          presence "true";
          container log {
            description
              "Generate syslogs on successful logins";
            presence "true";
            leaf every {
              description
                "Periodicity for logs generated";
              type uint16 {
                range "1..65535";
              }
            }
          }
        }
      }
      container multilink {
        description
          "PPP multilink global configuration";
      }
      container mac-address-table {
        description
          "Configure the MAC address table";
        container evc-xconnect {
          description
            "All ethernet virtual connections xconnect";
          leaf l2pt-forward-all {
            description
              "Layer 2 Protocol Forward All";
            type empty;
          }
        }
        container limit {
          description
            "Enter parameters for mac limit feature";
          list bdomain {
            description
              "bdomain number for  mac limit feature";
            key "number";
            leaf number {
              type uint16 {
                range "1..4095";
              }
            }
            leaf action {
              description
                "Enter action";
              type enumeration {
                enum "warning";
                enum "limit";
                enum "shutdown";
              }
            }
            leaf maximum {
              description
                "Enter max allowed entries";
              type uint32 {
                range "0..16000";
              }
            }
          }
        }
        container learning {
          description
            "Enable a MAC table learning feature";
          list vlan {
            description
              "Layer 2 table learning per VLAN";
            key "id";
            leaf id {
              type uint16 {
                range "1..4094";
              }
            }
            leaf module {
              description
                "Layer 2 table learning per VLAN per module";
              type uint8 {
                range "1..9";
              }
            }
          }
        }
      }
      container redundancy {
        description
          "Enter redundancy mode";
        presence "true";
        leaf maintenance-mode {
          description
            "Enable/Disable maintenance mode ";
          type empty;
        }
        container main-cpu {
          description
            "Enter main-cpu mode";
          presence "true";
          container auto-sync {
            leaf running-config {
              type empty;
            }
            leaf config-register {
              type empty;
            }
            leaf bootvar {
              type empty;
            }
            leaf standard {
              type empty;
            }
          }
          container standby {
            description
              "Standby";
            container console {
              description
                "Console";
              leaf enable {
                description
                  "Enable";
                type empty;
              }
            }
            container initialization {
              description
                "Initialization";
              container delay {
                description
                  "Delay";
                leaf second {
                  description
                    "Delay value in seconds";
                  type uint16 {
                    range "30..1800";
                  }
                }
                leaf boot-only {
                  description
                    "Delay effective only on system boot";
                  type empty;
                }
              }
            }
          }
        }
        leaf mode {
          description
            "redundancy mode for this chassis";
          type enumeration {
            enum "rpr";
            enum "rpr-plus";
            enum "sso";
            enum "none";
          }
        }
        container policy {
          description
            "redundancy policy enforcement";
          container config-sync {
            description
              "config sync parameters";
            container bulk {
              description
                "bulk configuration mode";
              container prc {
                description
                  "prc policy enforcement";
                leaf reload {
                  description
                    "reload standby";
                  type boolean;
                }
              }
            }
            container lbl {
              description
                "line-by-line configuration mode";
              container prc {
                description
                  "prc policy enforcement";
                leaf reload {
                  description
                    "reload standby";
                  type boolean;
                }
              }
            }
          }
        }
        container timer {
          description
            "Select a timer to configure";
          leaf rpso {
            description
              "Delay value in seconds";
            type uint16 {
              range "120..1200";
            }
          }
        }
        container interchassis {
          description
            "Enter interchassis mode";
          list group {
            description
              "Enter the redundancy group number";
            key "group-number";
            leaf group-number {
              type uint64 {
                range "1..4294967295";
              }
            }
            container monitor {
              description
                "define the peer monitoring method";
              leaf peer {
                description
                  "the peer method";
                type empty;
              }
              leaf bfd {
                description
                  "set peer monitoring method to bfd";
                type empty;
              }
            }
            container member {
              description
                "specify a redundancy group member";
              leaf ip {
                description
                  "specify the redundancy group member using an ip address";
                type inet:ipv4-address;
              }
            }
            container backbone {
              description
                "specify a redundancy group member";
              container interface {
                uses ios-ifc:live_ncs_interface-grouping;
              }
            }
          }
        }
      }
      container scheduler {
        description
          "Scheduler parameters";
        container runtime {
          description
            "Process runtime controls";
          leaf netinput {
            description
              "Process-switching run time (in milliseconds)";
            type uint16 {
              range "100..40000";
            }
          }
        }
        container allocate {
          description
            "Guarantee CPU time for processes";
          leaf interrupt-time {
            type uint16 {
              range "400..60000";
            }
          }
          leaf process-time {
            type uint16 {
              range "100..4000";
            }
          }
        }
      }
      container epm {
        description
          "EPM Global Configuration Commands";
        leaf logging {
          description
            "Enable EPM logging";
          type empty;
        }
      }
      container spanning-tree {
        description
          "Spanning Tree Subsystem";
      }
      container subscriber {
        description
          "Subscriber configuration";
        leaf templating {
          description
            "Configure subscriber templating";
          type empty;
        }
      }
      container track {
        description
          "Object tracking configuration commands";
      }
      container dot1x {
        description
          "IEEE 802.1X Global Configuration Commands";
      }
      container fallback {
        description
          "Fallback configuration commands";
      }
      list parameter-map {
        description
          "parameter map";
        key "name";
        leaf name {
          description
            "cws_tunnel global parameter-map";
          type union {
            type string;
            type enumeration {
              enum "global";
              enum "gtp";
            }
          }
        }
        leaf type {
          description
            "parameter map type";
          type enumeration {
            enum "cws-tunnel";
            enum "inspect";
            enum "inspect-global";
            enum "webauth";
            enum "inspect-vrf";
            enum "inspect-zone";
            enum "regex";
            enum "authbypass";
          }
        }
        leaf parameter-map-type {
          description
            "type - web-auth, consent or both";
          type enumeration {
            enum "webauth";
            enum "authbypass";
          }
        }
      }
      container ppp {
        description
          "PPP global configuration";
      }
      container mac {
        description
          "Global MAC configuration subcommands";
        container address-table {
          description
            "Configure the MAC address table";
          container aging-time {
            description
              "Set MAC address table entry maximum age";
            leaf val {
              type uint32 {
                range "0 | 10..1000000";
              }
            }
            leaf routed-mac {
              description
                "Set RM Aging interval";
              type empty;
            }
            leaf vlan {
              description
                "VLAN Keyword";
              type uint16 {
                range "1..4094";
              }
            }
          }
          leaf control-packet-learn {
            description
              "Enable/Disable learning from Control Packets";
            type empty;
          }
          container learning {
            description
              "Enable MAC table learning feature";
            leaf vlan {
              description
                "<1-4094>;;VLAN id to enable MAC Address learning";
              type uint16 {
                range "1..4094";
              }
            }
          }
          container notification {
            description
              "Enable/Disable MAC Notification on the switch";
            container change {
              description
                "Enable/Disable MAC Notification feature on the switch";
              presence "true";
              leaf history-size {
                description
                  "Number of entries in history table (0-500)";
                type uint16 {
                  range "0..500";
                }
              }
              leaf interval {
                description
                  "Notification interval in seconds (0-2147483647)";
                type uint32 {
                  range "0..2147483647";
                }
              }
            }
            leaf mac-move {
              description
                "Enable Mac Move Notification";
              type empty;
            }
            container threshold {
              description
                "Configure L2 Table monitoring";
              presence "true";
              leaf interval {
                description
                  "<120-1000000> Interval time in seconds";
                type uint32 {
                  range "120..1000000";
                }
              }
              container limit {
                description
                  "Limit percentage";
                leaf percentage {
                  description
                    "Percentage (0-100)";
                  type uint8 {
                    range "0..100";
                  }
                }
                leaf interval {
                  description
                    "<120-1000000> Interval time in seconds";
                  type uint32 {
                    range "120..1000000";
                  }
                }
              }
            }
          }
          container static {
            description
              "Static MAC entry";
            leaf mac-address {
              description
                "xxxx.xxxx.xxxx 48 bit mac address";
              type ios-types:cisco-mac-address-type;
            }
            leaf vlan {
              description
                "<1-4094> VLAN id of mac address table (1-4094)";
              type uint16 {
                range "1..4094";
              }
            }
            leaf drop {
              description
                "drop frames";
              type empty;
            }
            leaf interface {
              description
                "Output interface exact long name";
              type string;
            }
          }
        }
      }
      container tacacs {
        description
          "TACACS server configuration command";
      }
      container tacacs-server {
        description
          "Modify TACACS query parameters";
      }
      container software {
        description
          "Configure software installation parameters";
        container auto-upgrade {
          description
            "Configure software auto upgrade parameters";
          leaf enable {
            description
              "Enable the auto upgrade installation feature";
            type empty;
          }
        }
      }
      container upgrade {
        description
          "Global upgrade configuration subcommands";
        container fpd {
          description
            "Configure field programmable devices upgrade options";
          leaf auto {
            description
              "Auto upgrade all FPD images";
            type empty;
          }
          leaf path {
            description
              "Set path to locate the FPD image package file for auto upgrade";
            type string;
          }
        }
      }
      container vtp {
        description
          "Configure global VTP state";
      }
      container xconnect;
      container fabric {
        description
          "Catalyst 6000 crossbar fabric configuration commands";
        container switching-mode {
          description
            "Switching mode settings";
          container allow {
            description
              "Allow settings";
            choice allow-choice {
              leaf bus-mode {
                description
                  "Allow switching in bus mode for modules";
                type empty;
              }
              container truncated {
                description
                  "Truncated switching mode";
                presence "true";
                leaf threshold {
                  description
                    "Number of SFM-capable modules for truncated switching mode. Switch applies the threshold only when the mode is disallowed. Switch ignores the threshold when the truncated mode is allowed";
                  type uint8 {
                    range "1..9";
                  }
                }
              }
            }
          }
          container force {
            description
              "Force modules to different switching modes";
            leaf bus-mode {
              description
                "Switching mode of service modules will be forced to bus-mode by powercycling it.";
              type empty;
            }
          }
        }
      }
      container port-channel {
        description
          "EtherChannel configuration";
      }
      container key {
        description
          "Key management";
      }
      container l2 {
        description
          "Layer 2 configuration";
        leaf router-id {
          description
            "Configure a layer 2 identifier";
          type inet:ipv4-address;
        }
      }
      container system {
        description
          "Set the system configuration";
      }
      container errdisable {
        description
          "Error disable";
        container detect {
          description
            "Error disable detection";
          container cause {
            description
              "Enable error disable detection for application";
            leaf all {
              description
                "Enable error detection on all cases";
              type empty;
            }
            leaf arp-inspection {
              description
                "Enable error detection for arp inspection";
              type empty;
            }
            leaf bpduguard {
              description
                "Enable error detection on bpdu-guard";
              type empty;
            }
            leaf dhcp-rate-limit {
              description
                "Enable error detection on dhcp-rate-limit";
              type empty;
            }
            leaf dtp-flap {
              description
                "Enable error detection on dtp-flapping";
              type empty;
            }
            leaf gbic-invalid {
              description
                "Enable error detection on gbic-invalid";
              type empty;
            }
            leaf inline-power {
              description
                "Enable error detection for inline-power";
              type empty;
            }
            leaf l2ptguard {
              description
                "Enable timer to recover from l2protocol-tunnel error disable state";
              type empty;
            }
            leaf link-flap {
              description
                "Enable error detection on linkstate-flapping";
              type empty;
            }
            leaf loopback {
              description
                "Enable error detection on loopback";
              type empty;
            }
            leaf mlacp-minlink {
              type empty;
            }
            leaf pagp-flap {
              description
                "Enable error detection on pagp-flapping";
              type empty;
            }
            leaf pppoe-ia-rate-limit {
              description
                "Enable error detection on PPPoE IA rate-limit";
              type empty;
            }
            container security-violation {
              description
                "Enable error detection on 802.1x-guard";
              container shutdown {
                description
                  "Specify error disable shutdown mode for 802.1x-guard";
                leaf vlan {
                  description
                    "Shutdown vlan on 802.1x-guard violation";
                  type empty;
                }
              }
            }
            leaf sfp-config-mismatch {
              description
                "Enable error detection on SFP config mismatch";
              type empty;
            }
            leaf small-frame {
              description
                "Enable error detection on small_frame";
              type empty;
            }
          }
        }
        container flap-setting {
          description
            "Error disable flap detection setting";
          container cause {
            description
              "Set error disable flap parameters for application";
            container dtp-flap {
              description
                "Set the variables related to detection of dtp flaps";
              leaf max-flaps {
                description
                  "maximum flaps allowed before setting to errdisable";
                type uint8 {
                  range "1..100";
                }
              }
              leaf time {
                description
                  "time period the flaps are counted";
                type uint8 {
                  range "1..120";
                }
              }
            }
            container link-flap {
              description
                "Set the variables related to detection of link flaps";
              leaf max-flaps {
                description
                  "maximum flaps allowed before setting to errdisable";
                type uint8 {
                  range "1..100";
                }
              }
              leaf time {
                description
                  "time period the flaps are counted";
                type uint8 {
                  range "1..120";
                }
              }
            }
            container pagp-flap {
              description
                "Set the variables related to detection of pagp flaps";
              leaf max-flaps {
                description
                  "maximum flaps allowed before setting to errdisable";
                type uint8 {
                  range "1..100";
                }
              }
              leaf time {
                description
                  "time period the flaps are counted";
                type uint8 {
                  range "1..120";
                }
              }
            }
          }
        }
        container recovery {
          description
            "Error disable recovery";
          container cause {
            description
              "Enable error disable recovery for application";
            leaf all {
              description
                "Enable timer to recover from all error causes";
              type empty;
            }
            leaf arp-inspection {
              description
                "Enable timer to recover from arp inspection error disable state";
              type empty;
            }
            leaf bpduguard {
              description
                "Enable timer to recover from BPDU Guard error";
              type empty;
            }
            leaf channel-misconfig {
              description
                "(STP)  Enable timer to recover from channel misconfig error";
              type empty;
            }
            leaf dhcp-rate-limit {
              description
                "Enable timer to recover from dhcp-rate-limit error";
              type empty;
            }
            leaf dtp-flap {
              description
                "Enable timer to recover from dtp-flap error";
              type empty;
            }
            leaf gbic-invalid {
              description
                "Enable timer to recover from invalid GBIC error";
              type empty;
            }
            leaf inline-power {
              description
                "Enable timer to recover from inline-power error";
              type empty;
            }
            leaf l2ptguard {
              description
                "Enable timer to recover from l2protocol-tunnel error disable state";
              type empty;
            }
            leaf link-flap {
              description
                "Enable timer to recover from link-flap error";
              type empty;
            }
            leaf link-monitor-failure {
              type empty;
            }
            leaf loopback {
              description
                "Enable timer to recover from loopback error";
              type empty;
            }
            leaf mac-limit {
              description
                "Enable timer to recover from mac limit disable state";
              type empty;
            }
            leaf mlacp-minlink {
              type empty;
            }
            container oam-remote-failure {
              presence "true";
              leaf critical-event {
                type empty;
              }
              leaf dying-gasp {
                type empty;
              }
              leaf link-fault {
                type empty;
              }
            }
            leaf pagp-flap {
              description
                "Enable timer to recover from pagp-flap error";
              type empty;
            }
            leaf port-mode-failure {
              description
                "Enable timer to recover from port mode change failure";
              type empty;
            }
            leaf pppoe-ia-rate-limit {
              description
                "Enable timer to recover from PPPoE IA rate-limit error";
              type empty;
            }
            leaf psp {
              type empty;
            }
            leaf psecure-violation {
              description
                "Enable timer to recover from psecure violation error";
              type empty;
            }
            leaf security-violation {
              description
                "Enable timer to recover from 802.1x violation error";
              type empty;
            }
            leaf sfp-config-mismatch {
              description
                "Enable timer to recover from SFP config mismatch error";
              type empty;
            }
            leaf small-frame {
              description
                "Enable timer to recover from small frame error";
              type empty;
            }
            leaf storm-control {
              description
                "Enable timer to recover from storm-control error";
              type empty;
            }
            leaf udld {
              description
                "Enable timer to recover from udld error";
              type empty;
            }
            leaf unicast-flood {
              type empty;
            }
            leaf vmps {
              description
                "Enable timer to recover from vmps shutdown error";
              type empty;
            }
          }
          leaf interval {
            description
              "Error disable recovery timer value";
            type uint32 {
              range "30..86400";
            }
          }
        }
      }
      container identity {
        description
          "Identity Configuration Commands";
        container profile {
          description
            "Create an Identity profile";
          leaf dot1x {
            description
              "Service type for 802.1x";
            type empty;
          }
          leaf default {
            description
              "Service type default";
            type empty;
          }
        }
      }
      container monitor {
        description
          "Monitoring different system events";
        container event-trace {
          description
            "Tracing of system events";
        }
        list session {
          description
            "Configure a SPAN session";
          key "id";
          leaf id {
            type uint8 {
              range "1..66";
            }
          }
          container destination {
            description
              "SPAN destination interface or VLAN";
            list interface {
              description
                "SPAN destination interface";
              key "name";
              leaf name {
                description
                  "Interface Name";
                type string;
              }
              leaf encapsulation {
                description
                  "Set encapsulation for destination interface";
                type enumeration {
                  enum "dot1q";
                  enum "isl";
                  enum "replicate";
                }
              }
              leaf ingress {
                description
                  "Enable ingress traffic forwarding";
                type empty;
              }
              leaf ingress-encap {
                // NCS drop when statement
                type enumeration {
                  enum "dot1q";
                  enum "isl";
                  enum "untagged";
                }
              }
              leaf vlan {
                description
                  "Set default VLAN for untagged ingress traffic";
                // NCS drop when statement
                type uint16 {
                  range "1..4094";
                }
              }
            }
            container remote {
              description
                "SPAN destination Remote";
              leaf vlan {
                description
                  "Remote SPAN destination RSPAN VLAN";
                type uint16 {
                  range "1006..4094";
                }
              }
            }
          }
          container filter {
            description
              "SPAN filter VLAN";
            container packet-type {
              leaf status {
                type enumeration {
                  enum "good";
                  enum "bad";
                }
              }
              leaf direction {
                type enumeration {
                  enum "rx";
                  enum "tx";
                }
              }
            }
            container ip {
              description
                "Specify IP Access control rules";
              container access-group {
                description
                  "Specify access control group";
                leaf acl-name {
                  description
                    "Access-list name";
                  type string;
                }
              }
            }
          }
          container source {
            description
              "SPAN source interface, VLAN ";
            list interface {
              description
                "SPAN source interface";
              key "name";
              leaf name {
                description
                  "Interface Name";
                type string;
              }
              leaf direction {
                type enumeration {
                  enum "both";
                  enum "rx";
                  enum "tx";
                }
              }
            }
            container vlan {
              description
                "SPAN source VLAN";
              leaf vlan {
                type uint16 {
                  range "1..4094";
                }
              }
              leaf direction {
                type enumeration {
                  enum "both";
                  enum "rx";
                  enum "tx";
                }
              }
            }
            container remote {
              description
                "SPAN source Remote";
              leaf vlan {
                description
                  "Remote SPAN source RSPAN VLAN <1-1001>|<1006-4094>";
                type uint16 {
                  range "1..1001 | 1006..4094";
                }
              }
            }
          }
        }
      }
      list tftp-server {
        description
          "Provide TFTP service for netload requests";
        key "name";
        leaf name {
          type string;
        }
      }
      container radius-server {
        description
          "Modify RADIUS query parameters";
      }
      container radius {
        description
          "RADIUS server configuration command";
      }
      container zone {
        description
          "FW with zoning";
      }
      container zone-pair {
        description
          "Zone pair command";
      }
      list alarm-contact {
        key "name";
        leaf name {
          type uint8 {
            range "1..4";
          }
        }
        leaf description {
          type string {
            length "1..80";
          }
        }
        leaf severity {
          type enumeration {
            enum "critical";
            enum "major";
            enum "minor";
          }
        }
        leaf trigger {
          type enumeration {
            enum "open";
            enum "closed";
          }
        }
      }
      container ethernet {
        description
          "Ethernet configuration";
      }
      container access-list {
        description
          "Add an access list entry";
      }
      container bridge-domain {
        description
          "Bridge-domain global configuration commands";
      }
      container crypto {
        description
          "Encryption module";
      }
      container cts {
        description
          "Configures Cisco TrustSec";
      }
      container bfd-template {
        description
          "BFD-template";
      }
      container pfr {
        description
          "Performance Routing configuration submodes";
      }
      list pfr-map {
        description
          "Create pfr-map and enter pfr-map command mode";
        key "pfr-tg";
        leaf pfr-tg {
          description
            "pfr-map tag";
          type string;
        }
      }
      container facility-alarm {
        description
          "Configure facility alarms";
        leaf severity {
          type enumeration {
            enum "critical";
          }
        }
        leaf exceed-action {
          description
            "Behavior on critical threshold exceed";
          type enumeration {
            enum "shutdown";
          }
        }
      }
      container setup {
        description
          "Configure setup options";
      }
      container tod-clock {
        // NCS drop if-feature statement
        description
          "Tod clock config commands";
        container input-source {
          description
            "Synchronization Input Source";
          leaf priority {
            type uint8 {
              range "1..250";
            }
          }
          container ptp {
            leaf domain {
              type uint8;
            }
          }
        }
      }
      container network-clock {
        description
          "Network clock config commands";
        container synchronization {
          description
            "Network clock synchronization selection process";
          leaf automatic {
            description
              "ITU-T G.781/Telcordia standard based";
            type empty;
          }
          leaf mode {
            description
              "synchronization networking mode";
            type enumeration {
              enum "QL-enabled";
            }
          }
        }
        container wait-to-restore {
          description
            "Wait-to-Restore timer";
          leaf time {
            description
              "Wait-to-Restore time";
            type uint32 {
              range "0..86400";
            }
          }
          leaf global {
            description
              "Global";
            type empty;
          }
        }
        container input-source {
          description
            "Synchronization Input Source";
          leaf priority {
            type uint8 {
              range "1..250";
            }
          }
          container interface {
            uses ios-ifc:live_ncs_interface-grouping;
          }
          container ptp {
            leaf domain {
              type uint8;
            }
          }
        }
      }
      container l2vpn {
        description
          "Layer2 VPN commands";
      }
      container l2vpn-config;
      container l3vpn {
        description
          "l3vpn encapsulation ip commands";
      }
      container mpls {
        description
          "Configure MPLS parameters";
      }
      container router;
      container service-chain {
        description
          "Service Chain mode";
      }
      container performance {
        description
          "Global Performance monitor configuration";
      }
      container otv {
        description
          "Configure OTV information";
      }
      container remote-management {
        description
          "Enable the remote managment";
        leaf dmi {
          description
            "data-model-interface";
          type empty;
        }
        leaf restful-api {
          description
            "RESTful API";
          type boolean;
        }
      }
      list virtual-service {
        description
          "Configure virtual service";
        key "name";
        leaf name {
          type string {
            length "1..63";
          }
        }
      }
      container snmp {
        description
          "Modify SNMP interface parameters";
      }
      container snmp-server {
        description
          "Modify SNMP engine parameters";
      }
      container segment-routing {
        description
          "Enter Segment Routing Mode";
      }
      uses live_ncs_config-license-grouping;
      leaf disable-eadi {
        type empty;
      }
      container memory-size {
        // NCS drop if-feature statement
        description
          "Adjust memory size by percentage";
        leaf iomem {
          description
            "I/O memory";
          type uint8 {
            range "5..25";
          }
        }
      }
      container transceiver {
        // NCS drop if-feature statement
        description
          "Select from transceiver configuration commands";
        container type {
          description
            "type keyword";
          container all {
            container monitoring {
              description
                "Enable/disable monitoring";
              presence "true";
              leaf interval {
                description
                  "Set interval for monitoring";
                type uint16 {
                  range "300..3600";
                }
              }
            }
          }
        }
      }
      container service-insertion {
        description
          "Service Insertion mode";
      }
      container udld {
        description
          "Configure global UDLD setting";
      }
      container wireless {
        description
          "Configure wireless parameters";
        leaf mdns-bridging {
          description
            "Enable Ethernet mDNS Support";
          type boolean;
        }
      }
      container qos {
        description
          "Global QoS configuration commands";
        presence "true";
      }
      list time-range {
        description
          "Define time range entries";
        key "word";
        leaf word {
          type string;
        }
        container absolute {
          description
            "absolute time and date";
          container start {
            description
              "starting time and date";
            leaf start-time {
              description
                "Starting time";
              type string;
            }
            leaf day-of-month {
              description
                "<1-31>  Day of the month";
              type uint8;
            }
            leaf month {
              description
                "Month of the year [eg: Jan for January, Jun for June]";
              type string;
            }
            leaf year {
              description
                "Year";
              type uint16 {
                range "1993..2035";
              }
            }
          }
        }
      }
      container device-tracking {
        description
          "Device tracking configuration commands";
      }
      container fhrp {
        description
          "Configure First Hop Redundancy Protocols";
        container version {
          description
            "Configure which FHRP version is allowed to run";
          leaf vrrp {
            description
              "Configure Virtual Router Rendundancy Protocol";
            type enumeration {
              enum "v2";
              enum "v3";
            }
          }
        }
      }
      container metadata {
        description
          "Metadata Application";
        container flow {
          description
            "Enable Metadata Flow Handling";
          presence "true";
          leaf transmit {
            description
              "Enable Metadata Flow Transmit ";
            type empty;
          }
        }
      }
      container profile {
        description
          "MSP Profile";
        leaf flow {
          description
            "MSP Profile Flow";
          type empty;
        }
      }
      container alias {
        description
          "Create command alias";
        container exec {
          description
            "Exec mode";
          leaf alias-name {
            type string;
          }
          leaf new-alias-name {
            type string;
          }
        }
      }
      uses live_ncs_config-line-grouping;
      container ntp {
        description
          "Configure NTP";
      }
      container wsma {
        description
          "Configure Web Services Management Agents";
      }
      container event {
        description
          "Event related configuration commands";
      }
      container template {
        description
          "template";
      }

      grouping service-timestamp-show-timezone-and-year {
        leaf show-timezone {
          description
            "Add time zone information to timestamp";
          type empty;
        }
        leaf year {
          description
            "Include year in timestamp";
          type empty;
        }
      }

      grouping service-timestamp-msec-and-year {
        leaf msec {
          description
            "Include milliseconds in timestamp";
          type empty;
        }
        leaf year {
          description
            "Include year in timestamp";
          type empty;
        }
      }

      grouping service-timestamp-msec-and-show-timezone {
        leaf msec {
          description
            "Include milliseconds in timestamp";
          type empty;
        }
        leaf show-timezone {
          description
            "Add time zone information to timestamp";
          type empty;
        }
      }

      grouping service-timestamp-local-time-and-year {
        leaf localtime {
          description
            "Use local time zone for timestamps";
          type empty;
        }
        leaf year {
          description
            "Include year in timestamp";
          type empty;
        }
      }

      grouping service-timestamp-local-time-and-show-timezone {
        leaf localtime {
          description
            "Use local time zone for timestamps";
          type empty;
        }
        leaf show-timezone {
          description
            "Add time zone information to timestamp";
          type empty;
        }
      }

      grouping service-timestamp-local-time-and-msec {
        leaf localtime {
          description
            "Use local time zone for timestamps";
          type empty;
        }
        leaf msec {
          description
            "Include milliseconds in timestamp";
          type empty;
        }
      }

      grouping process-rising-grouping {
        container rising {
          description
            "rising threshold";
          list cpu-range {
            key "cpu-range";
            leaf cpu-range {
              type uint8 {
                range "1..100";
              }
            }
            container interval {
              description
                "observation interval";
              list cpu-range {
                key "cpu-range";
                leaf cpu-range {
                  type uint32 {
                    range "5..86400";
                  }
                }
                container falling {
                  description
                    "falling threshold";
                  list cpu-range {
                    key "cpu-range";
                    leaf cpu-range {
                      type uint8 {
                        range "1..100";
                      }
                    }
                    leaf interval {
                      description
                        "observation interval";
                      type uint32 {
                        range "5..86400";
                      }
                    }
                  }
                }
              }
            }
          }
        }
      }
      container process {
        description
          "Configure process";
        container cpu {
          description
            "Configure cpu parameters";
          container threshold {
            description
              "cpu threshold parameters";
            container type {
              description
                "cpu threshold type";
              container interrupt {
                description
                  "interrupt level utilization";
                uses process-rising-grouping;
              }
              container process {
                description
                  "process level utilization";
                uses process-rising-grouping;
              }
              container total {
                description
                  "total cpu utilization";
                uses process-rising-grouping;
              }
            }
          }
        }
      }
      container exception {
        description
          "help";
        container crashinfo {
          description
            "Crashinfo collection";
          presence "true";
          leaf buffersize {
            description
              "buffer size in Kbytes 256K or less (default is 32K)";
            type uint16 {
              range "32..256";
            }
          }
        }
      }
      container iox {
        description
          "Configure IOx services";
        presence "true";
      }
    }
  }
  augment "/ncs:devices/ncs:template/ncs:config" {
    container native {
      container default {
        description
          "Set a command to its defaults";
        container crypto {
          description
            "Encryption module";
          container ikev2 {
            description
              "Configure IKEv2 Options";
            leaf proposal {
              description
                "Define IKEV2 proposals";
              type empty;
            }
            leaf policy {
              description
                "Define IKEV2 policies";
              type empty;
            }
          }
        }
      }
      container bfd {
        description
          "BFD configuration commands";
      }
      leaf version {
        description
          "Version";
        type string;
      }
      leaf boot-start-marker {
        type empty;
      }
      container boot {
        description
          "Modify boot system parameters";
        container system {
          description
            "System Image";
          leaf tftp-path {
            description
              "Example: 192.x.x.x/<path to image>";
            type string;
          }
          leaf tftp {
            description
              "Example 192.168.x.x/<image-path>";
            type string;
          }
          container bootfile {
            description
              "WORD - boot filename";
            list filename-list {
              // NCS patched for predictable order
              ordered-by user;
              key "filename";
              leaf filename {
                description
                  "WORD - TFTP filename or URL";
                type string;
              }
            }
          }
          container flash {
            description
              "flash - Boot from flash memory";
            list flash-list {
              // NCS patched for predictable order
              ordered-by user;
              key "flash-leaf";
              leaf flash-leaf {
                type string;
              }
            }
          }
        }
      }
      leaf boot-end-marker {
        type empty;
      }
      leaf captive-portal-bypass {
        description
          "Enable Captive portal bypass for apple devices";
        type empty;
      }
      container memory {
        description
          "Configure memory management";
        container statistics {
          description
            "Configure statistics history table";
          container history {
            description
              "Configure statistics history table";
            leaf table {
              description
                "Configure statistics history table";
              type string;
            }
          }
        }
        container chunk {
          description
            "chunk related configuration";
          container siblings {
            description
              "chunk siblings related configuration";
            leaf threshold {
              description
                "Default is platform dependent";
              type string;
            }
          }
        }
        container free {
          description
            "free memory low water mark";
          container low-watermark {
            description
              "low water mark for notifications";
            leaf IO {
              description
                "low water mark of memory in KB";
              type string;
            }
            leaf processor {
              description
                "low water mark of memory in KB";
              type string;
            }
          }
        }
        leaf lite {
          description
            "Enable/disable memory lite";
          type empty;
        }
        container reserve {
          description
            "reserve memory";
          container critical {
            description
              "Reserve Critical Memory";
            presence "true";
            leaf memory-range {
              description
                "total amount of memory to be reserved in kilobytes";
              type string;
            }
          }
        }
        container sanity {
          description
            "Enable memory sanity";
          presence "true";
          leaf all {
            description
              "Enable memory sanity all";
            type empty;
          }
          leaf buffer {
            description
              "Enable memory sanity buffer";
            type empty;
          }
          leaf queue {
            type empty;
          }
        }
      }
      container location {
        description
          "Global location configuration commands";
        container civic-location {
          description
            "Civic location information";
          list identifier {
            // NCS patched for predictable order
            ordered-by user;
            description
              "Set the identifier";
            key "identifier";
            leaf identifier {
              type string;
            }
            leaf building {
              description
                "Building information";
              type string;
            }
            leaf floor {
              description
                "Floor number";
              type string;
            }
            leaf landmark {
              description
                "Landmark";
              type string;
            }
            leaf name {
              description
                "Resident name";
              type string;
            }
            leaf number {
              description
                "Street number";
              type string;
            }
          }
        }
      }
      container call-home {
        description
          "Enter call-home configuration mode";
        presence "true";
      }
      container hw-module {
        description
          "Control of individual components in the system";
        container uplink {
          description
            "Uplink control";
          leaf select {
            description
              "Select uplink interface";
            type string;
          }
          leaf mode {
            description
              "Uplink mode";
            type string;
          }
        }
        leaf sm {
          type string;
        }
        leaf pvdm {
          type string;
        }
      }
      container cisp {
        description
          "Set CISP parameters";
        leaf enable {
          description
            "Enable CISP";
          type empty;
        }
      }
      container module {
        description
          "Module";
      }
      list domain {
        // NCS patched for predictable order
        ordered-by user;
        description
          "Domain Configuration Commands";
        key "name";
        leaf name {
          type string;
        }
        list vrf {
          // NCS patched for predictable order
          ordered-by user;
          description
            "Specify vrf for domain";
          key "name";
          leaf name {
            type string;
          }
          container border {
            description
              "Enter border router configuration submode";
            container source-interface {
              description
                "Source Interface for border";
              leaf Loopback {
                description
                  "Loopback interface";
                type string;
              }
            }
            leaf master {
              description
                "Specify IP address of Domain master controller";
              type string;
            }
            container password {
              description
                "MD5 password to be used with MC";
              leaf encryption {
                type string;
              }
              leaf clear-key {
                type string;
              }
            }
          }
          container master {
            description
              "Enter master controller configuration submode";
            choice master-type {
              case branch {
                leaf branch {
                  description
                    "Set master type as branch hub";
                  type empty;
                }
              }
              case hub {
                leaf hub {
                  description
                    "Set master type as hub";
                  type empty;
                }
              }
              case transit {
                leaf transit {
                  description
                    "Set master type as transit";
                  type empty;
                }
              }
            }
            container advanced {
              description
                "Advanced configuration submode";
              leaf byte-loss-threshold {
                description
                  "Specify minimum byte loss calculation threshold";
                type string;
              }
              leaf channel-unreachable-timer {
                description
                  "Unreach interval detection";
                type string;
              }
              leaf load-sharing {
                description
                  "Enable load-sharing";
                type empty;
              }
              leaf minimum-mask-length {
                description
                  "Specify minimum mask length";
                type string;
              }
              leaf mitigation-mode {
                description
                  "Enable brownout detection in domain";
                type string;
              }
              leaf packet-loss-threshold {
                description
                  "Specify minimum packet loss calculation threshold";
                type string;
              }
              container smart-probes {
                description
                  "Smart probes configuration";
                leaf destination-port {
                  description
                    "Specify smart probes destination port number";
                  type string;
                }
                leaf source-port {
                  description
                    "Specify smart probes source port number";
                  type string;
                }
              }
              container syslog {
                description
                  "Specify syslog minimim time between tca";
                leaf tca-time-min {
                  description
                    "Specify time between syslog tcas in seconds";
                  type string;
                }
              }
              container tcp {
                description
                  "Specify tcp port numbers for mc-br communication";
                leaf mc-port {
                  description
                    "Specify tcp MC self port for mc-br communication";
                  type string;
                }
              }
              leaf threshold-variance {
                description
                  "Policy decision Threshold variance";
                type string;
              }
              container traffic-class-ageout-timer {
                description
                  "Traffic-class DB age timer";
                leaf interval {
                  description
                    "Specify new timer interval value mins/hours";
                  type string;
                }
                leaf interval-unit {
                  type string;
                }
              }
              leaf transit-site-affinity {
                description
                  "Enable Transit Site Affinity";
                type empty;
              }
            }
            container collector {
              description
                "NMS/v9 collector configuration";
              leaf ip {
                type string;
              }
              leaf port {
                description
                  "Specify collector port number";
                type string;
              }
            }
            container enterprise-prefix {
              description
                "Enterprise prefix configuration";
              leaf prefix-list {
                description
                  "Specify prefix-list with static site targets";
                type string;
              }
            }
            container load-balance {
              description
                "load balance non-policy traffic";
              presence "true";
              leaf advanced {
                description
                  "Load balancing configuration mode";
                type empty;
              }
            }
            container password {
              description
                "MD5 password to be used with BRs";
              leaf encryption {
                type string;
              }
              leaf clear-key {
                type string;
              }
            }
            container site-prefixes {
              description
                "site-prefixes configuration";
              leaf prefix-list {
                description
                  "Specify prefix-list with static site targets";
                type string;
              }
            }
            container source-interface {
              description
                "Source Interface for master controller";
              leaf Loopback {
                description
                  "Loopback interface";
                type string;
              }
            }
            list class {
              // NCS patched for predictable order
              ordered-by user;
              description
                "Create domain class and enter domain class command mode";
              key "name sequence";
              leaf name {
                type string;
              }
              leaf sequence {
                description
                  "Set the Sequence for the class";
                type string;
              }
              container match {
                description
                  "Specify the applications the policy applies to";
                list dscp {
                  // NCS patched for predictable order
                  ordered-by user;
                  description
                    "specify DSCP";
                  key "value";
                  leaf value {
                    type string;
                  }
                  leaf policy {
                    description
                      "Specify the policy (user defined/predefined)";
                    type string;
                  }
                }
              }
              container path-preference {
                description
                  "Specify the preferred provider";
                leaf-list primary {
                  // NCS patched for predictable order
                  ordered-by user;
                  description
                    "Primary service provider";
                  type string;
                }
                leaf-list fallback {
                  // NCS patched for predictable order
                  ordered-by user;
                  description
                    "Specify the fallback provider";
                  type string;
                }
              }
            }
            leaf hub-ip {
              type string;
            }
          }
        }
      }
      uses ncs_template_config-parser-grouping;
      container service {
        description
          "Modify use of network based services";
        leaf internal {
          description
            "Enable/Disable Internal commands";
          type empty;
        }
        container pad-conf {
          leaf pad {
            description
              "Enable PAD commands";
            type string;
          }
        }
        container pad {
          description
            "Enable PAD commands";
          presence "true";
          leaf cmns {
            description
              "Enable PAD over CMNS connections";
            type empty;
          }
          leaf from-xot {
            description
              "Accept XOT to PAD connections";
            type empty;
          }
          leaf to-xot {
            description
              "Allow outgoing PAD over XOT connections";
            type empty;
          }
        }
        leaf password-encryption {
          description
            "Encrypt system passwords";
          type empty;
        }
        leaf password-recovery {
          description
            "Enable password recovery";
          type string;
        }
        container timestamps {
          description
            "Timestamp debug/log messages";
          presence "true";
          container debug {
            description
              "Timestamp debug messages";
            container datetime {
              description
                "Timestamp with date and time";
              presence "true";
              container localtime {
                description
                  "Use local time zone for timestamps";
                presence "true";
                container msec {
                  description
                    "Include milliseconds in timestamp";
                  presence "true";
                  uses service-timestamp-show-timezone-and-year;
                }
                container show-timezone {
                  description
                    "Add time zone information to timestamp";
                  presence "true";
                  uses service-timestamp-msec-and-year;
                }
                container year {
                  description
                    "Include year in timestamp";
                  presence "true";
                  uses service-timestamp-msec-and-show-timezone;
                }
              }
              container msec {
                description
                  "Include milliseconds in timestamp";
                presence "true";
                container localtime {
                  description
                    "Use local time zone for timestamps";
                  presence "true";
                  uses service-timestamp-show-timezone-and-year;
                }
                container show-timezone {
                  description
                    "Add time zone information to timestamp";
                  presence "true";
                  uses service-timestamp-local-time-and-year;
                }
                container year {
                  description
                    "Include year in timestamp";
                  presence "true";
                  uses service-timestamp-local-time-and-show-timezone;
                }
              }
              container show-timezone {
                description
                  "Add time zone information to timestamp";
                presence "true";
                container localtime {
                  description
                    "Use local time zone for timestamps";
                  presence "true";
                  uses service-timestamp-msec-and-year;
                }
                container msec {
                  description
                    "Include milliseconds in timestamp";
                  presence "true";
                  uses service-timestamp-local-time-and-year;
                }
                container year {
                  description
                    "Include year in timestamp";
                  presence "true";
                  uses service-timestamp-local-time-and-msec;
                }
              }
              container year {
                description
                  "Include year in timestamp";
                presence "true";
                container localtime {
                  description
                    "Use local time zone for timestamps";
                  presence "true";
                  uses service-timestamp-msec-and-show-timezone;
                }
                container msec {
                  description
                    "Include milliseconds in timestamp";
                  presence "true";
                  uses service-timestamp-local-time-and-show-timezone;
                }
                container show-timezone {
                  description
                    "Add time zone information to timestamp";
                  presence "true";
                  uses service-timestamp-local-time-and-msec;
                }
              }
            }
            leaf uptime {
              description
                "Timestamp with system uptime";
              type empty;
            }
          }
          container log {
            description
              "Timestamp log messages";
            container datetime {
              description
                "Timestamp with date and time";
              presence "true";
              leaf msec {
                description
                  "Include milliseconds in timestamp";
                type empty;
              }
              leaf localtime {
                description
                  "Use local time zone for timestamps";
                type empty;
              }
              leaf show-timezone {
                description
                  "Add time zone information to timestamp";
                type empty;
              }
              leaf year {
                description
                  "Include year in timestamp";
                type empty;
              }
            }
            leaf uptime {
              description
                "Timestamp with system uptime";
              type empty;
            }
          }
        }
        container alignment {
          description
            "Control alignment correction and logging";
          leaf detection {
            description
              "Enable detection of alignment issues";
            type empty;
          }
          leaf logging {
            description
              "Enable logging of alignment issues";
            type empty;
          }
        }
        leaf call-home {
          description
            "Enable call-home service";
          type empty;
        }
        leaf compress-config {
          description
            "Compress the configuration file";
          type empty;
        }
        leaf config {
          description
            "TFTP load config files";
          type empty;
        }
        container counters {
          description
            "Control aging of interface counters";
          container max {
            description
              "Maximum counter aging threshold";
            leaf age {
              description
                "Aging threshold";
              type string;
            }
          }
        }
        leaf dhcp {
          description
            "Enable DHCP server and relay agent";
          type empty;
        }
        leaf disable-ip-fast-frag {
          description
            "Disable IP particle-based fast fragmentation";
          type empty;
        }
        leaf exec-callback {
          description
            "Enable exec callback";
          type empty;
        }
        leaf exec-wait {
          description
            "Delay EXEC startup on noisy lines";
          type empty;
        }
        leaf finger {
          description
            "Allow responses to finger requests";
          type empty;
        }
        container heartbeat {
          description
            "Enable heartbeat processing";
          leaf fatal-count {
            description
              "Set heartbeat fatal count";
            type string;
          }
          leaf interrupt-interval {
            description
              "Set heartbeat interrupt test interval";
            type string;
          }
          leaf interrupt-max {
            description
              "Set maximum message count from interrupt test";
            type string;
          }
          leaf transmit-interval {
            description
              "Set heartbeat transmit interval";
            type string;
          }
          leaf warning-timeout {
            description
              "Set heartbeat warning timeout interval";
            type string;
          }
        }
        leaf hide-telnet-addresses {
          description
            "Hide destination addresses in telnet command";
          type empty;
        }
        leaf linenumber {
          description
            "enable line number banner for each exec";
          type empty;
        }
        leaf log-hidden {
          description
            "Enable syslog msgs for hidden/internal commands";
          type empty;
        }
        leaf nagle {
          description
            "Enable Nagle's congestion control algorithm";
          type empty;
        }
        leaf old-slip-prompts {
          description
            "Allow old scripts to operate with slip/ppp";
          type empty;
        }
        container prompt {
          description
            "Enable mode specific prompt";
          leaf config {
            description
              "Enable configuration mode prompt";
            type empty;
          }
        }
        leaf pt-vty-logging {
          description
            "Log significant VTY-Async events";
          type empty;
        }
        leaf sequence-numbers {
          description
            "Stamp logger messages with a sequence number";
          type empty;
        }
        leaf slave-log {
          description
            "Enable log capability of slave IPs";
          type empty;
        }
        leaf tcp-keepalives-in {
          description
            "Generate keepalives on idle incoming network connections";
          type empty;
        }
        leaf tcp-keepalives-out {
          description
            "Generate keepalives on idle outgoing network connections";
          type empty;
        }
        leaf telnet-zeroidle {
          description
            "Set TCP window 0 when connection is idle";
          type empty;
        }
        leaf tcp-small-servers {
          description
            "Enable small TCP servers (e.g., ECHO)";
          type empty;
        }
        leaf udp-small-servers {
          description
            "Enable small UDP servers (e.g., ECHO)";
          type empty;
        }
        leaf unsupported-transceiver {
          description
            "Enable support for third-party transceivers";
          type empty;
        }
      }
      container platform {
        description
          "platform specific configuration";
      }
      leaf hostname {
        description
          "Set system's network name";
        type string;
      }
      container enable {
        description
          "Modify enable password parameters";
        container password {
          description
            "Assign the privileged level password (MAX of 25 characters)";
          uses ncs_template_password-07-grouping;
        }
        leaf last-resort {
          description
            "Define enable action if no TACACS servers respond";
          type string;
        }
        container secret {
          description
            "Assign the privileged level secret";
          leaf level {
            description
              "Set exec level password";
            type string;
          }
          leaf type {
            type string;
          }
          leaf secret {
            type string;
          }
        }
        leaf use-tacacs {
          description
            "Use TACACS to check enable passwords";
          type empty;
        }
      }
      container password {
        description
          "Configure encryption password (key)";
        container encryption {
          description
            "Encrypt system passwords";
          leaf aes {
            description
              "Enable stronger (AES) password encryption";
            type empty;
          }
        }
      }
      container eap {
        description
          "Configure EAP authenticator parameters";
        list profile {
          // NCS patched for predictable order
          ordered-by user;
          description
            "EAP authenticator profile configuration";
          key "name";
          leaf name {
            description
              "WORD;;EAP authenticator profile name";
            type string;
          }
          container method {
            description
              "Add an allowed method";
            leaf fast {
              description
                "EAP-FAST method allowed";
              type empty;
            }
            leaf gtc {
              description
                "EAP-GTC method allowed";
              type empty;
            }
            leaf leap {
              description
                "EAP-LEAP method allowed";
              type empty;
            }
            leaf mschapv2 {
              description
                "EAP-MSCHAPV2 method allowed";
              type empty;
            }
            leaf peap {
              description
                "EAP-PEAP method allowed";
              type empty;
            }
            leaf md5 {
              description
                "EAP-MD5 method allowed";
              type empty;
            }
            leaf tls {
              description
                "EAP-TLS method allowed";
              type empty;
            }
          }
          leaf pki-trustpoint {
            description
              "Set the default pki trustpoint";
            type string;
          }
        }
      }
      container archive {
        description
          "Archive the configuration";
        container log {
          description
            "Logging commands";
          container config {
            description
              "Logging changes to the running configuration";
            leaf hidekeys {
              description
                "suppress output (e.g. passwords) when displaying logged commands";
              type empty;
            }
            container logging {
              description
                "Modify config logging parameters";
              leaf enable {
                description
                  "Enable the config logger";
                type empty;
              }
              leaf size {
                description
                  "Maximum number of logged commands that will be kept by the config log";
                type string;
              }
              container persistent {
                description
                  "Log configuration persistent";
                presence "true";
                leaf auto {
                  description
                    "Log configuration commands automatically";
                  type empty;
                }
                leaf reload {
                  description
                    "Apply persisted commands on reload";
                  type empty;
                }
              }
            }
            container notify {
              description
                "Send logged commands to target applications";
              container syslog {
                description
                  "Send logged commands as syslog messages";
                presence "true";
                leaf contenttype {
                  description
                    "Type of the syslog message content";
                  type string;
                }
              }
            }
          }
        }
        leaf path {
          description
            "path for backups";
          type string;
        }
        leaf maximum {
          description
            "maximum number of backup copies";
          type string;
        }
        leaf write-memory {
          description
            "Enable automatic backup generation during write memory";
          type empty;
        }
        leaf time-period {
          description
            "Period of time in minutes to automatically archive the running-config";
          type string;
        }
      }
      list username {
        // NCS patched for predictable order
        ordered-by user;
        description
          "Establish User Name Authentication";
        key "name";
        leaf name {
          type string;
        }
        leaf privilege {
          description
            "Set user privilege level";
          type string;
        }
        leaf one-time {
          description
            "Specify that the username/password is valid for only one time";
          type empty;
        }
        container password {
          description
            "Specify the password for the user";
          leaf encryption {
            type string;
          }
          leaf password {
            type string;
          }
        }
        container secret {
          description
            "Specify the secret for the user";
          leaf encryption {
            type string;
          }
          leaf secret {
            type string;
          }
        }
      }
      container controller {
        description
          "Configure controller";
      }
      leaf aqm-register-fnf {
        description
          "Export audio/video stats to flow record";
        type empty;
      }
      uses ncs_template_config-vrf-definition-grouping;
      container rmon {
        description
          "Remote Monitoring";
        list alarm {
          // NCS patched for predictable order
          ordered-by user;
          description
            "Configure an RMON alarm";
          key "number";
          leaf number {
            type string;
          }
          leaf mib-object {
            type string;
          }
          leaf sample-interval {
            type string;
          }
          leaf test-mode {
            type string;
          }
          leaf rising-threshold {
            description
              "Configure the rising threshold";
            type string;
          }
          leaf rising-event {
            type string;
          }
          leaf falling-threshold {
            description
              "Configure the falling threshold";
            type string;
          }
          leaf falling-event {
            type string;
          }
          leaf owner {
            description
              "Specify an owner for the alarm";
            type string;
          }
        }
        list event {
          // NCS patched for predictable order
          ordered-by user;
          description
            "Configure an RMON event";
          key "number";
          leaf number {
            type string;
          }
          container log {
            description
              "Generate RMON log when the event fires";
            presence "true";
            leaf trap {
              description
                "Generate SNMP trap when the event fires";
              type string;
            }
            leaf description {
              description
                "Specify a description of the event";
              type string;
            }
            leaf owner {
              description
                "Specify an owner for the event";
              type string;
            }
          }
        }
      }
      list sampler {
        // NCS patched for predictable order
        ordered-by user;
        description
          "Define a Sampler";
        key "name";
        leaf name {
          type string;
        }
      }
      container flow {
        description
          "Global Flow configuration subcommands";
      }
      uses ncs_template_config-ip-grouping;
      container mka {
        description
          "MACsec Key Agreement (MKA) configuration";
      }
      container macro {
        description
          "Macro configuration";
        container global {
          description
            "Enter global macro configuration";
          leaf description {
            description
              "Macro description of this device";
            type string;
          }
        }
        container auto {
          description
            "Macro autoexecution settings";
        }
      }
      uses ncs_template_config-ipv6-grouping;
      container vlan {
        description
          "Global vlan configuration";
      }
      container cdp {
        description
          "Global CDP configuration subcommands";
      }
      container policy;
      uses ncs_template_config-interface-grouping;
      list route-map {
        // NCS patched for predictable order
        ordered-by user;
        description
          "Route map tag";
        key "name";
        leaf name {
          description
            "WORD;;Route map tag";
          type string;
        }
      }
      container route-tag;
      list table-map {
        // NCS patched for predictable order
        ordered-by user;
        description
          "Configure Table Map";
        key "name";
        leaf name {
          type string;
        }
      }
      container sdm {
        description
          "Switch database management";
      }
      container mls {
        description
          "mls global commands";
      }
      container object-group {
        description
          "Configure Object group";
      }
      list pseudowire-class {
        // NCS patched for predictable order
        ordered-by user;
        description
          "Pseudowire-class configuration";
        key "name";
        leaf name {
          type string;
        }
      }
      container control-plane {
        description
          "Configure control plane services";
        presence "true";
      }
      container control-plane-host {
        container control-plane {
          description
            "Configure control plane services";
          container host {
            presence "true";
            list management-interface {
              // NCS patched for predictable order
              ordered-by user;
              description
                "Configure interface for receiving network management traffic";
              key "interface-name";
              leaf interface-name {
                type string;
              }
              container allow {
                description
                  "Allowed network management protocols on selected interface";
                leaf beep {
                  description
                    "Beep Protocol";
                  type empty;
                }
                leaf ftp {
                  description
                    "File Transfer Protocol";
                  type empty;
                }
                leaf http {
                  description
                    "HTTP Protocol";
                  type empty;
                }
                leaf https {
                  description
                    "HTTPS Protocol";
                  type empty;
                }
                leaf snmp {
                  description
                    "Simple Network Management Protocol";
                  type empty;
                }
                leaf ssh {
                  description
                    "Secure Shell Protocol";
                  type empty;
                }
                leaf telnet {
                  description
                    "Telnet Protocol";
                  type empty;
                }
                leaf tftp {
                  description
                    "Trivial File Transfer Protocol";
                  type empty;
                }
                leaf tl1 {
                  description
                    "Transaction Language Session Protocol";
                  type empty;
                }
              }
            }
          }
        }
      }
      leaf config-register {
        description
          "Define the configuration register";
        type string;
      }
      container clock {
        description
          "Configure time-of-day clock";
        container calendar-valid {
          description
            "Calendar time is authoritative";
          presence "true";
        }
        container summer-time {
          description
            "Configure summer (daylight savings) time";
          leaf zone {
            type string;
          }
          choice summer-choice {
            case date-case {
              leaf date {
                description
                  "Configure absolute summer time";
                type empty;
              }
              leaf start-day {
                type string;
              }
              leaf start-month {
                type string;
              }
              leaf start-year {
                type string;
              }
              leaf start-time {
                type string;
              }
              leaf date-end-day {
                type string;
              }
              leaf date-end-month {
                type string;
              }
              leaf date-end-year {
                type string;
              }
              leaf date-end-time {
                type string;
              }
              leaf offset {
                type string;
              }
            }
            case recurring-case {
              leaf recurring {
                description
                  "Configure recurring summer time";
                type empty;
              }
              leaf recurring-start {
                type string;
              }
              leaf recurring-start-day {
                type string;
              }
              leaf recurring-start-month {
                type string;
              }
              leaf recurring-start-time {
                type string;
              }
              leaf recurring-end {
                type string;
              }
              leaf recurring-end-day {
                type string;
              }
              leaf recurring-end-month {
                type string;
              }
              leaf recurring-end-time {
                type string;
              }
              leaf recurring-offset {
                type string;
              }
            }
          }
        }
        container timezone {
          description
            "Configure time zone";
          leaf zone {
            type string;
          }
          leaf offset {
            type string;
          }
          leaf hours {
            type string;
          }
          leaf minutes {
            type string;
          }
        }
      }
      uses ncs_template_config-logging-grouping;
      container aaa {
        description
          "Authentication, Authorization and Accounting.";
      }
      uses ncs_template_config-privilege-grouping;
      container login {
        description
          "Enable secure login checking";
        leaf delay {
          description
            "Set delay between successive fail login";
          type string;
        }
        container on-failure {
          description
            "Set options for failed login attempt";
          presence "true";
          container log {
            description
              "Generate syslogs on failure logins";
            presence "true";
            leaf every {
              description
                "Periodicity for logs generated";
              type string;
            }
          }
        }
        container on-success {
          description
            "Set options for successful login attempt";
          presence "true";
          container log {
            description
              "Generate syslogs on successful logins";
            presence "true";
            leaf every {
              description
                "Periodicity for logs generated";
              type string;
            }
          }
        }
      }
      container multilink {
        description
          "PPP multilink global configuration";
      }
      container mac-address-table {
        description
          "Configure the MAC address table";
        container evc-xconnect {
          description
            "All ethernet virtual connections xconnect";
          leaf l2pt-forward-all {
            description
              "Layer 2 Protocol Forward All";
            type empty;
          }
        }
        container limit {
          description
            "Enter parameters for mac limit feature";
          list bdomain {
            // NCS patched for predictable order
            ordered-by user;
            description
              "bdomain number for  mac limit feature";
            key "number";
            leaf number {
              type string;
            }
            leaf action {
              description
                "Enter action";
              type string;
            }
            leaf maximum {
              description
                "Enter max allowed entries";
              type string;
            }
          }
        }
        container learning {
          description
            "Enable a MAC table learning feature";
          list vlan {
            // NCS patched for predictable order
            ordered-by user;
            description
              "Layer 2 table learning per VLAN";
            key "id";
            leaf id {
              type string;
            }
            leaf module {
              description
                "Layer 2 table learning per VLAN per module";
              type string;
            }
          }
        }
      }
      container redundancy {
        description
          "Enter redundancy mode";
        presence "true";
        leaf maintenance-mode {
          description
            "Enable/Disable maintenance mode ";
          type empty;
        }
        container main-cpu {
          description
            "Enter main-cpu mode";
          presence "true";
          container auto-sync {
            leaf running-config {
              type empty;
            }
            leaf config-register {
              type empty;
            }
            leaf bootvar {
              type empty;
            }
            leaf standard {
              type empty;
            }
          }
          container standby {
            description
              "Standby";
            container console {
              description
                "Console";
              leaf enable {
                description
                  "Enable";
                type empty;
              }
            }
            container initialization {
              description
                "Initialization";
              container delay {
                description
                  "Delay";
                leaf second {
                  description
                    "Delay value in seconds";
                  type string;
                }
                leaf boot-only {
                  description
                    "Delay effective only on system boot";
                  type empty;
                }
              }
            }
          }
        }
        leaf mode {
          description
            "redundancy mode for this chassis";
          type string;
        }
        container policy {
          description
            "redundancy policy enforcement";
          container config-sync {
            description
              "config sync parameters";
            container bulk {
              description
                "bulk configuration mode";
              container prc {
                description
                  "prc policy enforcement";
                leaf reload {
                  description
                    "reload standby";
                  type string;
                }
              }
            }
            container lbl {
              description
                "line-by-line configuration mode";
              container prc {
                description
                  "prc policy enforcement";
                leaf reload {
                  description
                    "reload standby";
                  type string;
                }
              }
            }
          }
        }
        container timer {
          description
            "Select a timer to configure";
          leaf rpso {
            description
              "Delay value in seconds";
            type string;
          }
        }
        container interchassis {
          description
            "Enter interchassis mode";
          list group {
            // NCS patched for predictable order
            ordered-by user;
            description
              "Enter the redundancy group number";
            key "group-number";
            leaf group-number {
              type string;
            }
            container monitor {
              description
                "define the peer monitoring method";
              leaf peer {
                description
                  "the peer method";
                type empty;
              }
              leaf bfd {
                description
                  "set peer monitoring method to bfd";
                type empty;
              }
            }
            container member {
              description
                "specify a redundancy group member";
              leaf ip {
                description
                  "specify the redundancy group member using an ip address";
                type string;
              }
            }
            container backbone {
              description
                "specify a redundancy group member";
              container interface {
                uses ios-ifc:ncs_template_interface-grouping;
              }
            }
          }
        }
      }
      container scheduler {
        description
          "Scheduler parameters";
        container runtime {
          description
            "Process runtime controls";
          leaf netinput {
            description
              "Process-switching run time (in milliseconds)";
            type string;
          }
        }
        container allocate {
          description
            "Guarantee CPU time for processes";
          leaf interrupt-time {
            type string;
          }
          leaf process-time {
            type string;
          }
        }
      }
      container epm {
        description
          "EPM Global Configuration Commands";
        leaf logging {
          description
            "Enable EPM logging";
          type empty;
        }
      }
      container spanning-tree {
        description
          "Spanning Tree Subsystem";
      }
      container subscriber {
        description
          "Subscriber configuration";
        leaf templating {
          description
            "Configure subscriber templating";
          type empty;
        }
      }
      container track {
        description
          "Object tracking configuration commands";
      }
      container dot1x {
        description
          "IEEE 802.1X Global Configuration Commands";
      }
      container fallback {
        description
          "Fallback configuration commands";
      }
      list parameter-map {
        // NCS patched for predictable order
        ordered-by user;
        description
          "parameter map";
        key "name";
        leaf name {
          description
            "cws_tunnel global parameter-map";
          type string;
        }
        leaf type {
          description
            "parameter map type";
          type string;
        }
        leaf parameter-map-type {
          description
            "type - web-auth, consent or both";
          type string;
        }
      }
      container ppp {
        description
          "PPP global configuration";
      }
      container mac {
        description
          "Global MAC configuration subcommands";
        container address-table {
          description
            "Configure the MAC address table";
          container aging-time {
            description
              "Set MAC address table entry maximum age";
            leaf val {
              type string;
            }
            leaf routed-mac {
              description
                "Set RM Aging interval";
              type empty;
            }
            leaf vlan {
              description
                "VLAN Keyword";
              type string;
            }
          }
          leaf control-packet-learn {
            description
              "Enable/Disable learning from Control Packets";
            type empty;
          }
          container learning {
            description
              "Enable MAC table learning feature";
            leaf vlan {
              description
                "<1-4094>;;VLAN id to enable MAC Address learning";
              type string;
            }
          }
          container notification {
            description
              "Enable/Disable MAC Notification on the switch";
            container change {
              description
                "Enable/Disable MAC Notification feature on the switch";
              presence "true";
              leaf history-size {
                description
                  "Number of entries in history table (0-500)";
                type string;
              }
              leaf interval {
                description
                  "Notification interval in seconds (0-2147483647)";
                type string;
              }
            }
            leaf mac-move {
              description
                "Enable Mac Move Notification";
              type empty;
            }
            container threshold {
              description
                "Configure L2 Table monitoring";
              presence "true";
              leaf interval {
                description
                  "<120-1000000> Interval time in seconds";
                type string;
              }
              container limit {
                description
                  "Limit percentage";
                leaf percentage {
                  description
                    "Percentage (0-100)";
                  type string;
                }
                leaf interval {
                  description
                    "<120-1000000> Interval time in seconds";
                  type string;
                }
              }
            }
          }
          container static {
            description
              "Static MAC entry";
            leaf mac-address {
              description
                "xxxx.xxxx.xxxx 48 bit mac address";
              type string;
            }
            leaf vlan {
              description
                "<1-4094> VLAN id of mac address table (1-4094)";
              type string;
            }
            leaf drop {
              description
                "drop frames";
              type empty;
            }
            leaf interface {
              description
                "Output interface exact long name";
              type string;
            }
          }
        }
      }
      container tacacs {
        description
          "TACACS server configuration command";
      }
      container tacacs-server {
        description
          "Modify TACACS query parameters";
      }
      container software {
        description
          "Configure software installation parameters";
        container auto-upgrade {
          description
            "Configure software auto upgrade parameters";
          leaf enable {
            description
              "Enable the auto upgrade installation feature";
            type empty;
          }
        }
      }
      container upgrade {
        description
          "Global upgrade configuration subcommands";
        container fpd {
          description
            "Configure field programmable devices upgrade options";
          leaf auto {
            description
              "Auto upgrade all FPD images";
            type empty;
          }
          leaf path {
            description
              "Set path to locate the FPD image package file for auto upgrade";
            type string;
          }
        }
      }
      container vtp {
        description
          "Configure global VTP state";
      }
      container xconnect;
      container fabric {
        description
          "Catalyst 6000 crossbar fabric configuration commands";
        container switching-mode {
          description
            "Switching mode settings";
          container allow {
            description
              "Allow settings";
            choice allow-choice {
              leaf bus-mode {
                description
                  "Allow switching in bus mode for modules";
                type empty;
              }
              container truncated {
                description
                  "Truncated switching mode";
                presence "true";
                leaf threshold {
                  description
                    "Number of SFM-capable modules for truncated switching mode. Switch applies the threshold only when the mode is disallowed. Switch ignores the threshold when the truncated mode is allowed";
                  type string;
                }
              }
            }
          }
          container force {
            description
              "Force modules to different switching modes";
            leaf bus-mode {
              description
                "Switching mode of service modules will be forced to bus-mode by powercycling it.";
              type empty;
            }
          }
        }
      }
      container port-channel {
        description
          "EtherChannel configuration";
      }
      container key {
        description
          "Key management";
      }
      container l2 {
        description
          "Layer 2 configuration";
        leaf router-id {
          description
            "Configure a layer 2 identifier";
          type string;
        }
      }
      container system {
        description
          "Set the system configuration";
      }
      container errdisable {
        description
          "Error disable";
        container detect {
          description
            "Error disable detection";
          container cause {
            description
              "Enable error disable detection for application";
            leaf all {
              description
                "Enable error detection on all cases";
              type empty;
            }
            leaf arp-inspection {
              description
                "Enable error detection for arp inspection";
              type empty;
            }
            leaf bpduguard {
              description
                "Enable error detection on bpdu-guard";
              type empty;
            }
            leaf dhcp-rate-limit {
              description
                "Enable error detection on dhcp-rate-limit";
              type empty;
            }
            leaf dtp-flap {
              description
                "Enable error detection on dtp-flapping";
              type empty;
            }
            leaf gbic-invalid {
              description
                "Enable error detection on gbic-invalid";
              type empty;
            }
            leaf inline-power {
              description
                "Enable error detection for inline-power";
              type empty;
            }
            leaf l2ptguard {
              description
                "Enable timer to recover from l2protocol-tunnel error disable state";
              type empty;
            }
            leaf link-flap {
              description
                "Enable error detection on linkstate-flapping";
              type empty;
            }
            leaf loopback {
              description
                "Enable error detection on loopback";
              type empty;
            }
            leaf mlacp-minlink {
              type empty;
            }
            leaf pagp-flap {
              description
                "Enable error detection on pagp-flapping";
              type empty;
            }
            leaf pppoe-ia-rate-limit {
              description
                "Enable error detection on PPPoE IA rate-limit";
              type empty;
            }
            container security-violation {
              description
                "Enable error detection on 802.1x-guard";
              container shutdown {
                description
                  "Specify error disable shutdown mode for 802.1x-guard";
                leaf vlan {
                  description
                    "Shutdown vlan on 802.1x-guard violation";
                  type empty;
                }
              }
            }
            leaf sfp-config-mismatch {
              description
                "Enable error detection on SFP config mismatch";
              type empty;
            }
            leaf small-frame {
              description
                "Enable error detection on small_frame";
              type empty;
            }
          }
        }
        container flap-setting {
          description
            "Error disable flap detection setting";
          container cause {
            description
              "Set error disable flap parameters for application";
            container dtp-flap {
              description
                "Set the variables related to detection of dtp flaps";
              leaf max-flaps {
                description
                  "maximum flaps allowed before setting to errdisable";
                type string;
              }
              leaf time {
                description
                  "time period the flaps are counted";
                type string;
              }
            }
            container link-flap {
              description
                "Set the variables related to detection of link flaps";
              leaf max-flaps {
                description
                  "maximum flaps allowed before setting to errdisable";
                type string;
              }
              leaf time {
                description
                  "time period the flaps are counted";
                type string;
              }
            }
            container pagp-flap {
              description
                "Set the variables related to detection of pagp flaps";
              leaf max-flaps {
                description
                  "maximum flaps allowed before setting to errdisable";
                type string;
              }
              leaf time {
                description
                  "time period the flaps are counted";
                type string;
              }
            }
          }
        }
        container recovery {
          description
            "Error disable recovery";
          container cause {
            description
              "Enable error disable recovery for application";
            leaf all {
              description
                "Enable timer to recover from all error causes";
              type empty;
            }
            leaf arp-inspection {
              description
                "Enable timer to recover from arp inspection error disable state";
              type empty;
            }
            leaf bpduguard {
              description
                "Enable timer to recover from BPDU Guard error";
              type empty;
            }
            leaf channel-misconfig {
              description
                "(STP)  Enable timer to recover from channel misconfig error";
              type empty;
            }
            leaf dhcp-rate-limit {
              description
                "Enable timer to recover from dhcp-rate-limit error";
              type empty;
            }
            leaf dtp-flap {
              description
                "Enable timer to recover from dtp-flap error";
              type empty;
            }
            leaf gbic-invalid {
              description
                "Enable timer to recover from invalid GBIC error";
              type empty;
            }
            leaf inline-power {
              description
                "Enable timer to recover from inline-power error";
              type empty;
            }
            leaf l2ptguard {
              description
                "Enable timer to recover from l2protocol-tunnel error disable state";
              type empty;
            }
            leaf link-flap {
              description
                "Enable timer to recover from link-flap error";
              type empty;
            }
            leaf link-monitor-failure {
              type empty;
            }
            leaf loopback {
              description
                "Enable timer to recover from loopback error";
              type empty;
            }
            leaf mac-limit {
              description
                "Enable timer to recover from mac limit disable state";
              type empty;
            }
            leaf mlacp-minlink {
              type empty;
            }
            container oam-remote-failure {
              presence "true";
              leaf critical-event {
                type empty;
              }
              leaf dying-gasp {
                type empty;
              }
              leaf link-fault {
                type empty;
              }
            }
            leaf pagp-flap {
              description
                "Enable timer to recover from pagp-flap error";
              type empty;
            }
            leaf port-mode-failure {
              description
                "Enable timer to recover from port mode change failure";
              type empty;
            }
            leaf pppoe-ia-rate-limit {
              description
                "Enable timer to recover from PPPoE IA rate-limit error";
              type empty;
            }
            leaf psp {
              type empty;
            }
            leaf psecure-violation {
              description
                "Enable timer to recover from psecure violation error";
              type empty;
            }
            leaf security-violation {
              description
                "Enable timer to recover from 802.1x violation error";
              type empty;
            }
            leaf sfp-config-mismatch {
              description
                "Enable timer to recover from SFP config mismatch error";
              type empty;
            }
            leaf small-frame {
              description
                "Enable timer to recover from small frame error";
              type empty;
            }
            leaf storm-control {
              description
                "Enable timer to recover from storm-control error";
              type empty;
            }
            leaf udld {
              description
                "Enable timer to recover from udld error";
              type empty;
            }
            leaf unicast-flood {
              type empty;
            }
            leaf vmps {
              description
                "Enable timer to recover from vmps shutdown error";
              type empty;
            }
          }
          leaf interval {
            description
              "Error disable recovery timer value";
            type string;
          }
        }
      }
      container identity {
        description
          "Identity Configuration Commands";
        container profile {
          description
            "Create an Identity profile";
          leaf dot1x {
            description
              "Service type for 802.1x";
            type empty;
          }
          leaf default {
            description
              "Service type default";
            type empty;
          }
        }
      }
      container monitor {
        description
          "Monitoring different system events";
        container event-trace {
          description
            "Tracing of system events";
        }
        list session {
          // NCS patched for predictable order
          ordered-by user;
          description
            "Configure a SPAN session";
          key "id";
          leaf id {
            type string;
          }
          container destination {
            description
              "SPAN destination interface or VLAN";
            list interface {
              // NCS patched for predictable order
              ordered-by user;
              description
                "SPAN destination interface";
              key "name";
              leaf name {
                description
                  "Interface Name";
                type string;
              }
              leaf encapsulation {
                description
                  "Set encapsulation for destination interface";
                type string;
              }
              leaf ingress {
                description
                  "Enable ingress traffic forwarding";
                type empty;
              }
              leaf ingress-encap {
                // NCS drop when statement
                type string;
              }
              leaf vlan {
                description
                  "Set default VLAN for untagged ingress traffic";
                // NCS drop when statement
                type string;
              }
            }
            container remote {
              description
                "SPAN destination Remote";
              leaf vlan {
                description
                  "Remote SPAN destination RSPAN VLAN";
                type string;
              }
            }
          }
          container filter {
            description
              "SPAN filter VLAN";
            container packet-type {
              leaf status {
                type string;
              }
              leaf direction {
                type string;
              }
            }
            container ip {
              description
                "Specify IP Access control rules";
              container access-group {
                description
                  "Specify access control group";
                leaf acl-name {
                  description
                    "Access-list name";
                  type string;
                }
              }
            }
          }
          container source {
            description
              "SPAN source interface, VLAN ";
            list interface {
              // NCS patched for predictable order
              ordered-by user;
              description
                "SPAN source interface";
              key "name";
              leaf name {
                description
                  "Interface Name";
                type string;
              }
              leaf direction {
                type string;
              }
            }
            container vlan {
              description
                "SPAN source VLAN";
              leaf vlan {
                type string;
              }
              leaf direction {
                type string;
              }
            }
            container remote {
              description
                "SPAN source Remote";
              leaf vlan {
                description
                  "Remote SPAN source RSPAN VLAN <1-1001>|<1006-4094>";
                type string;
              }
            }
          }
        }
      }
      list tftp-server {
        // NCS patched for predictable order
        ordered-by user;
        description
          "Provide TFTP service for netload requests";
        key "name";
        leaf name {
          type string;
        }
      }
      container radius-server {
        description
          "Modify RADIUS query parameters";
      }
      container radius {
        description
          "RADIUS server configuration command";
      }
      container zone {
        description
          "FW with zoning";
      }
      container zone-pair {
        description
          "Zone pair command";
      }
      list alarm-contact {
        // NCS patched for predictable order
        ordered-by user;
        key "name";
        leaf name {
          type string;
        }
        leaf description {
          type string;
        }
        leaf severity {
          type string;
        }
        leaf trigger {
          type string;
        }
      }
      container ethernet {
        description
          "Ethernet configuration";
      }
      container access-list {
        description
          "Add an access list entry";
      }
      container bridge-domain {
        description
          "Bridge-domain global configuration commands";
      }
      container crypto {
        description
          "Encryption module";
      }
      container cts {
        description
          "Configures Cisco TrustSec";
      }
      container bfd-template {
        description
          "BFD-template";
      }
      container pfr {
        description
          "Performance Routing configuration submodes";
      }
      list pfr-map {
        // NCS patched for predictable order
        ordered-by user;
        description
          "Create pfr-map and enter pfr-map command mode";
        key "pfr-tg";
        leaf pfr-tg {
          description
            "pfr-map tag";
          type string;
        }
      }
      container facility-alarm {
        description
          "Configure facility alarms";
        leaf severity {
          type string;
        }
        leaf exceed-action {
          description
            "Behavior on critical threshold exceed";
          type string;
        }
      }
      container setup {
        description
          "Configure setup options";
      }
      container tod-clock {
        // NCS drop if-feature statement
        description
          "Tod clock config commands";
        container input-source {
          description
            "Synchronization Input Source";
          leaf priority {
            type string;
          }
          container ptp {
            leaf domain {
              type string;
            }
          }
        }
      }
      container network-clock {
        description
          "Network clock config commands";
        container synchronization {
          description
            "Network clock synchronization selection process";
          leaf automatic {
            description
              "ITU-T G.781/Telcordia standard based";
            type empty;
          }
          leaf mode {
            description
              "synchronization networking mode";
            type string;
          }
        }
        container wait-to-restore {
          description
            "Wait-to-Restore timer";
          leaf time {
            description
              "Wait-to-Restore time";
            type string;
          }
          leaf global {
            description
              "Global";
            type empty;
          }
        }
        container input-source {
          description
            "Synchronization Input Source";
          leaf priority {
            type string;
          }
          container interface {
            uses ios-ifc:ncs_template_interface-grouping;
          }
          container ptp {
            leaf domain {
              type string;
            }
          }
        }
      }
      container l2vpn {
        description
          "Layer2 VPN commands";
      }
      container l2vpn-config;
      container l3vpn {
        description
          "l3vpn encapsulation ip commands";
      }
      container mpls {
        description
          "Configure MPLS parameters";
      }
      container router;
      container service-chain {
        description
          "Service Chain mode";
      }
      container performance {
        description
          "Global Performance monitor configuration";
      }
      container otv {
        description
          "Configure OTV information";
      }
      container remote-management {
        description
          "Enable the remote managment";
        leaf dmi {
          description
            "data-model-interface";
          type empty;
        }
        leaf restful-api {
          description
            "RESTful API";
          type string;
        }
      }
      list virtual-service {
        // NCS patched for predictable order
        ordered-by user;
        description
          "Configure virtual service";
        key "name";
        leaf name {
          type string;
        }
      }
      container snmp {
        description
          "Modify SNMP interface parameters";
      }
      container snmp-server {
        description
          "Modify SNMP engine parameters";
      }
      container segment-routing {
        description
          "Enter Segment Routing Mode";
      }
      uses ncs_template_config-license-grouping;
      leaf disable-eadi {
        type empty;
      }
      container memory-size {
        // NCS drop if-feature statement
        description
          "Adjust memory size by percentage";
        leaf iomem {
          description
            "I/O memory";
          type string;
        }
      }
      container transceiver {
        // NCS drop if-feature statement
        description
          "Select from transceiver configuration commands";
        container type {
          description
            "type keyword";
          container all {
            container monitoring {
              description
                "Enable/disable monitoring";
              presence "true";
              leaf interval {
                description
                  "Set interval for monitoring";
                type string;
              }
            }
          }
        }
      }
      container service-insertion {
        description
          "Service Insertion mode";
      }
      container udld {
        description
          "Configure global UDLD setting";
      }
      container wireless {
        description
          "Configure wireless parameters";
        leaf mdns-bridging {
          description
            "Enable Ethernet mDNS Support";
          type string;
        }
      }
      container qos {
        description
          "Global QoS configuration commands";
        presence "true";
      }
      list time-range {
        // NCS patched for predictable order
        ordered-by user;
        description
          "Define time range entries";
        key "word";
        leaf word {
          type string;
        }
        container absolute {
          description
            "absolute time and date";
          container start {
            description
              "starting time and date";
            leaf start-time {
              description
                "Starting time";
              type string;
            }
            leaf day-of-month {
              description
                "<1-31>  Day of the month";
              type string;
            }
            leaf month {
              description
                "Month of the year [eg: Jan for January, Jun for June]";
              type string;
            }
            leaf year {
              description
                "Year";
              type string;
            }
          }
        }
      }
      container device-tracking {
        description
          "Device tracking configuration commands";
      }
      container fhrp {
        description
          "Configure First Hop Redundancy Protocols";
        container version {
          description
            "Configure which FHRP version is allowed to run";
          leaf vrrp {
            description
              "Configure Virtual Router Rendundancy Protocol";
            type string;
          }
        }
      }
      container metadata {
        description
          "Metadata Application";
        container flow {
          description
            "Enable Metadata Flow Handling";
          presence "true";
          leaf transmit {
            description
              "Enable Metadata Flow Transmit ";
            type empty;
          }
        }
      }
      container profile {
        description
          "MSP Profile";
        leaf flow {
          description
            "MSP Profile Flow";
          type empty;
        }
      }
      container alias {
        description
          "Create command alias";
        container exec {
          description
            "Exec mode";
          leaf alias-name {
            type string;
          }
          leaf new-alias-name {
            type string;
          }
        }
      }
      uses ncs_template_config-line-grouping;
      container ntp {
        description
          "Configure NTP";
      }
      container wsma {
        description
          "Configure Web Services Management Agents";
      }
      container event {
        description
          "Event related configuration commands";
      }
      container template {
        description
          "template";
      }

      grouping service-timestamp-show-timezone-and-year {
        leaf show-timezone {
          description
            "Add time zone information to timestamp";
          type empty;
        }
        leaf year {
          description
            "Include year in timestamp";
          type empty;
        }
      }

      grouping service-timestamp-msec-and-year {
        leaf msec {
          description
            "Include milliseconds in timestamp";
          type empty;
        }
        leaf year {
          description
            "Include year in timestamp";
          type empty;
        }
      }

      grouping service-timestamp-msec-and-show-timezone {
        leaf msec {
          description
            "Include milliseconds in timestamp";
          type empty;
        }
        leaf show-timezone {
          description
            "Add time zone information to timestamp";
          type empty;
        }
      }

      grouping service-timestamp-local-time-and-year {
        leaf localtime {
          description
            "Use local time zone for timestamps";
          type empty;
        }
        leaf year {
          description
            "Include year in timestamp";
          type empty;
        }
      }

      grouping service-timestamp-local-time-and-show-timezone {
        leaf localtime {
          description
            "Use local time zone for timestamps";
          type empty;
        }
        leaf show-timezone {
          description
            "Add time zone information to timestamp";
          type empty;
        }
      }

      grouping service-timestamp-local-time-and-msec {
        leaf localtime {
          description
            "Use local time zone for timestamps";
          type empty;
        }
        leaf msec {
          description
            "Include milliseconds in timestamp";
          type empty;
        }
      }

      grouping process-rising-grouping {
        container rising {
          description
            "rising threshold";
          list cpu-range {
            // NCS patched for predictable order
            ordered-by user;
            key "cpu-range";
            leaf cpu-range {
              type string;
            }
            container interval {
              description
                "observation interval";
              list cpu-range {
                // NCS patched for predictable order
                ordered-by user;
                key "cpu-range";
                leaf cpu-range {
                  type string;
                }
                container falling {
                  description
                    "falling threshold";
                  list cpu-range {
                    // NCS patched for predictable order
                    ordered-by user;
                    key "cpu-range";
                    leaf cpu-range {
                      type string;
                    }
                    leaf interval {
                      description
                        "observation interval";
                      type string;
                    }
                  }
                }
              }
            }
          }
        }
      }
      container process {
        description
          "Configure process";
        container cpu {
          description
            "Configure cpu parameters";
          container threshold {
            description
              "cpu threshold parameters";
            container type {
              description
                "cpu threshold type";
              container interrupt {
                description
                  "interrupt level utilization";
                uses process-rising-grouping;
              }
              container process {
                description
                  "process level utilization";
                uses process-rising-grouping;
              }
              container total {
                description
                  "total cpu utilization";
                uses process-rising-grouping;
              }
            }
          }
        }
      }
      container exception {
        description
          "help";
        container crashinfo {
          description
            "Crashinfo collection";
          presence "true";
          leaf buffersize {
            description
              "buffer size in Kbytes 256K or less (default is 32K)";
            type string;
          }
        }
      }
      container iox {
        description
          "Configure IOx services";
        presence "true";
      }
    }
  }
}
