submodule Cisco-IOS-XE-parser {
  // Generated by yanger -t ncs
  belongs-to Cisco-IOS-XE-native {
    prefix ios;
  }

  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Parser Yang model.
     Copyright (c) 2016 by Cisco Systems, Inc.
     All rights reserved.";

  revision 2017-02-07 {
    description
      "Initial revision";
  }

  grouping ncs_template_config-parser-grouping {
    container parser {
      description
        "Configure parser";
      container config {
        description
          "Configure config generation";
        leaf cache {
          description
            "Cache the configuration";
          type string;
        }
        leaf partition {
          description
            "Enable configuration Partitioning";
          type empty;
        }
      }
    }
  }

  grouping ncs_template_config-privilege-grouping {
    container privilege {
      description
        "Command privilege parameters";
      container exec {
        description
          "Exec mode";
        list level {
          // NCS patched for predictable order
          ordered-by user;
          description
            "Set privilege level of command";
          key "privilege";
          leaf privilege {
            type string;
          }
          list command-list {
            // NCS patched for predictable order
            ordered-by user;
            key "command";
            leaf command {
              description
                "There are side effects";
              type string;
            }
          }
        }
      }
    }
  }

  grouping ncs_rpc_notif_config-parser-grouping {
    container parser {
      description
        "Configure parser";
      container config {
        description
          "Configure config generation";
        leaf cache {
          description
            "Cache the configuration";
          type enumeration {
            enum "interface";
          }
        }
        leaf partition {
          description
            "Enable configuration Partitioning";
          type empty;
        }
      }
    }
  }

  grouping ncs_rpc_notif_config-privilege-grouping {
    container privilege {
      description
        "Command privilege parameters";
      container exec {
        description
          "Exec mode";
        list level {
          description
            "Set privilege level of command";
          key "privilege";
          leaf privilege {
            type uint8;
          }
          list command-list {
            ordered-by user;
            key "command";
            leaf command {
              description
                "There are side effects";
              type string {
                pattern '(show.*)|(write.*)';
              }
            }
          }
        }
      }
    }
  }

  grouping live_ncs_config-parser-grouping {
    container parser {
      description
        "Configure parser";
      container config {
        description
          "Configure config generation";
        leaf cache {
          description
            "Cache the configuration";
          type enumeration {
            enum "interface";
          }
        }
        leaf partition {
          description
            "Enable configuration Partitioning";
          type empty;
        }
      }
    }
  }

  grouping live_ncs_config-privilege-grouping {
    container privilege {
      description
        "Command privilege parameters";
      container exec {
        description
          "Exec mode";
        list level {
          description
            "Set privilege level of command";
          key "privilege";
          leaf privilege {
            type uint8;
          }
          list command-list {
            ordered-by user;
            key "command";
            leaf command {
              description
                "There are side effects";
              type string {
                pattern '(show.*)|(write.*)';
              }
            }
          }
        }
      }
    }
  }

  grouping config-parser-grouping {
    container parser {
      description
        "Configure parser";
      container config {
        description
          "Configure config generation";
        leaf cache {
          description
            "Cache the configuration";
          type enumeration {
            enum "interface";
          }
        }
        leaf partition {
          description
            "Enable configuration Partitioning";
          type empty;
        }
      }
    }
  }

  grouping config-privilege-grouping {
    container privilege {
      description
        "Command privilege parameters";
      container exec {
        description
          "Exec mode";
        list level {
          description
            "Set privilege level of command";
          key "privilege";
          leaf privilege {
            type uint8;
          }
          list command-list {
            ordered-by user;
            key "command";
            leaf command {
              description
                "There are side effects";
              type string {
                pattern '(show.*)|(write.*)';
              }
            }
          }
        }
      }
    }
  }
}
