module Cisco-IOS-XE-otv {
  // Generated by yanger -t ncs
  tailf:ncs-device-type "netconf";

  namespace "http://cisco.com/ns/yang/Cisco-IOS-XE-otv";
  prefix ios-otv;

  import ietf-inet-types {
    prefix inet;
  }
  import Cisco-IOS-XE-native {
    prefix ios;
  }
  import Cisco-IOS-XE-interface-common {
    prefix ios-ifc;
  }
  import Cisco-IOS-XE-ethernet {
    prefix ios-eth;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Overlay Transport Virtualization (OTV) Yang model.
     Copyright (c) 2016 by Cisco Systems, Inc.
     All rights reserved.";

  revision 2017-02-07 {
    description
      "Initial revision";
  }

  grouping ncs_template_otv-isis-hostname-grouping {
    container hostname {
      description
        "Dynamic hostname for IS-IS";
      leaf dynamic {
        description
          "Dynamic hostname";
        type empty;
      }
    }
  }

  grouping ncs_template_otv-isis-skeptical-grouping {
    container skeptical {
      description
        "Be a cautious NSF helper when refresh adjacency";
      leaf interval {
        description
          "Interval during which holdtime will NOT be refreshed";
        type string;
      }
    }
  }

  grouping ncs_template_otv-isis-log-adjacency-changes-grouping {
    container log-adjacency-changes {
      description
        "Log changes in adjacency state";
      presence "true";
      leaf all {
        description
          "Include changes generated by non-IIH event";
        type empty;
      }
    }
  }

  grouping ncs_template_otv-isis-site-grouping {
    container default {
      description
        "Set a command to its defaults";
      leaf log-adjacency-changes {
        description
          "Log changes in adjacency state";
        type empty;
      }
      leaf net {
        description
          "A Network Entity Title for this process";
        type empty;
      }
      container skeptical {
        description
          "Be a cautious NSF helper when refresh adjacency";
        leaf interval {
          description
            "Interval during which holdtime will NOT be refreshed";
          type empty;
        }
      }
    }
    uses ncs_template_otv-isis-log-adjacency-changes-grouping;
    leaf net {
      description
        "A Network Entity Title for this process";
      type string;
    }
    uses ncs_template_otv-isis-skeptical-grouping;
  }

  grouping ncs_template_otv-isis-authentication-grouping {
    container authentication {
      description
        "ISIS authentication for interface related PDUs";
      leaf key-chain {
        description
          "Authentication key-chain";
        type string;
      }
      leaf mode {
        description
          "Authentication mode for PDUs";
        type string;
      }
      leaf send-only {
        description
          "Authentication send only, receive ignore";
        type empty;
      }
    }
  }

  grouping ncs_template_interface-overlay-grouping {
    container otv {
      description
        "Configure OTV information";
      container adjacency-server {
        description
          "Indicate if the box is an Adjacency Server";
        leaf unicast-only {
          description
            "Unicast Only";
          type empty;
        }
      }
      leaf control-group {
        description
          "OTV VPN control multicast group";
        type string;
      }
      leaf data-group {
        description
          "Multicast group range for data";
        type string;
      }
      container encapsulation-format {
        description
          "Encapsulation format";
        container ip {
          description
            "Use IP for outer header encapsulation";
          leaf gre {
            description
              "Use GRE middle header encapsulation";
            type empty;
          }
        }
      }
      leaf filter-fhrp {
        description
          "Configure to not forward HSRP, GLBP, and VRRP packets on overlay";
        type empty;
      }
      container isis {
        description
          "ISIS interface subcommands";
        uses ncs_template_otv-isis-authentication-grouping;
        leaf bfd {
          description
            "Bidirectional Forwarding Protocol";
          type empty;
        }
        leaf csnp-interval {
          description
            "Set CSNP interval in seconds";
          type string;
        }
        container hello {
          description
            "Add padding to IS-IS hello packets";
          container padding {
            description
              "Pad hello packets";
            presence "true";
            leaf always {
              description
                "Never pad hello packets if no prefix present";
              type empty;
            }
          }
        }
        container hello-interval {
          description
            "Set Hello interval in seconds";
          leaf value {
            type string;
          }
          leaf minimal {
            description
              "Holdtime 1 second, interval depends on multiplier";
            type empty;
          }
        }
        leaf hello-multiplier {
          description
            "Set multiplier for Hello holding time";
          type string;
        }
        leaf lsp-interval {
          description
            "Set LSP transmission interval";
          type string;
        }
        container metric {
          description
            "Configure the metric for interface";
          choice default-maximum {
            case default-case {
              leaf default {
                type string;
              }
            }
            case maximum-case {
              leaf maximum {
                description
                  "Maximum metric. All routers will exclude this link from their SPF";
                type empty;
              }
            }
          }
          leaf delay {
            type string;
          }
          leaf expense {
            type string;
          }
          leaf error {
            type string;
          }
        }
        leaf priority {
          description
            "Set priority for Designated Router election";
          type string;
        }
        leaf retransmit-interval {
          description
            "Set per-LSP retransmission interval";
          type string;
        }
        leaf retransmit-throttle-interval {
          description
            "Set interface LSP retransmission interval";
          type string;
        }
      }
      container join-interface {
        description
          "OTV VPN join-interface";
        uses ios-ifc:ncs_template_interface-grouping;
      }
      container suppress {
        description
          "Enable overlay packet suppression";
        leaf arp-nd {
          description
            "Suppress sending ARP and neighbor discovery packets on overlay";
          type empty;
        }
      }
      container use-adjacency-server {
        description
          "Point to remote Adjacency Server address";
        leaf remote-pri-ip {
          type string;
        }
        leaf remote-sec-ip {
          type string;
        }
        leaf unicast-only {
          description
            "Unicast Only Capability";
          type empty;
        }
      }
      leaf vpn-name {
        description
          "OTV VPN name";
        type string;
      }
    }
  }

  grouping ncs_template_config-otv-grouping {
    container fragmentation {
      description
        "Clear the DF (Don't Fragment) bit in the IP header";
      container join-interface {
        description
          "Allow fragmentation for overlays using this join-interface";
        uses ios-ifc:ncs_template_interface-grouping;
      }
    }
    container isis {
      description
        "OTV ISIS instance subcommands";
      list Overlay {
        // NCS patched for predictable order
        ordered-by user;
        description
          "Overlay interface";
        key "number";
        leaf number {
          type string;
        }
        uses ncs_template_otv-isis-overlay-grouping;
      }
      container site {
        description
          "Site Instance";
        uses ncs_template_otv-isis-site-grouping;
      }
    }
    list site {
      // NCS patched for predictable order
      ordered-by user;
      description
        "OTV site network configuration";
      key "bridge-domain";
      leaf bridge-domain {
        description
          "Bridge-domain to discover local OTV enabled devices";
        type string;
      }
      container default {
        description
          "Set a command to its defaults";
        container otv {
          description
            "OTV site configuration subcommands";
          uses ncs_template_otv-isis-grouping;
        }
      }
      container otv {
        description
          "OTV site configuration subcommands";
        uses ncs_template_otv-isis-grouping;
      }
    }
    leaf site-identifier {
      description
        "OTV site id";
      type string;
    }
  }

  grouping ncs_template_otv-isis-grouping {
    container isis {
      description
        "ISIS interface subcommands";
      uses ncs_template_otv-isis-authentication-grouping;
      leaf bfd {
        description
          "Bidirectional Forwarding Protocol";
        type empty;
      }
      container hello {
        description
          "Add padding to IS-IS hello packets";
        container padding {
          description
            "Pad hello packets";
          presence "true";
          leaf always {
            description
              "Never pad hello packets if no prefix present";
            type empty;
          }
        }
      }
      container hello-interval {
        description
          "Set Hello interval in seconds";
        leaf value {
          type string;
        }
        leaf minimal {
          description
            "Holdtime 1 second, interval depends on multiplier";
          type empty;
        }
      }
      leaf hello-multiplier {
        description
          "Set multiplier for Hello holding time";
        type string;
      }
      leaf priority {
        description
          "Set priority for Designated Router election";
        type string;
      }
    }
  }

  grouping ncs_template_otv-isis-overlay-grouping {
    uses ncs_template_otv-isis-authentication-grouping;
    container default {
      description
        "Set a command to its defaults";
      uses ncs_template_otv-isis-authentication-grouping;
      uses ncs_template_otv-isis-hostname-grouping;
      leaf delayed-deletion-interval {
        description
          "Set delayed deletion interval";
        type empty;
      }
      leaf log-adjacency-changes {
        description
          "Log changes in adjacency state";
        type empty;
      }
      leaf lsp-gen-interval {
        description
          "Minimum interval between regenerating same LSP";
        type empty;
      }
      leaf lsp-mtu {
        description
          "Set maximum LSP size";
        type empty;
      }
      leaf lsp-refresh-interval {
        description
          "Set LSP refresh interval";
        type empty;
      }
      leaf max-lsp-lifetime {
        description
          "Set maximum LSP lifetime";
        type empty;
      }
      leaf prc-interval {
        description
          "Minimum interval between partial route calculations";
        type empty;
      }
      leaf spf-interval {
        description
          "Minimum interval between SPF calculations";
        type empty;
      }
      container nsf {
        description
          "Non-stop forwarding";
        leaf cisco {
          description
            "Checkpoint method";
          type empty;
        }
        leaf interval {
          description
            "Minimum required stable interval between restarts";
          type empty;
        }
      }
      container skeptical {
        description
          "Be a cautious NSF helper when refresh adjacency";
        leaf interval {
          description
            "Interval during which holdtime will NOT be refreshed";
          type empty;
        }
      }
    }
    leaf delayed-deletion-interval {
      description
        "Set delayed deletion interval";
      type string;
    }
    uses ncs_template_otv-isis-hostname-grouping;
    uses ncs_template_otv-isis-log-adjacency-changes-grouping;
    container lsp-gen-interval {
      description
        "Minimum interval between regenerating same LSP";
      leaf seconds {
        type string;
      }
      leaf milliseconds {
        type string;
      }
      leaf wait {
        type string;
      }
    }
    leaf lsp-mtu {
      description
        "Set maximum LSP size";
      type string;
    }
    leaf lsp-refresh-interval {
      description
        "Set LSP refresh interval";
      type string;
    }
    leaf max-lsp-lifetime {
      description
        "Set maximum LSP lifetime";
      type string;
    }
    container nsf {
      description
        "Non-stop forwarding";
      leaf cisco {
        description
          "Checkpoint method";
        type empty;
      }
      leaf interval {
        description
          "Minimum required stable interval between restarts";
        type string;
      }
    }
    container prc-interval {
      description
        "Minimum interval between partial route calculations";
      leaf seconds {
        type string;
      }
      leaf milliseconds {
        type string;
      }
      leaf wait {
        type string;
      }
    }
    uses ncs_template_otv-isis-skeptical-grouping;
    container spf-interval {
      description
        "Minimum interval between SPF calculations";
      leaf seconds {
        type string;
      }
      leaf milliseconds {
        type string;
      }
      leaf wait {
        type string;
      }
    }
  }

  grouping ncs_rpc_notif_otv-isis-hostname-grouping {
    container hostname {
      description
        "Dynamic hostname for IS-IS";
      leaf dynamic {
        description
          "Dynamic hostname";
        type empty;
      }
    }
  }

  grouping ncs_rpc_notif_otv-isis-skeptical-grouping {
    container skeptical {
      description
        "Be a cautious NSF helper when refresh adjacency";
      leaf interval {
        description
          "Interval during which holdtime will NOT be refreshed";
        type uint32 {
          range "0..1440";
        }
      }
    }
  }

  grouping ncs_rpc_notif_otv-isis-log-adjacency-changes-grouping {
    container log-adjacency-changes {
      description
        "Log changes in adjacency state";
      presence "true";
      leaf all {
        description
          "Include changes generated by non-IIH event";
        type empty;
      }
    }
  }

  grouping ncs_rpc_notif_otv-isis-site-grouping {
    container default {
      description
        "Set a command to its defaults";
      leaf log-adjacency-changes {
        description
          "Log changes in adjacency state";
        type empty;
      }
      leaf net {
        description
          "A Network Entity Title for this process";
        type empty;
      }
      container skeptical {
        description
          "Be a cautious NSF helper when refresh adjacency";
        leaf interval {
          description
            "Interval during which holdtime will NOT be refreshed";
          type empty;
        }
      }
    }
    uses ncs_rpc_notif_otv-isis-log-adjacency-changes-grouping;
    leaf net {
      description
        "A Network Entity Title for this process";
      type string;
    }
    uses ncs_rpc_notif_otv-isis-skeptical-grouping;
  }

  grouping ncs_rpc_notif_otv-isis-authentication-grouping {
    container authentication {
      description
        "ISIS authentication for interface related PDUs";
      leaf key-chain {
        description
          "Authentication key-chain";
        type string;
      }
      leaf mode {
        description
          "Authentication mode for PDUs";
        type enumeration {
          enum "md5";
          enum "text";
        }
      }
      leaf send-only {
        description
          "Authentication send only, receive ignore";
        type empty;
      }
    }
  }

  grouping ncs_rpc_notif_interface-overlay-grouping {
    container otv {
      description
        "Configure OTV information";
      container adjacency-server {
        description
          "Indicate if the box is an Adjacency Server";
        leaf unicast-only {
          description
            "Unicast Only";
          type empty;
        }
      }
      leaf control-group {
        description
          "OTV VPN control multicast group";
        type inet:ipv4-address;
      }
      leaf data-group {
        description
          "Multicast group range for data";
        type inet:ipv4-prefix;
      }
      container encapsulation-format {
        description
          "Encapsulation format";
        container ip {
          description
            "Use IP for outer header encapsulation";
          leaf gre {
            description
              "Use GRE middle header encapsulation";
            type empty;
          }
        }
      }
      leaf filter-fhrp {
        description
          "Configure to not forward HSRP, GLBP, and VRRP packets on overlay";
        type empty;
      }
      container isis {
        description
          "ISIS interface subcommands";
        uses ncs_rpc_notif_otv-isis-authentication-grouping;
        leaf bfd {
          description
            "Bidirectional Forwarding Protocol";
          type empty;
        }
        leaf csnp-interval {
          description
            "Set CSNP interval in seconds";
          type uint16 {
            range "0..65535";
          }
        }
        container hello {
          description
            "Add padding to IS-IS hello packets";
          container padding {
            description
              "Pad hello packets";
            presence "true";
            leaf always {
              description
                "Never pad hello packets if no prefix present";
              type empty;
            }
          }
        }
        container hello-interval {
          description
            "Set Hello interval in seconds";
          leaf value {
            type uint16 {
              range "1..65535";
            }
          }
          leaf minimal {
            description
              "Holdtime 1 second, interval depends on multiplier";
            type empty;
          }
        }
        leaf hello-multiplier {
          description
            "Set multiplier for Hello holding time";
          type uint16 {
            range "3..1000";
          }
        }
        leaf lsp-interval {
          description
            "Set LSP transmission interval";
          type uint64 {
            range "1..4294967295";
          }
        }
        container metric {
          description
            "Configure the metric for interface";
          choice default-maximum {
            case default-case {
              leaf default {
                type uint32 {
                  range "1..16777214";
                }
              }
            }
            case maximum-case {
              leaf maximum {
                description
                  "Maximum metric. All routers will exclude this link from their SPF";
                type empty;
              }
            }
          }
          leaf delay {
            type uint32 {
              range "1..16777214";
            }
          }
          leaf expense {
            type uint32 {
              range "1..16777214";
            }
          }
          leaf error {
            type uint32 {
              range "1..16777214";
            }
          }
        }
        leaf priority {
          description
            "Set priority for Designated Router election";
          type uint8 {
            range "0..127";
          }
        }
        leaf retransmit-interval {
          description
            "Set per-LSP retransmission interval";
          type uint16;
        }
        leaf retransmit-throttle-interval {
          description
            "Set interface LSP retransmission interval";
          type uint16;
        }
      }
      container join-interface {
        description
          "OTV VPN join-interface";
        uses ios-ifc:ncs_rpc_notif_interface-grouping;
      }
      container suppress {
        description
          "Enable overlay packet suppression";
        leaf arp-nd {
          description
            "Suppress sending ARP and neighbor discovery packets on overlay";
          type empty;
        }
      }
      container use-adjacency-server {
        description
          "Point to remote Adjacency Server address";
        leaf remote-pri-ip {
          type inet:ipv4-address;
        }
        leaf remote-sec-ip {
          type inet:ipv4-address;
        }
        leaf unicast-only {
          description
            "Unicast Only Capability";
          type empty;
        }
      }
      leaf vpn-name {
        description
          "OTV VPN name";
        type string;
      }
    }
  }

  grouping ncs_rpc_notif_config-otv-grouping {
    container fragmentation {
      description
        "Clear the DF (Don't Fragment) bit in the IP header";
      container join-interface {
        description
          "Allow fragmentation for overlays using this join-interface";
        uses ios-ifc:ncs_rpc_notif_interface-grouping;
      }
    }
    container isis {
      description
        "OTV ISIS instance subcommands";
      list Overlay {
        description
          "Overlay interface";
        key "number";
        leaf number {
          type uint16 {
            range "0..512";
          }
        }
        uses ncs_rpc_notif_otv-isis-overlay-grouping;
      }
      container site {
        description
          "Site Instance";
        uses ncs_rpc_notif_otv-isis-site-grouping;
      }
    }
    list site {
      description
        "OTV site network configuration";
      key "bridge-domain";
      leaf bridge-domain {
        description
          "Bridge-domain to discover local OTV enabled devices";
        type uint16 {
          range "1..8192";
        }
      }
      container default {
        description
          "Set a command to its defaults";
        container otv {
          description
            "OTV site configuration subcommands";
          uses ncs_rpc_notif_otv-isis-grouping;
        }
      }
      container otv {
        description
          "OTV site configuration subcommands";
        uses ncs_rpc_notif_otv-isis-grouping;
      }
    }
    leaf site-identifier {
      description
        "OTV site id";
      type union {
        type uint32;
        type string;
      }
    }
  }

  grouping ncs_rpc_notif_otv-isis-grouping {
    container isis {
      description
        "ISIS interface subcommands";
      uses ncs_rpc_notif_otv-isis-authentication-grouping;
      leaf bfd {
        description
          "Bidirectional Forwarding Protocol";
        type empty;
      }
      container hello {
        description
          "Add padding to IS-IS hello packets";
        container padding {
          description
            "Pad hello packets";
          presence "true";
          leaf always {
            description
              "Never pad hello packets if no prefix present";
            type empty;
          }
        }
      }
      container hello-interval {
        description
          "Set Hello interval in seconds";
        leaf value {
          type uint16 {
            range "1..65535";
          }
        }
        leaf minimal {
          description
            "Holdtime 1 second, interval depends on multiplier";
          type empty;
        }
      }
      leaf hello-multiplier {
        description
          "Set multiplier for Hello holding time";
        type uint16 {
          range "3..1000";
        }
      }
      leaf priority {
        description
          "Set priority for Designated Router election";
        type uint8 {
          range "0..127";
        }
      }
    }
  }

  grouping ncs_rpc_notif_otv-isis-overlay-grouping {
    uses ncs_rpc_notif_otv-isis-authentication-grouping;
    container default {
      description
        "Set a command to its defaults";
      uses ncs_rpc_notif_otv-isis-authentication-grouping;
      uses ncs_rpc_notif_otv-isis-hostname-grouping;
      leaf delayed-deletion-interval {
        description
          "Set delayed deletion interval";
        type empty;
      }
      leaf log-adjacency-changes {
        description
          "Log changes in adjacency state";
        type empty;
      }
      leaf lsp-gen-interval {
        description
          "Minimum interval between regenerating same LSP";
        type empty;
      }
      leaf lsp-mtu {
        description
          "Set maximum LSP size";
        type empty;
      }
      leaf lsp-refresh-interval {
        description
          "Set LSP refresh interval";
        type empty;
      }
      leaf max-lsp-lifetime {
        description
          "Set maximum LSP lifetime";
        type empty;
      }
      leaf prc-interval {
        description
          "Minimum interval between partial route calculations";
        type empty;
      }
      leaf spf-interval {
        description
          "Minimum interval between SPF calculations";
        type empty;
      }
      container nsf {
        description
          "Non-stop forwarding";
        leaf cisco {
          description
            "Checkpoint method";
          type empty;
        }
        leaf interval {
          description
            "Minimum required stable interval between restarts";
          type empty;
        }
      }
      container skeptical {
        description
          "Be a cautious NSF helper when refresh adjacency";
        leaf interval {
          description
            "Interval during which holdtime will NOT be refreshed";
          type empty;
        }
      }
    }
    leaf delayed-deletion-interval {
      description
        "Set delayed deletion interval";
      type uint32 {
        range "1..86400";
      }
    }
    uses ncs_rpc_notif_otv-isis-hostname-grouping;
    uses ncs_rpc_notif_otv-isis-log-adjacency-changes-grouping;
    container lsp-gen-interval {
      description
        "Minimum interval between regenerating same LSP";
      leaf seconds {
        type uint8 {
          range "1..120";
        }
      }
      leaf milliseconds {
        type uint32 {
          range "1..120000";
        }
      }
      leaf wait {
        type uint32 {
          range "1..120000";
        }
      }
    }
    leaf lsp-mtu {
      description
        "Set maximum LSP size";
      type uint32 {
        range "128..4352";
      }
    }
    leaf lsp-refresh-interval {
      description
        "Set LSP refresh interval";
      type uint32 {
        range "1..65535";
      }
    }
    leaf max-lsp-lifetime {
      description
        "Set maximum LSP lifetime";
      type uint32 {
        range "1..65535";
      }
    }
    container nsf {
      description
        "Non-stop forwarding";
      leaf cisco {
        description
          "Checkpoint method";
        type empty;
      }
      leaf interval {
        description
          "Minimum required stable interval between restarts";
        type uint32 {
          range "0..1440";
        }
      }
    }
    container prc-interval {
      description
        "Minimum interval between partial route calculations";
      leaf seconds {
        type uint8 {
          range "1..120";
        }
      }
      leaf milliseconds {
        type uint32 {
          range "1..120000";
        }
      }
      leaf wait {
        type uint32 {
          range "1..120000";
        }
      }
    }
    uses ncs_rpc_notif_otv-isis-skeptical-grouping;
    container spf-interval {
      description
        "Minimum interval between SPF calculations";
      leaf seconds {
        type uint8 {
          range "1..120";
        }
      }
      leaf milliseconds {
        type uint32 {
          range "1..120000";
        }
      }
      leaf wait {
        type uint32 {
          range "1..120000";
        }
      }
    }
  }

  grouping live_ncs_otv-isis-hostname-grouping {
    container hostname {
      description
        "Dynamic hostname for IS-IS";
      leaf dynamic {
        description
          "Dynamic hostname";
        type empty;
      }
    }
  }

  grouping live_ncs_otv-isis-skeptical-grouping {
    container skeptical {
      description
        "Be a cautious NSF helper when refresh adjacency";
      leaf interval {
        description
          "Interval during which holdtime will NOT be refreshed";
        type uint32 {
          range "0..1440";
        }
      }
    }
  }

  grouping live_ncs_otv-isis-log-adjacency-changes-grouping {
    container log-adjacency-changes {
      description
        "Log changes in adjacency state";
      presence "true";
      leaf all {
        description
          "Include changes generated by non-IIH event";
        type empty;
      }
    }
  }

  grouping live_ncs_otv-isis-site-grouping {
    container default {
      description
        "Set a command to its defaults";
      leaf log-adjacency-changes {
        description
          "Log changes in adjacency state";
        type empty;
      }
      leaf net {
        description
          "A Network Entity Title for this process";
        type empty;
      }
      container skeptical {
        description
          "Be a cautious NSF helper when refresh adjacency";
        leaf interval {
          description
            "Interval during which holdtime will NOT be refreshed";
          type empty;
        }
      }
    }
    uses live_ncs_otv-isis-log-adjacency-changes-grouping;
    leaf net {
      description
        "A Network Entity Title for this process";
      type string;
    }
    uses live_ncs_otv-isis-skeptical-grouping;
  }

  grouping live_ncs_otv-isis-authentication-grouping {
    container authentication {
      description
        "ISIS authentication for interface related PDUs";
      leaf key-chain {
        description
          "Authentication key-chain";
        type string;
      }
      leaf mode {
        description
          "Authentication mode for PDUs";
        type enumeration {
          enum "md5";
          enum "text";
        }
      }
      leaf send-only {
        description
          "Authentication send only, receive ignore";
        type empty;
      }
    }
  }

  grouping live_ncs_interface-overlay-grouping {
    container otv {
      description
        "Configure OTV information";
      container adjacency-server {
        description
          "Indicate if the box is an Adjacency Server";
        leaf unicast-only {
          description
            "Unicast Only";
          type empty;
        }
      }
      leaf control-group {
        description
          "OTV VPN control multicast group";
        type inet:ipv4-address;
      }
      leaf data-group {
        description
          "Multicast group range for data";
        type inet:ipv4-prefix;
      }
      container encapsulation-format {
        description
          "Encapsulation format";
        container ip {
          description
            "Use IP for outer header encapsulation";
          leaf gre {
            description
              "Use GRE middle header encapsulation";
            type empty;
          }
        }
      }
      leaf filter-fhrp {
        description
          "Configure to not forward HSRP, GLBP, and VRRP packets on overlay";
        type empty;
      }
      container isis {
        description
          "ISIS interface subcommands";
        uses live_ncs_otv-isis-authentication-grouping;
        leaf bfd {
          description
            "Bidirectional Forwarding Protocol";
          type empty;
        }
        leaf csnp-interval {
          description
            "Set CSNP interval in seconds";
          type uint16 {
            range "0..65535";
          }
        }
        container hello {
          description
            "Add padding to IS-IS hello packets";
          container padding {
            description
              "Pad hello packets";
            presence "true";
            leaf always {
              description
                "Never pad hello packets if no prefix present";
              type empty;
            }
          }
        }
        container hello-interval {
          description
            "Set Hello interval in seconds";
          leaf value {
            type uint16 {
              range "1..65535";
            }
          }
          leaf minimal {
            description
              "Holdtime 1 second, interval depends on multiplier";
            type empty;
          }
        }
        leaf hello-multiplier {
          description
            "Set multiplier for Hello holding time";
          type uint16 {
            range "3..1000";
          }
        }
        leaf lsp-interval {
          description
            "Set LSP transmission interval";
          type uint64 {
            range "1..4294967295";
          }
        }
        container metric {
          description
            "Configure the metric for interface";
          choice default-maximum {
            case default-case {
              leaf default {
                type uint32 {
                  range "1..16777214";
                }
              }
            }
            case maximum-case {
              leaf maximum {
                description
                  "Maximum metric. All routers will exclude this link from their SPF";
                type empty;
              }
            }
          }
          leaf delay {
            type uint32 {
              range "1..16777214";
            }
          }
          leaf expense {
            type uint32 {
              range "1..16777214";
            }
          }
          leaf error {
            type uint32 {
              range "1..16777214";
            }
          }
        }
        leaf priority {
          description
            "Set priority for Designated Router election";
          type uint8 {
            range "0..127";
          }
        }
        leaf retransmit-interval {
          description
            "Set per-LSP retransmission interval";
          type uint16;
        }
        leaf retransmit-throttle-interval {
          description
            "Set interface LSP retransmission interval";
          type uint16;
        }
      }
      container join-interface {
        description
          "OTV VPN join-interface";
        uses ios-ifc:live_ncs_interface-grouping;
      }
      container suppress {
        description
          "Enable overlay packet suppression";
        leaf arp-nd {
          description
            "Suppress sending ARP and neighbor discovery packets on overlay";
          type empty;
        }
      }
      container use-adjacency-server {
        description
          "Point to remote Adjacency Server address";
        leaf remote-pri-ip {
          type inet:ipv4-address;
        }
        leaf remote-sec-ip {
          type inet:ipv4-address;
        }
        leaf unicast-only {
          description
            "Unicast Only Capability";
          type empty;
        }
      }
      leaf vpn-name {
        description
          "OTV VPN name";
        type string;
      }
    }
  }

  grouping live_ncs_config-otv-grouping {
    container fragmentation {
      description
        "Clear the DF (Don't Fragment) bit in the IP header";
      container join-interface {
        description
          "Allow fragmentation for overlays using this join-interface";
        uses ios-ifc:live_ncs_interface-grouping;
      }
    }
    container isis {
      description
        "OTV ISIS instance subcommands";
      list Overlay {
        description
          "Overlay interface";
        key "number";
        leaf number {
          type uint16 {
            range "0..512";
          }
        }
        uses live_ncs_otv-isis-overlay-grouping;
      }
      container site {
        description
          "Site Instance";
        uses live_ncs_otv-isis-site-grouping;
      }
    }
    list site {
      description
        "OTV site network configuration";
      key "bridge-domain";
      leaf bridge-domain {
        description
          "Bridge-domain to discover local OTV enabled devices";
        type uint16 {
          range "1..8192";
        }
      }
      container default {
        description
          "Set a command to its defaults";
        container otv {
          description
            "OTV site configuration subcommands";
          uses live_ncs_otv-isis-grouping;
        }
      }
      container otv {
        description
          "OTV site configuration subcommands";
        uses live_ncs_otv-isis-grouping;
      }
    }
    leaf site-identifier {
      description
        "OTV site id";
      type union {
        type uint32;
        type string;
      }
    }
  }

  grouping live_ncs_otv-isis-grouping {
    container isis {
      description
        "ISIS interface subcommands";
      uses live_ncs_otv-isis-authentication-grouping;
      leaf bfd {
        description
          "Bidirectional Forwarding Protocol";
        type empty;
      }
      container hello {
        description
          "Add padding to IS-IS hello packets";
        container padding {
          description
            "Pad hello packets";
          presence "true";
          leaf always {
            description
              "Never pad hello packets if no prefix present";
            type empty;
          }
        }
      }
      container hello-interval {
        description
          "Set Hello interval in seconds";
        leaf value {
          type uint16 {
            range "1..65535";
          }
        }
        leaf minimal {
          description
            "Holdtime 1 second, interval depends on multiplier";
          type empty;
        }
      }
      leaf hello-multiplier {
        description
          "Set multiplier for Hello holding time";
        type uint16 {
          range "3..1000";
        }
      }
      leaf priority {
        description
          "Set priority for Designated Router election";
        type uint8 {
          range "0..127";
        }
      }
    }
  }

  grouping live_ncs_otv-isis-overlay-grouping {
    uses live_ncs_otv-isis-authentication-grouping;
    container default {
      description
        "Set a command to its defaults";
      uses live_ncs_otv-isis-authentication-grouping;
      uses live_ncs_otv-isis-hostname-grouping;
      leaf delayed-deletion-interval {
        description
          "Set delayed deletion interval";
        type empty;
      }
      leaf log-adjacency-changes {
        description
          "Log changes in adjacency state";
        type empty;
      }
      leaf lsp-gen-interval {
        description
          "Minimum interval between regenerating same LSP";
        type empty;
      }
      leaf lsp-mtu {
        description
          "Set maximum LSP size";
        type empty;
      }
      leaf lsp-refresh-interval {
        description
          "Set LSP refresh interval";
        type empty;
      }
      leaf max-lsp-lifetime {
        description
          "Set maximum LSP lifetime";
        type empty;
      }
      leaf prc-interval {
        description
          "Minimum interval between partial route calculations";
        type empty;
      }
      leaf spf-interval {
        description
          "Minimum interval between SPF calculations";
        type empty;
      }
      container nsf {
        description
          "Non-stop forwarding";
        leaf cisco {
          description
            "Checkpoint method";
          type empty;
        }
        leaf interval {
          description
            "Minimum required stable interval between restarts";
          type empty;
        }
      }
      container skeptical {
        description
          "Be a cautious NSF helper when refresh adjacency";
        leaf interval {
          description
            "Interval during which holdtime will NOT be refreshed";
          type empty;
        }
      }
    }
    leaf delayed-deletion-interval {
      description
        "Set delayed deletion interval";
      type uint32 {
        range "1..86400";
      }
    }
    uses live_ncs_otv-isis-hostname-grouping;
    uses live_ncs_otv-isis-log-adjacency-changes-grouping;
    container lsp-gen-interval {
      description
        "Minimum interval between regenerating same LSP";
      leaf seconds {
        type uint8 {
          range "1..120";
        }
      }
      leaf milliseconds {
        type uint32 {
          range "1..120000";
        }
      }
      leaf wait {
        type uint32 {
          range "1..120000";
        }
      }
    }
    leaf lsp-mtu {
      description
        "Set maximum LSP size";
      type uint32 {
        range "128..4352";
      }
    }
    leaf lsp-refresh-interval {
      description
        "Set LSP refresh interval";
      type uint32 {
        range "1..65535";
      }
    }
    leaf max-lsp-lifetime {
      description
        "Set maximum LSP lifetime";
      type uint32 {
        range "1..65535";
      }
    }
    container nsf {
      description
        "Non-stop forwarding";
      leaf cisco {
        description
          "Checkpoint method";
        type empty;
      }
      leaf interval {
        description
          "Minimum required stable interval between restarts";
        type uint32 {
          range "0..1440";
        }
      }
    }
    container prc-interval {
      description
        "Minimum interval between partial route calculations";
      leaf seconds {
        type uint8 {
          range "1..120";
        }
      }
      leaf milliseconds {
        type uint32 {
          range "1..120000";
        }
      }
      leaf wait {
        type uint32 {
          range "1..120000";
        }
      }
    }
    uses live_ncs_otv-isis-skeptical-grouping;
    container spf-interval {
      description
        "Minimum interval between SPF calculations";
      leaf seconds {
        type uint8 {
          range "1..120";
        }
      }
      leaf milliseconds {
        type uint32 {
          range "1..120000";
        }
      }
      leaf wait {
        type uint32 {
          range "1..120000";
        }
      }
    }
  }

  grouping otv-isis-hostname-grouping {
    container hostname {
      description
        "Dynamic hostname for IS-IS";
      leaf dynamic {
        description
          "Dynamic hostname";
        type empty;
      }
    }
  }

  grouping otv-isis-skeptical-grouping {
    container skeptical {
      description
        "Be a cautious NSF helper when refresh adjacency";
      leaf interval {
        description
          "Interval during which holdtime will NOT be refreshed";
        type uint32 {
          range "0..1440";
        }
      }
    }
  }

  grouping otv-isis-log-adjacency-changes-grouping {
    container log-adjacency-changes {
      description
        "Log changes in adjacency state";
      presence "true";
      leaf all {
        description
          "Include changes generated by non-IIH event";
        type empty;
      }
    }
  }

  grouping otv-isis-site-grouping {
    container default {
      description
        "Set a command to its defaults";
      leaf log-adjacency-changes {
        description
          "Log changes in adjacency state";
        type empty;
      }
      leaf net {
        description
          "A Network Entity Title for this process";
        type empty;
      }
      container skeptical {
        description
          "Be a cautious NSF helper when refresh adjacency";
        leaf interval {
          description
            "Interval during which holdtime will NOT be refreshed";
          type empty;
        }
      }
    }
    uses otv-isis-log-adjacency-changes-grouping;
    leaf net {
      description
        "A Network Entity Title for this process";
      type string;
    }
    uses otv-isis-skeptical-grouping;
  }

  grouping otv-isis-authentication-grouping {
    container authentication {
      description
        "ISIS authentication for interface related PDUs";
      leaf key-chain {
        description
          "Authentication key-chain";
        type string;
      }
      leaf mode {
        description
          "Authentication mode for PDUs";
        type enumeration {
          enum "md5";
          enum "text";
        }
      }
      leaf send-only {
        description
          "Authentication send only, receive ignore";
        type empty;
      }
    }
  }

  grouping interface-overlay-grouping {
    container otv {
      description
        "Configure OTV information";
      container adjacency-server {
        description
          "Indicate if the box is an Adjacency Server";
        leaf unicast-only {
          description
            "Unicast Only";
          type empty;
        }
      }
      leaf control-group {
        description
          "OTV VPN control multicast group";
        type inet:ipv4-address;
      }
      leaf data-group {
        description
          "Multicast group range for data";
        type inet:ipv4-prefix;
      }
      container encapsulation-format {
        description
          "Encapsulation format";
        container ip {
          description
            "Use IP for outer header encapsulation";
          leaf gre {
            description
              "Use GRE middle header encapsulation";
            type empty;
          }
        }
      }
      leaf filter-fhrp {
        description
          "Configure to not forward HSRP, GLBP, and VRRP packets on overlay";
        type empty;
      }
      container isis {
        description
          "ISIS interface subcommands";
        uses otv-isis-authentication-grouping;
        leaf bfd {
          description
            "Bidirectional Forwarding Protocol";
          type empty;
        }
        leaf csnp-interval {
          description
            "Set CSNP interval in seconds";
          type uint16 {
            range "0..65535";
          }
        }
        container hello {
          description
            "Add padding to IS-IS hello packets";
          container padding {
            description
              "Pad hello packets";
            presence "true";
            leaf always {
              description
                "Never pad hello packets if no prefix present";
              type empty;
            }
          }
        }
        container hello-interval {
          description
            "Set Hello interval in seconds";
          leaf value {
            type uint16 {
              range "1..65535";
            }
          }
          leaf minimal {
            description
              "Holdtime 1 second, interval depends on multiplier";
            type empty;
          }
        }
        leaf hello-multiplier {
          description
            "Set multiplier for Hello holding time";
          type uint16 {
            range "3..1000";
          }
        }
        leaf lsp-interval {
          description
            "Set LSP transmission interval";
          type uint64 {
            range "1..4294967295";
          }
        }
        container metric {
          description
            "Configure the metric for interface";
          choice default-maximum {
            case default-case {
              leaf default {
                type uint32 {
                  range "1..16777214";
                }
              }
            }
            case maximum-case {
              leaf maximum {
                description
                  "Maximum metric. All routers will exclude this link from their SPF";
                type empty;
              }
            }
          }
          leaf delay {
            type uint32 {
              range "1..16777214";
            }
          }
          leaf expense {
            type uint32 {
              range "1..16777214";
            }
          }
          leaf error {
            type uint32 {
              range "1..16777214";
            }
          }
        }
        leaf priority {
          description
            "Set priority for Designated Router election";
          type uint8 {
            range "0..127";
          }
        }
        leaf retransmit-interval {
          description
            "Set per-LSP retransmission interval";
          type uint16;
        }
        leaf retransmit-throttle-interval {
          description
            "Set interface LSP retransmission interval";
          type uint16;
        }
      }
      container join-interface {
        description
          "OTV VPN join-interface";
        uses ios-ifc:interface-grouping;
      }
      container suppress {
        description
          "Enable overlay packet suppression";
        leaf arp-nd {
          description
            "Suppress sending ARP and neighbor discovery packets on overlay";
          type empty;
        }
      }
      container use-adjacency-server {
        description
          "Point to remote Adjacency Server address";
        leaf remote-pri-ip {
          type inet:ipv4-address;
        }
        leaf remote-sec-ip {
          type inet:ipv4-address;
        }
        leaf unicast-only {
          description
            "Unicast Only Capability";
          type empty;
        }
      }
      leaf vpn-name {
        description
          "OTV VPN name";
        type string;
      }
    }
  }

  grouping config-otv-grouping {
    container fragmentation {
      description
        "Clear the DF (Don't Fragment) bit in the IP header";
      container join-interface {
        description
          "Allow fragmentation for overlays using this join-interface";
        uses ios-ifc:interface-grouping;
      }
    }
    container isis {
      description
        "OTV ISIS instance subcommands";
      list Overlay {
        description
          "Overlay interface";
        key "number";
        leaf number {
          type uint16 {
            range "0..512";
          }
        }
        uses otv-isis-overlay-grouping;
      }
      container site {
        description
          "Site Instance";
        uses otv-isis-site-grouping;
      }
    }
    list site {
      description
        "OTV site network configuration";
      key "bridge-domain";
      leaf bridge-domain {
        description
          "Bridge-domain to discover local OTV enabled devices";
        type uint16 {
          range "1..8192";
        }
      }
      container default {
        description
          "Set a command to its defaults";
        container otv {
          description
            "OTV site configuration subcommands";
          uses otv-isis-grouping;
        }
      }
      container otv {
        description
          "OTV site configuration subcommands";
        uses otv-isis-grouping;
      }
    }
    leaf site-identifier {
      description
        "OTV site id";
      type union {
        type uint32;
        type string;
      }
    }
  }

  grouping otv-isis-grouping {
    container isis {
      description
        "ISIS interface subcommands";
      uses otv-isis-authentication-grouping;
      leaf bfd {
        description
          "Bidirectional Forwarding Protocol";
        type empty;
      }
      container hello {
        description
          "Add padding to IS-IS hello packets";
        container padding {
          description
            "Pad hello packets";
          presence "true";
          leaf always {
            description
              "Never pad hello packets if no prefix present";
            type empty;
          }
        }
      }
      container hello-interval {
        description
          "Set Hello interval in seconds";
        leaf value {
          type uint16 {
            range "1..65535";
          }
        }
        leaf minimal {
          description
            "Holdtime 1 second, interval depends on multiplier";
          type empty;
        }
      }
      leaf hello-multiplier {
        description
          "Set multiplier for Hello holding time";
        type uint16 {
          range "3..1000";
        }
      }
      leaf priority {
        description
          "Set priority for Designated Router election";
        type uint8 {
          range "0..127";
        }
      }
    }
  }

  grouping otv-isis-overlay-grouping {
    uses otv-isis-authentication-grouping;
    container default {
      description
        "Set a command to its defaults";
      uses otv-isis-authentication-grouping;
      uses otv-isis-hostname-grouping;
      leaf delayed-deletion-interval {
        description
          "Set delayed deletion interval";
        type empty;
      }
      leaf log-adjacency-changes {
        description
          "Log changes in adjacency state";
        type empty;
      }
      leaf lsp-gen-interval {
        description
          "Minimum interval between regenerating same LSP";
        type empty;
      }
      leaf lsp-mtu {
        description
          "Set maximum LSP size";
        type empty;
      }
      leaf lsp-refresh-interval {
        description
          "Set LSP refresh interval";
        type empty;
      }
      leaf max-lsp-lifetime {
        description
          "Set maximum LSP lifetime";
        type empty;
      }
      leaf prc-interval {
        description
          "Minimum interval between partial route calculations";
        type empty;
      }
      leaf spf-interval {
        description
          "Minimum interval between SPF calculations";
        type empty;
      }
      container nsf {
        description
          "Non-stop forwarding";
        leaf cisco {
          description
            "Checkpoint method";
          type empty;
        }
        leaf interval {
          description
            "Minimum required stable interval between restarts";
          type empty;
        }
      }
      container skeptical {
        description
          "Be a cautious NSF helper when refresh adjacency";
        leaf interval {
          description
            "Interval during which holdtime will NOT be refreshed";
          type empty;
        }
      }
    }
    leaf delayed-deletion-interval {
      description
        "Set delayed deletion interval";
      type uint32 {
        range "1..86400";
      }
    }
    uses otv-isis-hostname-grouping;
    uses otv-isis-log-adjacency-changes-grouping;
    container lsp-gen-interval {
      description
        "Minimum interval between regenerating same LSP";
      leaf seconds {
        type uint8 {
          range "1..120";
        }
      }
      leaf milliseconds {
        type uint32 {
          range "1..120000";
        }
      }
      leaf wait {
        type uint32 {
          range "1..120000";
        }
      }
    }
    leaf lsp-mtu {
      description
        "Set maximum LSP size";
      type uint32 {
        range "128..4352";
      }
    }
    leaf lsp-refresh-interval {
      description
        "Set LSP refresh interval";
      type uint32 {
        range "1..65535";
      }
    }
    leaf max-lsp-lifetime {
      description
        "Set maximum LSP lifetime";
      type uint32 {
        range "1..65535";
      }
    }
    container nsf {
      description
        "Non-stop forwarding";
      leaf cisco {
        description
          "Checkpoint method";
        type empty;
      }
      leaf interval {
        description
          "Minimum required stable interval between restarts";
        type uint32 {
          range "0..1440";
        }
      }
    }
    container prc-interval {
      description
        "Minimum interval between partial route calculations";
      leaf seconds {
        type uint8 {
          range "1..120";
        }
      }
      leaf milliseconds {
        type uint32 {
          range "1..120000";
        }
      }
      leaf wait {
        type uint32 {
          range "1..120000";
        }
      }
    }
    uses otv-isis-skeptical-grouping;
    container spf-interval {
      description
        "Minimum interval between SPF calculations";
      leaf seconds {
        type uint8 {
          range "1..120";
        }
      }
      leaf milliseconds {
        type uint32 {
          range "1..120000";
        }
      }
      leaf wait {
        type uint32 {
          range "1..120000";
        }
      }
    }
  }

  augment "/ncs:devices/ncs:template/ncs:config/ios:native/ios:otv" {
    uses ncs_template_config-otv-grouping;
  }
  augment "/ncs:devices/ncs:device/ncs:live-status/ios:native/ios:otv" {
    uses live_ncs_config-otv-grouping {
      refine site-identifier {
        tailf:ncs-device-type "netconf";
        tailf:display-when "not(../../../../ncs:module) or ../../../../ncs:module[ncs:name='Cisco-IOS-XE-otv'] or (../../../../ncs:live-status-protocol[not(ncs:capability)]) or (../../../../ncs:live-status-protocol/ncs:capability/ncs:module[.='Cisco-IOS-XE-otv'])";
      }
      refine site {
        tailf:ncs-device-type "netconf";
        tailf:display-when "not(../../../ncs:module) or ../../../ncs:module[ncs:name='Cisco-IOS-XE-otv'] or (../../../ncs:live-status-protocol[not(ncs:capability)]) or (../../../ncs:live-status-protocol/ncs:capability/ncs:module[.='Cisco-IOS-XE-otv'])";
      }
      refine isis {
        tailf:ncs-device-type "netconf";
        tailf:display-when "not(../../../../ncs:module) or ../../../../ncs:module[ncs:name='Cisco-IOS-XE-otv'] or (../../../../ncs:live-status-protocol[not(ncs:capability)]) or (../../../../ncs:live-status-protocol/ncs:capability/ncs:module[.='Cisco-IOS-XE-otv'])";
      }
      refine fragmentation {
        tailf:ncs-device-type "netconf";
        tailf:display-when "not(../../../../ncs:module) or ../../../../ncs:module[ncs:name='Cisco-IOS-XE-otv'] or (../../../../ncs:live-status-protocol[not(ncs:capability)]) or (../../../../ncs:live-status-protocol/ncs:capability/ncs:module[.='Cisco-IOS-XE-otv'])";
      }
    }
  }
  augment "/ncs:devices/ncs:device/ncs:config/ios:native/ios:otv" {
    uses config-otv-grouping {
      refine site-identifier {
        tailf:ncs-device-type "netconf";
        tailf:display-when "not(../../../../ncs:module) or ../../../../ncs:module[ncs:name='Cisco-IOS-XE-otv']";
      }
      refine site {
        tailf:ncs-device-type "netconf";
        tailf:display-when "not(../../../ncs:module) or ../../../ncs:module[ncs:name='Cisco-IOS-XE-otv']";
      }
      refine isis {
        tailf:ncs-device-type "netconf";
        tailf:display-when "not(../../../../ncs:module) or ../../../../ncs:module[ncs:name='Cisco-IOS-XE-otv']";
      }
      refine fragmentation {
        tailf:ncs-device-type "netconf";
        tailf:display-when "not(../../../../ncs:module) or ../../../../ncs:module[ncs:name='Cisco-IOS-XE-otv']";
      }
    }
  }
  augment "/ncs:devices/ncs:template/ncs:config/ios:native/ios:interface/ios:overlay" {
    uses ios:ncs_template_interface-common-grouping;
    uses ios-eth:ncs_template_config-interface-ethernet-grouping;
    uses ios-otv:ncs_template_interface-overlay-grouping;
  }
  augment "/ncs:devices/ncs:device/ncs:live-status/ios:native/ios:interface/ios:overlay" {
    uses ios:live_ncs_interface-common-grouping {
      refine pm-path {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine peer {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine rcv-queue {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine priority-queue {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine utd {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine trust {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine storm-control {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine access-session {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine standby {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine service-insertion {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine interface_qos {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine mtu {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine max-reserved-bandwidth {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine mop {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine mdix {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine logging {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine load-interval {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine ipv6 {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine ip {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine vrf-choice;
      refine mpls {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine hold-queue {
        tailf:ncs-device-type "netconf";
        tailf:display-when "not(../../../../ncs:module) or ../../../../ncs:module[ncs:name='Cisco-IOS-XE-otv'] or (../../../../ncs:live-status-protocol[not(ncs:capability)]) or (../../../../ncs:live-status-protocol/ncs:capability/ncs:module[.='Cisco-IOS-XE-otv'])";
      }
      refine domain {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine delay {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine if-state {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine dampening {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine bandwidth {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine bfd {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine keepalive-choice;
      refine isis {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine flowcontrol {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine fair-queue {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine fair-queue-conf {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine encapsulation {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine l2protocol-tunnel {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine cws-tunnel {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine cemoudp {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine backup {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine arp {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine shutdown {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine mac-address {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine switchport {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine switchport-conf {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine description {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
    }
    uses ios-eth:live_ncs_config-interface-ethernet-grouping {
      refine service {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine pppoe {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine plim {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine speed {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine duplex {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine synchronous {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine negotiation {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine ethernet {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine channel-protocol {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine channel-group {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
      refine carrier-delay {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
    }
    uses ios-otv:live_ncs_interface-overlay-grouping {
      refine otv {
        tailf:ncs-device-type "netconf";
        tailf:display-when "not(../../../../../ncs:module) or ../../../../../ncs:module[ncs:name='Cisco-IOS-XE-otv'] or (../../../../../ncs:live-status-protocol[not(ncs:capability)]) or (../../../../../ncs:live-status-protocol/ncs:capability/ncs:module[.='Cisco-IOS-XE-otv'])";
      }
    }
  }
  augment "/ncs:devices/ncs:device/ncs:config/ios:native/ios:interface/ios:overlay" {
    uses ios:interface-common-grouping {
      refine pm-path {
        tailf:ncs-device-type "netconf";
        tailf:display-when "not(../../../../../ncs:module) or ../../../../../ncs:module[ncs:name='Cisco-IOS-XE-otv']";
      }
      refine peer {
        tailf:ncs-device-type "netconf";
        tailf:display-when "not(../../../../../ncs:module) or ../../../../../ncs:module[ncs:name='Cisco-IOS-XE-otv']";
      }
      refine rcv-queue {
        tailf:ncs-device-type "netconf";
        tailf:display-when "not(../../../../../ncs:module) or ../../../../../ncs:module[ncs:name='Cisco-IOS-XE-otv']";
      }
      refine priority-queue {
        tailf:ncs-device-type "netconf";
        tailf:display-when "not(../../../../../ncs:module) or ../../../../../ncs:module[ncs:name='Cisco-IOS-XE-otv']";
      }
      refine utd {
        tailf:ncs-device-type "netconf";
        tailf:display-when "not(../../../../../ncs:module) or ../../../../../ncs:module[ncs:name='Cisco-IOS-XE-otv']";
      }
      refine trust {
        tailf:ncs-device-type "netconf";
        tailf:display-when "not(../../../../../ncs:module) or ../../../../../ncs:module[ncs:name='Cisco-IOS-XE-otv']";
      }
      refine storm-control {
        tailf:ncs-device-type "netconf";
        tailf:display-when "not(../../../../../ncs:module) or ../../../../../ncs:module[ncs:name='Cisco-IOS-XE-otv']";
      }
      refine access-session {
        tailf:ncs-device-type "netconf";
        tailf:display-when "not(../../../../../ncs:module) or ../../../../../ncs:module[ncs:name='Cisco-IOS-XE-otv']";
      }
      refine standby {
        tailf:ncs-device-type "netconf";
        tailf:display-when "not(../../../../../ncs:module) or ../../../../../ncs:module[ncs:name='Cisco-IOS-XE-otv']";
      }
      refine service-insertion {
        tailf:ncs-device-type "netconf";
        tailf:display-when "not(../../../../../ncs:module) or ../../../../../ncs:module[ncs:name='Cisco-IOS-XE-otv']";
      }
      refine interface_qos {
        tailf:ncs-device-type "netconf";
        tailf:display-when "not(../../../../../ncs:module) or ../../../../../ncs:module[ncs:name='Cisco-IOS-XE-otv']";
      }
      refine mtu {
        tailf:ncs-device-type "netconf";
        tailf:display-when "not(../../../../../ncs:module) or ../../../../../ncs:module[ncs:name='Cisco-IOS-XE-otv']";
      }
      refine max-reserved-bandwidth {
        tailf:ncs-device-type "netconf";
        tailf:display-when "not(../../../../../ncs:module) or ../../../../../ncs:module[ncs:name='Cisco-IOS-XE-otv']";
      }
      refine mop {
        tailf:ncs-device-type "netconf";
        tailf:display-when "not(../../../../../ncs:module) or ../../../../../ncs:module[ncs:name='Cisco-IOS-XE-otv']";
      }
      refine mdix {
        tailf:ncs-device-type "netconf";
        tailf:display-when "not(../../../../../ncs:module) or ../../../../../ncs:module[ncs:name='Cisco-IOS-XE-otv']";
      }
      refine logging {
        tailf:ncs-device-type "netconf";
        tailf:display-when "not(../../../../../ncs:module) or ../../../../../ncs:module[ncs:name='Cisco-IOS-XE-otv']";
      }
      refine load-interval {
        tailf:ncs-device-type "netconf";
        tailf:display-when "not(../../../../../ncs:module) or ../../../../../ncs:module[ncs:name='Cisco-IOS-XE-otv']";
      }
      refine ipv6 {
        tailf:ncs-device-type "netconf";
        tailf:display-when "not(../../../../../ncs:module) or ../../../../../ncs:module[ncs:name='Cisco-IOS-XE-otv']";
      }
      refine ip {
        tailf:ncs-device-type "netconf";
        tailf:display-when "not(../../../../../ncs:module) or ../../../../../ncs:module[ncs:name='Cisco-IOS-XE-otv']";
      }
      refine vrf-choice;
      refine mpls {
        tailf:ncs-device-type "netconf";
        tailf:display-when "not(../../../../../ncs:module) or ../../../../../ncs:module[ncs:name='Cisco-IOS-XE-otv']";
      }
      refine hold-queue {
        tailf:ncs-device-type "netconf";
        tailf:display-when "not(../../../../ncs:module) or ../../../../ncs:module[ncs:name='Cisco-IOS-XE-otv']";
      }
      refine domain {
        tailf:ncs-device-type "netconf";
        tailf:display-when "not(../../../../../ncs:module) or ../../../../../ncs:module[ncs:name='Cisco-IOS-XE-otv']";
      }
      refine delay {
        tailf:ncs-device-type "netconf";
        tailf:display-when "not(../../../../../ncs:module) or ../../../../../ncs:module[ncs:name='Cisco-IOS-XE-otv']";
      }
      refine if-state {
        tailf:ncs-device-type "netconf";
        tailf:display-when "not(../../../../../ncs:module) or ../../../../../ncs:module[ncs:name='Cisco-IOS-XE-otv']";
      }
      refine dampening {
        tailf:ncs-device-type "netconf";
        tailf:display-when "not(../../../../../ncs:module) or ../../../../../ncs:module[ncs:name='Cisco-IOS-XE-otv']";
      }
      refine bandwidth {
        tailf:ncs-device-type "netconf";
        tailf:display-when "not(../../../../../ncs:module) or ../../../../../ncs:module[ncs:name='Cisco-IOS-XE-otv']";
      }
      refine bfd {
        tailf:ncs-device-type "netconf";
        tailf:display-when "not(../../../../../ncs:module) or ../../../../../ncs:module[ncs:name='Cisco-IOS-XE-otv']";
      }
      refine keepalive-choice;
      refine isis {
        tailf:ncs-device-type "netconf";
        tailf:display-when "not(../../../../../ncs:module) or ../../../../../ncs:module[ncs:name='Cisco-IOS-XE-otv']";
      }
      refine flowcontrol {
        tailf:ncs-device-type "netconf";
        tailf:display-when "not(../../../../../ncs:module) or ../../../../../ncs:module[ncs:name='Cisco-IOS-XE-otv']";
      }
      refine fair-queue {
        tailf:ncs-device-type "netconf";
        tailf:display-when "not(../../../../../ncs:module) or ../../../../../ncs:module[ncs:name='Cisco-IOS-XE-otv']";
      }
      refine fair-queue-conf {
        tailf:ncs-device-type "netconf";
        tailf:display-when "not(../../../../../ncs:module) or ../../../../../ncs:module[ncs:name='Cisco-IOS-XE-otv']";
      }
      refine encapsulation {
        tailf:ncs-device-type "netconf";
        tailf:display-when "not(../../../../../ncs:module) or ../../../../../ncs:module[ncs:name='Cisco-IOS-XE-otv']";
      }
      refine l2protocol-tunnel {
        tailf:ncs-device-type "netconf";
        tailf:display-when "not(../../../../../ncs:module) or ../../../../../ncs:module[ncs:name='Cisco-IOS-XE-otv']";
      }
      refine cws-tunnel {
        tailf:ncs-device-type "netconf";
        tailf:display-when "not(../../../../../ncs:module) or ../../../../../ncs:module[ncs:name='Cisco-IOS-XE-otv']";
      }
      refine cemoudp {
        tailf:ncs-device-type "netconf";
        tailf:display-when "not(../../../../../ncs:module) or ../../../../../ncs:module[ncs:name='Cisco-IOS-XE-otv']";
      }
      refine backup {
        tailf:ncs-device-type "netconf";
        tailf:display-when "not(../../../../../ncs:module) or ../../../../../ncs:module[ncs:name='Cisco-IOS-XE-otv']";
      }
      refine arp {
        tailf:ncs-device-type "netconf";
        tailf:display-when "not(../../../../../ncs:module) or ../../../../../ncs:module[ncs:name='Cisco-IOS-XE-otv']";
      }
      refine shutdown {
        tailf:ncs-device-type "netconf";
        tailf:display-when "not(../../../../../ncs:module) or ../../../../../ncs:module[ncs:name='Cisco-IOS-XE-otv']";
      }
      refine mac-address {
        tailf:ncs-device-type "netconf";
        tailf:display-when "not(../../../../../ncs:module) or ../../../../../ncs:module[ncs:name='Cisco-IOS-XE-otv']";
      }
      refine switchport {
        tailf:ncs-device-type "netconf";
        tailf:display-when "not(../../../../../ncs:module) or ../../../../../ncs:module[ncs:name='Cisco-IOS-XE-otv']";
      }
      refine switchport-conf {
        tailf:ncs-device-type "netconf";
        tailf:display-when "not(../../../../../ncs:module) or ../../../../../ncs:module[ncs:name='Cisco-IOS-XE-otv']";
      }
      refine description {
        tailf:ncs-device-type "netconf";
        tailf:display-when "not(../../../../../ncs:module) or ../../../../../ncs:module[ncs:name='Cisco-IOS-XE-otv']";
      }
    }
    uses ios-eth:config-interface-ethernet-grouping {
      refine service {
        tailf:ncs-device-type "netconf";
        tailf:display-when "not(../../../../../ncs:module) or ../../../../../ncs:module[ncs:name='Cisco-IOS-XE-otv']";
      }
      refine pppoe {
        tailf:ncs-device-type "netconf";
        tailf:display-when "not(../../../../../ncs:module) or ../../../../../ncs:module[ncs:name='Cisco-IOS-XE-otv']";
      }
      refine plim {
        tailf:ncs-device-type "netconf";
        tailf:display-when "not(../../../../../ncs:module) or ../../../../../ncs:module[ncs:name='Cisco-IOS-XE-otv']";
      }
      refine speed {
        tailf:ncs-device-type "netconf";
        tailf:display-when "not(../../../../../ncs:module) or ../../../../../ncs:module[ncs:name='Cisco-IOS-XE-otv']";
      }
      refine duplex {
        tailf:ncs-device-type "netconf";
        tailf:display-when "not(../../../../../ncs:module) or ../../../../../ncs:module[ncs:name='Cisco-IOS-XE-otv']";
      }
      refine synchronous {
        tailf:ncs-device-type "netconf";
        tailf:display-when "not(../../../../../ncs:module) or ../../../../../ncs:module[ncs:name='Cisco-IOS-XE-otv']";
      }
      refine negotiation {
        tailf:ncs-device-type "netconf";
        tailf:display-when "not(../../../../../ncs:module) or ../../../../../ncs:module[ncs:name='Cisco-IOS-XE-otv']";
      }
      refine ethernet {
        tailf:ncs-device-type "netconf";
        tailf:display-when "not(../../../../../ncs:module) or ../../../../../ncs:module[ncs:name='Cisco-IOS-XE-otv']";
      }
      refine channel-protocol {
        tailf:ncs-device-type "netconf";
        tailf:display-when "not(../../../../../ncs:module) or ../../../../../ncs:module[ncs:name='Cisco-IOS-XE-otv']";
      }
      refine channel-group {
        tailf:ncs-device-type "netconf";
        tailf:display-when "not(../../../../../ncs:module) or ../../../../../ncs:module[ncs:name='Cisco-IOS-XE-otv']";
      }
      refine carrier-delay {
        tailf:ncs-device-type "netconf";
        tailf:display-when "not(../../../../../ncs:module) or ../../../../../ncs:module[ncs:name='Cisco-IOS-XE-otv']";
      }
    }
    uses ios-otv:interface-overlay-grouping {
      refine otv {
        tailf:ncs-device-type "netconf";
        tailf:display-when "not(../../../../../ncs:module) or ../../../../../ncs:module[ncs:name='Cisco-IOS-XE-otv']";
      }
    }
  }
}
