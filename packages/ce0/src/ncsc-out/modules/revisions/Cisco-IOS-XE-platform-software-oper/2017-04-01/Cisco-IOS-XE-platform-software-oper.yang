module Cisco-IOS-XE-platform-software-oper {
  // Generated by yanger -t ncs
  tailf:ncs-device-type "netconf";

  yang-version "1";
  namespace "http://cisco.com/ns/yang/Cisco-IOS-XE-platform-software-oper";
  prefix platform-sw-ios-xe-oper;

  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring platform software in a Network Element";

  revision 2017-04-01 {
    description
      "New location data types. Leaf name changes";
    reference "2.0.0";
  }
  revision 2017-02-07 {
    description
      "Initial revision";
    reference "1.0.0";
  }

  typedef b-fru {
    type enumeration {
      enum "platform-fru-rp" {
        value 0;
      }
      enum "platform-fru-fp" {
        value 1;
      }
      enum "platform-fru-cc" {
        value 2;
      }
      enum "platform-fru-max" {
        value 3;
      }
    }
    description
      "FRU type";
  }

  grouping ncs_template_svc-loc {
    description
      "Service location details";
    leaf fru {
      type string;
      description
        "Field replaceable unit";
    }
    leaf slotnum {
      type string;
      description
        "Slot number";
    }
    leaf baynum {
      type string;
      description
        "Bay number";
    }
    leaf chassisnum {
      type string;
      description
        "Chassis number";
    }
  }

  grouping ncs_template_min-status {
    description
      "Load average statistics minute status";
    leaf condition {
      type string;
      description
        "Load average condition";
    }
    leaf threshold-status {
      type string;
      description
        "Load average status";
    }
    leaf threshold-value {
      type string;
      description
        "Load average threshold";
    }
  }

  grouping ncs_template_minute {
    description
      "Average calculated over a period of time";
    leaf number {
      type string;
      description
        "The number of minutes the average was calculated on";
    }
    leaf average {
      type string;
      description
        "Calculated average";
    }
    container status {
      description
        "Load average statistics minute status";
      uses platform-sw-ios-xe-oper:ncs_template_min-status;
    }
  }

  grouping ncs_template_load-average-stats {
    description
      "Statistics on the load average";
    leaf load-average-status {
      type string;
      description
        "Load average status";
    }
  }

  grouping ncs_template_memory-status {
    description
      "Memory statistics status";
    leaf warning-threshold-percent {
      type string;
      description
        "Memory warning threshold value percent";
    }
    leaf critical-threshold-percent {
      type string;
      description
        "Memory critical threshold value percent";
    }
  }

  grouping ncs_template_platform-memory-stats {
    description
      "Platform memory statistics status";
    leaf memory-status {
      type string;
      description
        "The status of the memory";
    }
    leaf total {
      type string;
      description
        "The total amount of memory in kb";
    }
    leaf used-number {
      type string;
      description
        "The amount of memory being used in kb";
    }
    leaf used-percent {
      type string;
      description
        "The percentage of memory being used";
    }
    leaf free-number {
      type string;
      description
        "The amount of free memory in kb";
    }
    leaf free-percent {
      type string;
      description
        "The percentage of free memory";
    }
    leaf available-number {
      type string;
      description
        "The amount of available memory in kb";
    }
    leaf available-percent {
      type string;
      description
        "The percentage of available memory";
    }
    leaf committed-number {
      type string;
      description
        "The amount of committed memory in kb";
    }
    leaf committed-percent {
      type string;
      description
        "The percentage of committed memory";
    }
    container status {
      description
        "Memory status";
      uses platform-sw-ios-xe-oper:ncs_template_memory-status;
    }
  }

  grouping ncs_template_core {
    description
      "Processor core information";
    leaf name {
      type string;
      description
        "The identifier of the core";
    }
    leaf user {
      type string;
      description
        "CPU utilization in user mode";
    }
    leaf system {
      type string;
      description
        "CPU utilization in system mode";
    }
    leaf nice {
      type string;
      description
        "Nice level";
    }
    leaf idle {
      type string;
      description
        "Idle percentage";
    }
    leaf irq {
      type string;
      description
        "The percentage of utilization by irq";
    }
    leaf sirq {
      type string;
      description
        "The percentage of utilization by sirq";
    }
    leaf io-wait {
      type string;
      description
        "IOWait percentage";
    }
  }

  grouping ncs_template_control-process {
    description
      "Control process information";
    leaf control-process-status {
      type string;
      description
        "Status of the control process";
    }
    leaf updated {
      type string;
      description
        "Number of seconds since the data has been updated";
    }
    container load-average-stats {
      description
        "Load average statictics";
      uses platform-sw-ios-xe-oper:ncs_template_load-average-stats;
    }
    container load-avg-minutes {
      description
        "Load average statistics calculated over a period of time";
      list load-avg-minute {
        // NCS patched for predictable order
        ordered-by user;
        key "number";
        description
          "List of Load averages based on a time frame";
        uses platform-sw-ios-xe-oper:ncs_template_minute;
      }
    }
    container memory-stats {
      description
        "Memory statistics";
      uses platform-sw-ios-xe-oper:ncs_template_platform-memory-stats;
    }
    container per-core-stats {
      description
        "Processor core statistics";
      list per-core-stat {
        // NCS patched for predictable order
        ordered-by user;
        key "name";
        description
          "List of processor cores";
        uses platform-sw-ios-xe-oper:ncs_template_core;
      }
    }
  }

  grouping ncs_rpc_notif_svc-loc {
    description
      "Service location details";
    leaf fru {
      type platform-sw-ios-xe-oper:b-fru;
      description
        "Field replaceable unit";
    }
    leaf slotnum {
      type int16;
      description
        "Slot number";
    }
    leaf baynum {
      type int16;
      description
        "Bay number";
    }
    leaf chassisnum {
      type int16;
      description
        "Chassis number";
    }
  }

  grouping ncs_rpc_notif_min-status {
    description
      "Load average statistics minute status";
    leaf condition {
      type string;
      description
        "Load average condition";
    }
    leaf threshold-status {
      type string;
      description
        "Load average status";
    }
    leaf threshold-value {
      type decimal64 {
        fraction-digits 2;
      }
      description
        "Load average threshold";
    }
  }

  grouping ncs_rpc_notif_minute {
    description
      "Average calculated over a period of time";
    leaf number {
      type uint64;
      description
        "The number of minutes the average was calculated on";
    }
    leaf average {
      type decimal64 {
        fraction-digits 2;
      }
      description
        "Calculated average";
    }
    container status {
      description
        "Load average statistics minute status";
      uses platform-sw-ios-xe-oper:ncs_rpc_notif_min-status;
    }
  }

  grouping ncs_rpc_notif_load-average-stats {
    description
      "Statistics on the load average";
    leaf load-average-status {
      type string;
      description
        "Load average status";
    }
  }

  grouping ncs_rpc_notif_memory-status {
    description
      "Memory statistics status";
    leaf warning-threshold-percent {
      type uint32;
      description
        "Memory warning threshold value percent";
    }
    leaf critical-threshold-percent {
      type uint32;
      description
        "Memory critical threshold value percent";
    }
  }

  grouping ncs_rpc_notif_platform-memory-stats {
    description
      "Platform memory statistics status";
    leaf memory-status {
      type string;
      description
        "The status of the memory";
    }
    leaf total {
      type uint64;
      description
        "The total amount of memory in kb";
    }
    leaf used-number {
      type uint64;
      description
        "The amount of memory being used in kb";
    }
    leaf used-percent {
      type uint64;
      description
        "The percentage of memory being used";
    }
    leaf free-number {
      type uint64;
      description
        "The amount of free memory in kb";
    }
    leaf free-percent {
      type uint64;
      description
        "The percentage of free memory";
    }
    leaf available-number {
      type uint64;
      description
        "The amount of available memory in kb";
    }
    leaf available-percent {
      type uint64;
      description
        "The percentage of available memory";
    }
    leaf committed-number {
      type uint64;
      description
        "The amount of committed memory in kb";
    }
    leaf committed-percent {
      type uint8;
      description
        "The percentage of committed memory";
    }
    container status {
      description
        "Memory status";
      uses platform-sw-ios-xe-oper:ncs_rpc_notif_memory-status;
    }
  }

  grouping ncs_rpc_notif_core {
    description
      "Processor core information";
    leaf name {
      type uint32;
      description
        "The identifier of the core";
    }
    leaf user {
      type decimal64 {
        fraction-digits 2;
      }
      description
        "CPU utilization in user mode";
    }
    leaf system {
      type decimal64 {
        fraction-digits 2;
      }
      description
        "CPU utilization in system mode";
    }
    leaf nice {
      type decimal64 {
        fraction-digits 2;
      }
      description
        "Nice level";
    }
    leaf idle {
      type decimal64 {
        fraction-digits 2;
      }
      description
        "Idle percentage";
    }
    leaf irq {
      type decimal64 {
        fraction-digits 2;
      }
      description
        "The percentage of utilization by irq";
    }
    leaf sirq {
      type decimal64 {
        fraction-digits 2;
      }
      description
        "The percentage of utilization by sirq";
    }
    leaf io-wait {
      type decimal64 {
        fraction-digits 2;
      }
      description
        "IOWait percentage";
    }
  }

  grouping ncs_rpc_notif_control-process {
    description
      "Control process information";
    leaf control-process-status {
      type string;
      description
        "Status of the control process";
    }
    leaf updated {
      type uint64;
      description
        "Number of seconds since the data has been updated";
    }
    container load-average-stats {
      description
        "Load average statictics";
      uses platform-sw-ios-xe-oper:ncs_rpc_notif_load-average-stats;
    }
    container load-avg-minutes {
      description
        "Load average statistics calculated over a period of time";
      list load-avg-minute {
        key "number";
        description
          "List of Load averages based on a time frame";
        uses platform-sw-ios-xe-oper:ncs_rpc_notif_minute;
      }
    }
    container memory-stats {
      description
        "Memory statistics";
      uses platform-sw-ios-xe-oper:ncs_rpc_notif_platform-memory-stats;
    }
    container per-core-stats {
      description
        "Processor core statistics";
      list per-core-stat {
        key "name";
        description
          "List of processor cores";
        uses platform-sw-ios-xe-oper:ncs_rpc_notif_core;
      }
    }
  }

  grouping live_ncs_svc-loc {
    description
      "Service location details";
    leaf fru {
      type platform-sw-ios-xe-oper:b-fru;
      description
        "Field replaceable unit";
    }
    leaf slotnum {
      type int16;
      description
        "Slot number";
    }
    leaf baynum {
      type int16;
      description
        "Bay number";
    }
    leaf chassisnum {
      type int16;
      description
        "Chassis number";
    }
  }

  grouping live_ncs_min-status {
    description
      "Load average statistics minute status";
    leaf condition {
      type string;
      description
        "Load average condition";
    }
    leaf threshold-status {
      type string;
      description
        "Load average status";
    }
    leaf threshold-value {
      type decimal64 {
        fraction-digits 2;
      }
      description
        "Load average threshold";
    }
  }

  grouping live_ncs_minute {
    description
      "Average calculated over a period of time";
    leaf number {
      type uint64;
      description
        "The number of minutes the average was calculated on";
    }
    leaf average {
      type decimal64 {
        fraction-digits 2;
      }
      description
        "Calculated average";
    }
    container status {
      description
        "Load average statistics minute status";
      uses platform-sw-ios-xe-oper:live_ncs_min-status;
    }
  }

  grouping live_ncs_load-average-stats {
    description
      "Statistics on the load average";
    leaf load-average-status {
      type string;
      description
        "Load average status";
    }
  }

  grouping live_ncs_memory-status {
    description
      "Memory statistics status";
    leaf warning-threshold-percent {
      type uint32;
      description
        "Memory warning threshold value percent";
    }
    leaf critical-threshold-percent {
      type uint32;
      description
        "Memory critical threshold value percent";
    }
  }

  grouping live_ncs_platform-memory-stats {
    description
      "Platform memory statistics status";
    leaf memory-status {
      type string;
      description
        "The status of the memory";
    }
    leaf total {
      type uint64;
      description
        "The total amount of memory in kb";
    }
    leaf used-number {
      type uint64;
      description
        "The amount of memory being used in kb";
    }
    leaf used-percent {
      type uint64;
      description
        "The percentage of memory being used";
    }
    leaf free-number {
      type uint64;
      description
        "The amount of free memory in kb";
    }
    leaf free-percent {
      type uint64;
      description
        "The percentage of free memory";
    }
    leaf available-number {
      type uint64;
      description
        "The amount of available memory in kb";
    }
    leaf available-percent {
      type uint64;
      description
        "The percentage of available memory";
    }
    leaf committed-number {
      type uint64;
      description
        "The amount of committed memory in kb";
    }
    leaf committed-percent {
      type uint8;
      description
        "The percentage of committed memory";
    }
    container status {
      description
        "Memory status";
      uses platform-sw-ios-xe-oper:live_ncs_memory-status;
    }
  }

  grouping live_ncs_core {
    description
      "Processor core information";
    leaf name {
      type uint32;
      description
        "The identifier of the core";
    }
    leaf user {
      type decimal64 {
        fraction-digits 2;
      }
      description
        "CPU utilization in user mode";
    }
    leaf system {
      type decimal64 {
        fraction-digits 2;
      }
      description
        "CPU utilization in system mode";
    }
    leaf nice {
      type decimal64 {
        fraction-digits 2;
      }
      description
        "Nice level";
    }
    leaf idle {
      type decimal64 {
        fraction-digits 2;
      }
      description
        "Idle percentage";
    }
    leaf irq {
      type decimal64 {
        fraction-digits 2;
      }
      description
        "The percentage of utilization by irq";
    }
    leaf sirq {
      type decimal64 {
        fraction-digits 2;
      }
      description
        "The percentage of utilization by sirq";
    }
    leaf io-wait {
      type decimal64 {
        fraction-digits 2;
      }
      description
        "IOWait percentage";
    }
  }

  grouping live_ncs_control-process {
    description
      "Control process information";
    leaf control-process-status {
      type string;
      description
        "Status of the control process";
    }
    leaf updated {
      type uint64;
      description
        "Number of seconds since the data has been updated";
    }
    container load-average-stats {
      description
        "Load average statictics";
      uses platform-sw-ios-xe-oper:live_ncs_load-average-stats;
    }
    container load-avg-minutes {
      description
        "Load average statistics calculated over a period of time";
      list load-avg-minute {
        key "number";
        description
          "List of Load averages based on a time frame";
        uses platform-sw-ios-xe-oper:live_ncs_minute;
      }
    }
    container memory-stats {
      description
        "Memory statistics";
      uses platform-sw-ios-xe-oper:live_ncs_platform-memory-stats;
    }
    container per-core-stats {
      description
        "Processor core statistics";
      list per-core-stat {
        key "name";
        description
          "List of processor cores";
        uses platform-sw-ios-xe-oper:live_ncs_core;
      }
    }
  }

  grouping svc-loc {
    description
      "Service location details";
    leaf fru {
      type platform-sw-ios-xe-oper:b-fru;
      description
        "Field replaceable unit";
    }
    leaf slotnum {
      type int16;
      description
        "Slot number";
    }
    leaf baynum {
      type int16;
      description
        "Bay number";
    }
    leaf chassisnum {
      type int16;
      description
        "Chassis number";
    }
  }

  grouping min-status {
    description
      "Load average statistics minute status";
    leaf condition {
      type string;
      description
        "Load average condition";
    }
    leaf threshold-status {
      type string;
      description
        "Load average status";
    }
    leaf threshold-value {
      type decimal64 {
        fraction-digits 2;
      }
      description
        "Load average threshold";
    }
  }

  grouping minute {
    description
      "Average calculated over a period of time";
    leaf number {
      type uint64;
      description
        "The number of minutes the average was calculated on";
    }
    leaf average {
      type decimal64 {
        fraction-digits 2;
      }
      description
        "Calculated average";
    }
    container status {
      description
        "Load average statistics minute status";
      uses platform-sw-ios-xe-oper:min-status;
    }
  }

  grouping load-average-stats {
    description
      "Statistics on the load average";
    leaf load-average-status {
      type string;
      description
        "Load average status";
    }
  }

  grouping memory-status {
    description
      "Memory statistics status";
    leaf warning-threshold-percent {
      type uint32;
      description
        "Memory warning threshold value percent";
    }
    leaf critical-threshold-percent {
      type uint32;
      description
        "Memory critical threshold value percent";
    }
  }

  grouping platform-memory-stats {
    description
      "Platform memory statistics status";
    leaf memory-status {
      type string;
      description
        "The status of the memory";
    }
    leaf total {
      type uint64;
      description
        "The total amount of memory in kb";
    }
    leaf used-number {
      type uint64;
      description
        "The amount of memory being used in kb";
    }
    leaf used-percent {
      type uint64;
      description
        "The percentage of memory being used";
    }
    leaf free-number {
      type uint64;
      description
        "The amount of free memory in kb";
    }
    leaf free-percent {
      type uint64;
      description
        "The percentage of free memory";
    }
    leaf available-number {
      type uint64;
      description
        "The amount of available memory in kb";
    }
    leaf available-percent {
      type uint64;
      description
        "The percentage of available memory";
    }
    leaf committed-number {
      type uint64;
      description
        "The amount of committed memory in kb";
    }
    leaf committed-percent {
      type uint8;
      description
        "The percentage of committed memory";
    }
    container status {
      description
        "Memory status";
      uses platform-sw-ios-xe-oper:memory-status;
    }
  }

  grouping core {
    description
      "Processor core information";
    leaf name {
      type uint32;
      description
        "The identifier of the core";
    }
    leaf user {
      type decimal64 {
        fraction-digits 2;
      }
      description
        "CPU utilization in user mode";
    }
    leaf system {
      type decimal64 {
        fraction-digits 2;
      }
      description
        "CPU utilization in system mode";
    }
    leaf nice {
      type decimal64 {
        fraction-digits 2;
      }
      description
        "Nice level";
    }
    leaf idle {
      type decimal64 {
        fraction-digits 2;
      }
      description
        "Idle percentage";
    }
    leaf irq {
      type decimal64 {
        fraction-digits 2;
      }
      description
        "The percentage of utilization by irq";
    }
    leaf sirq {
      type decimal64 {
        fraction-digits 2;
      }
      description
        "The percentage of utilization by sirq";
    }
    leaf io-wait {
      type decimal64 {
        fraction-digits 2;
      }
      description
        "IOWait percentage";
    }
  }

  grouping control-process {
    description
      "Control process information";
    leaf control-process-status {
      type string;
      description
        "Status of the control process";
    }
    leaf updated {
      type uint64;
      description
        "Number of seconds since the data has been updated";
    }
    container load-average-stats {
      description
        "Load average statictics";
      uses platform-sw-ios-xe-oper:load-average-stats;
    }
    container load-avg-minutes {
      description
        "Load average statistics calculated over a period of time";
      list load-avg-minute {
        key "number";
        description
          "List of Load averages based on a time frame";
        uses platform-sw-ios-xe-oper:minute;
      }
    }
    container memory-stats {
      description
        "Memory statistics";
      uses platform-sw-ios-xe-oper:platform-memory-stats;
    }
    container per-core-stats {
      description
        "Processor core statistics";
      list per-core-stat {
        key "name";
        description
          "List of processor cores";
        uses platform-sw-ios-xe-oper:core;
      }
    }
  }

  augment "/ncs:devices/ncs:device/ncs:config" {
    // NCS drop config false container 'cisco-platform-software'
  }
  augment "/ncs:devices/ncs:device/ncs:live-status" {
    container cisco-platform-software {
      tailf:ncs-device-type "netconf";
      tailf:display-when "not(../../ncs:module) or ../../ncs:module[ncs:name='Cisco-IOS-XE-platform-software-oper'] or (../../ncs:live-status-protocol[not(ncs:capability)]) or (../../ncs:live-status-protocol/ncs:capability/ncs:module[.='Cisco-IOS-XE-platform-software-oper'])";
      description
        "Cisco platform software information";
      container control-processes {
        description
          "Information about control processes";
        list control-process {
          key "fru slotnum baynum chassisnum";
          description
            "The list of control processes";
          uses platform-sw-ios-xe-oper:live_ncs_svc-loc;
          uses platform-sw-ios-xe-oper:live_ncs_control-process;
        }
      }
    }
  }
  augment "/ncs:devices/ncs:template/ncs:config" {
    // NCS drop config false container 'cisco-platform-software'
  }
}
