module Cisco-IOS-XE-rpc {
  // Generated by yanger -t ncs
  tailf:ncs-device-type "netconf";

  namespace "http://cisco.com/ns/yang/Cisco-IOS-XE-rpc";
  prefix ios-xe-rpc;

  import tailf-ncs {
    prefix ncs;
  }
  import tailf-common {
    prefix tailf;
  }

  organization "Cisco Systems";
  contact
    "<mailto:cs-yang@cisco.com>";
  description
    "NED RPC YANG module for IOS
     Copyright (c) 2016 by Cisco Systems, Inc.
     All rights reserved.";

  revision 2017-02-07 {
    description
      "Initial revision";
  }

  grouping ncs_template_cisco-xe-rpc-output {
    description
      "Used to return output from RPCs";
    leaf result {
      type string;
      description
        "Output returned by the network element";
    }
  }

  grouping ncs_rpc_notif_cisco-xe-rpc-output {
    description
      "Used to return output from RPCs";
    leaf result {
      type string;
      description
        "Output returned by the network element";
    }
  }

  grouping live_ncs_cisco-xe-rpc-output {
    description
      "Used to return output from RPCs";
    leaf result {
      type string;
      description
        "Output returned by the network element";
    }
  }

  grouping cisco-xe-rpc-output {
    description
      "Used to return output from RPCs";
    leaf result {
      type string;
      description
        "Output returned by the network element";
    }
  }

  augment "/ncs:devices/ncs:device/ncs:rpc" {
    container rpc-license {
      tailf:ncs-device-type "netconf";
      tailf:display-when "not(../../ncs:module) or ../../ncs:module[ncs:name='Cisco-IOS-XE-rpc']";
      tailf:action license {
        tailf:actionpoint ncsproxy {
          tailf:internal;
        }
        input {
          container smart {
            choice smart-choice {
              mandatory true;
              case register-case {
                container register {
                  leaf idtoken {
                    type empty;
                  }
                }
              }
              case deregister-case {
                leaf deregister {
                  type empty;
                }
              }
              case renew-case {
                container renew {
                  leaf id {
                    type empty;
                  }
                  leaf auth {
                    type empty;
                  }
                }
              }
            }
          }
        }
        output {
          uses ncs_rpc_notif_cisco-xe-rpc-output;
        }
      }
    }
  }
  augment "/ncs:devices/ncs:device-group/ncs:rpc" {
    container rpc-license {
      tailf:ncs-device-type "netconf";
      tailf:display-when "/ncs:devices/ncs:device[ncs:name=current()/../../ncs:member]/ncs:module[ncs:name='Cisco-IOS-XE-rpc']";
      tailf:action license {
        tailf:actionpoint ncsproxy {
          tailf:internal;
        }
        input {
          container smart {
            choice smart-choice {
              mandatory true;
              case register-case {
                container register {
                  leaf idtoken {
                    type empty;
                  }
                }
              }
              case deregister-case {
                leaf deregister {
                  type empty;
                }
              }
              case renew-case {
                container renew {
                  leaf id {
                    type empty;
                  }
                  leaf auth {
                    type empty;
                  }
                }
              }
            }
          }
        }
        output {
          container "device" {
            leaf "name" {
              type string;
            }
            leaf "info" {
              type string;
            }
            container "result" {
              uses ncs_rpc_notif_cisco-xe-rpc-output;
            }
          }
        }
      }
    }
  }
  augment "/ncs:devices/ncs:device/ncs:rpc" {
    container rpc-reload {
      tailf:ncs-device-type "netconf";
      tailf:display-when "not(../../ncs:module) or ../../ncs:module[ncs:name='Cisco-IOS-XE-rpc']";
      tailf:action reload {
        tailf:actionpoint ncsproxy {
          tailf:internal;
        }
        description
          "Halt and perform a cold restart";
        output {
          uses ncs_rpc_notif_cisco-xe-rpc-output;
        }
      }
    }
  }
  augment "/ncs:devices/ncs:device-group/ncs:rpc" {
    container rpc-reload {
      tailf:ncs-device-type "netconf";
      tailf:display-when "/ncs:devices/ncs:device[ncs:name=current()/../../ncs:member]/ncs:module[ncs:name='Cisco-IOS-XE-rpc']";
      tailf:action reload {
        tailf:actionpoint ncsproxy {
          tailf:internal;
        }
        description
          "Halt and perform a cold restart";
        output {
          container "device" {
            leaf "name" {
              type string;
            }
            leaf "info" {
              type string;
            }
            container "result" {
              uses ncs_rpc_notif_cisco-xe-rpc-output;
            }
          }
        }
      }
    }
  }
  augment "/ncs:devices/ncs:device/ncs:rpc" {
    container rpc-default {
      tailf:ncs-device-type "netconf";
      tailf:display-when "not(../../ncs:module) or ../../ncs:module[ncs:name='Cisco-IOS-XE-rpc']";
      tailf:action default {
        tailf:actionpoint ncsproxy {
          tailf:internal;
        }
        description
          "Set a command to its defaults";
        input {
          choice default-choice {
            mandatory true;
            case interface-case {
              leaf interface {
                description
                  "Select an interface to configure";
                type string;
              }
            }
          }
        }
        output {
          uses ncs_rpc_notif_cisco-xe-rpc-output;
        }
      }
    }
  }
  augment "/ncs:devices/ncs:device-group/ncs:rpc" {
    container rpc-default {
      tailf:ncs-device-type "netconf";
      tailf:display-when "/ncs:devices/ncs:device[ncs:name=current()/../../ncs:member]/ncs:module[ncs:name='Cisco-IOS-XE-rpc']";
      tailf:action default {
        tailf:actionpoint ncsproxy {
          tailf:internal;
        }
        description
          "Set a command to its defaults";
        input {
          choice default-choice {
            mandatory true;
            case interface-case {
              leaf interface {
                description
                  "Select an interface to configure";
                type string;
              }
            }
          }
        }
        output {
          container "device" {
            leaf "name" {
              type string;
            }
            leaf "info" {
              type string;
            }
            container "result" {
              uses ncs_rpc_notif_cisco-xe-rpc-output;
            }
          }
        }
      }
    }
  }
  augment "/ncs:devices/ncs:device/ncs:rpc" {
    container rpc-switch {
      tailf:ncs-device-type "netconf";
      tailf:display-when "not(../../ncs:module) or ../../ncs:module[ncs:name='Cisco-IOS-XE-rpc']";
      tailf:action switch {
        tailf:actionpoint ncsproxy {
          tailf:internal;
        }
        input {
          leaf switch-number {
            mandatory true;
            type uint8 {
              range "1..9";
            }
          }
          choice pri-renum-stack {
            mandatory true;
            case priority-case {
              leaf priority {
                description
                  "<1-15>  Switch Priority";
                type uint8 {
                  range "1..15";
                }
              }
            }
            case renumver-case {
              leaf renumber {
                description
                  "<1-9>  New number of the Switch";
                type uint8 {
                  range "1..9";
                }
              }
            }
            case stack-case {
              container statck {
                leaf port {
                  description
                    "<1-2>  Stack port number to enable/disable";
                  type uint8 {
                    range "1..2";
                  }
                }
              }
            }
          }
        }
        output {
          uses ncs_rpc_notif_cisco-xe-rpc-output;
        }
      }
    }
  }
  augment "/ncs:devices/ncs:device-group/ncs:rpc" {
    container rpc-switch {
      tailf:ncs-device-type "netconf";
      tailf:display-when "/ncs:devices/ncs:device[ncs:name=current()/../../ncs:member]/ncs:module[ncs:name='Cisco-IOS-XE-rpc']";
      tailf:action switch {
        tailf:actionpoint ncsproxy {
          tailf:internal;
        }
        input {
          leaf switch-number {
            mandatory true;
            type uint8 {
              range "1..9";
            }
          }
          choice pri-renum-stack {
            mandatory true;
            case priority-case {
              leaf priority {
                description
                  "<1-15>  Switch Priority";
                type uint8 {
                  range "1..15";
                }
              }
            }
            case renumver-case {
              leaf renumber {
                description
                  "<1-9>  New number of the Switch";
                type uint8 {
                  range "1..9";
                }
              }
            }
            case stack-case {
              container statck {
                leaf port {
                  description
                    "<1-2>  Stack port number to enable/disable";
                  type uint8 {
                    range "1..2";
                  }
                }
              }
            }
          }
        }
        output {
          container "device" {
            leaf "name" {
              type string;
            }
            leaf "info" {
              type string;
            }
            container "result" {
              uses ncs_rpc_notif_cisco-xe-rpc-output;
            }
          }
        }
      }
    }
  }
}
