module Cisco-IOS-XE-service-chain {
  // Generated by yanger -t ncs
  tailf:ncs-device-type "netconf";

  namespace "http://cisco.com/ns/yang/Cisco-IOS-XE-service-chain";
  prefix ios-service-chain;

  import ietf-inet-types {
    prefix inet;
  }
  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Service Chain Yang model.
     Copyright (c) 2016 by Cisco Systems, Inc.
     All rights reserved.";

  revision 2017-02-07 {
    description
      "Initial revision";
  }

  grouping ncs_template_service-chain-grouping {
    leaf description {
      description
        "Service function forwarder description";
      type string;
    }
    container ip {
      description
        "IP address for Service Function Forwarder";
      leaf address {
        description
          "Set IPv4 address";
        type string;
      }
    }
  }

  grouping ncs_template_config-service-chain-grouping {
    list service-function {
      // NCS patched for predictable order
      ordered-by user;
      description
        "Service function details";
      key "name";
      leaf name {
        description
          "WORD;;Service function name";
        type string;
      }
      container config-service-chain-sf-mode {
        leaf description {
          description
            "Service function description";
          type string;
        }
        container encapsulation {
          description
            "Service node encapsulation";
          choice mode-choice {
            container gre {
              description
                "Service node encapsulation type";
              presence "true";
              leaf enhanced {
                description
                  "Add enhanced NSH TLV information";
                type string;
              }
            }
            leaf none {
              description
                "Service node encapsulation type";
              type empty;
            }
          }
        }
        container ip {
          description
            "Service node";
          leaf address {
            type string;
          }
        }
      }
    }
    container service-function-forwarder {
      description
        "Service function forwarder details";
      list service-ff-name {
        // NCS patched for predictable order
        ordered-by user;
        key "name";
        leaf name {
          description
            "WORD;;Service function forwarder name";
          type string;
        }
        uses ncs_template_service-chain-grouping;
      }
      container local {
        description
          "Local service function forwarder";
        presence "true";
        uses ncs_template_service-chain-grouping;
      }
    }
    list service-path {
      // NCS patched for predictable order
      ordered-by user;
      description
        "Service Path Entries";
      key "service-path-id";
      leaf service-path-id {
        type string;
      }
      container config-service-chain-path-mode {
        leaf description {
          description
            "Path Description";
          type string;
        }
        container service-index {
          description
            "Service Index";
          list services {
            // NCS patched for predictable order
            ordered-by user;
            key "service-index-id";
            leaf service-index-id {
              type string;
            }
            choice service-type-choice {
              leaf service-function {
                description
                  "Service Function name";
                type string;
              }
              leaf service-function-forwarder {
                description
                  "Service Function Forwarder name";
                type string;
              }
              leaf terminate {
                description
                  "Terminate(Proxy)";
                type empty;
              }
            }
          }
        }
      }
    }
  }

  grouping ncs_rpc_notif_service-chain-grouping {
    leaf description {
      description
        "Service function forwarder description";
      type string {
        length "1..256";
      }
    }
    container ip {
      description
        "IP address for Service Function Forwarder";
      leaf address {
        description
          "Set IPv4 address";
        type inet:ipv4-address;
      }
    }
  }

  grouping ncs_rpc_notif_config-service-chain-grouping {
    list service-function {
      description
        "Service function details";
      key "name";
      leaf name {
        description
          "WORD;;Service function name";
        type string;
      }
      container config-service-chain-sf-mode {
        leaf description {
          description
            "Service function description";
          type string {
            length "1..256";
          }
        }
        container encapsulation {
          description
            "Service node encapsulation";
          choice mode-choice {
            container gre {
              description
                "Service node encapsulation type";
              presence "true";
              leaf enhanced {
                description
                  "Add enhanced NSH TLV information";
                type enumeration {
                  enum "copy";
                  enum "divert";
                }
              }
            }
            leaf none {
              description
                "Service node encapsulation type";
              type empty;
            }
          }
        }
        container ip {
          description
            "Service node";
          leaf address {
            type inet:ipv4-address;
          }
        }
      }
    }
    container service-function-forwarder {
      description
        "Service function forwarder details";
      list service-ff-name {
        key "name";
        leaf name {
          description
            "WORD;;Service function forwarder name";
          type string;
        }
        uses ncs_rpc_notif_service-chain-grouping;
      }
      container local {
        description
          "Local service function forwarder";
        presence "true";
        uses ncs_rpc_notif_service-chain-grouping;
      }
    }
    list service-path {
      description
        "Service Path Entries";
      key "service-path-id";
      leaf service-path-id {
        type uint32 {
          range "0..16777215";
        }
      }
      container config-service-chain-path-mode {
        leaf description {
          description
            "Path Description";
          type string {
            length "1..256";
          }
        }
        container service-index {
          description
            "Service Index";
          list services {
            key "service-index-id";
            leaf service-index-id {
              type uint8 {
                range "2..255";
              }
            }
            choice service-type-choice {
              leaf service-function {
                description
                  "Service Function name";
                type string;
              }
              leaf service-function-forwarder {
                description
                  "Service Function Forwarder name";
                type string;
              }
              leaf terminate {
                description
                  "Terminate(Proxy)";
                type empty;
              }
            }
          }
        }
      }
    }
  }

  grouping live_ncs_service-chain-grouping {
    leaf description {
      description
        "Service function forwarder description";
      type string {
        length "1..256";
      }
    }
    container ip {
      description
        "IP address for Service Function Forwarder";
      leaf address {
        description
          "Set IPv4 address";
        type inet:ipv4-address;
      }
    }
  }

  grouping live_ncs_config-service-chain-grouping {
    list service-function {
      description
        "Service function details";
      key "name";
      leaf name {
        description
          "WORD;;Service function name";
        type string;
      }
      container config-service-chain-sf-mode {
        leaf description {
          description
            "Service function description";
          type string {
            length "1..256";
          }
        }
        container encapsulation {
          description
            "Service node encapsulation";
          choice mode-choice {
            container gre {
              description
                "Service node encapsulation type";
              presence "true";
              leaf enhanced {
                description
                  "Add enhanced NSH TLV information";
                type enumeration {
                  enum "copy";
                  enum "divert";
                }
              }
            }
            leaf none {
              description
                "Service node encapsulation type";
              type empty;
            }
          }
        }
        container ip {
          description
            "Service node";
          leaf address {
            type inet:ipv4-address;
          }
        }
      }
    }
    container service-function-forwarder {
      description
        "Service function forwarder details";
      list service-ff-name {
        key "name";
        leaf name {
          description
            "WORD;;Service function forwarder name";
          type string;
        }
        uses live_ncs_service-chain-grouping;
      }
      container local {
        description
          "Local service function forwarder";
        presence "true";
        uses live_ncs_service-chain-grouping;
      }
    }
    list service-path {
      description
        "Service Path Entries";
      key "service-path-id";
      leaf service-path-id {
        type uint32 {
          range "0..16777215";
        }
      }
      container config-service-chain-path-mode {
        leaf description {
          description
            "Path Description";
          type string {
            length "1..256";
          }
        }
        container service-index {
          description
            "Service Index";
          list services {
            key "service-index-id";
            leaf service-index-id {
              type uint8 {
                range "2..255";
              }
            }
            choice service-type-choice {
              leaf service-function {
                description
                  "Service Function name";
                type string;
              }
              leaf service-function-forwarder {
                description
                  "Service Function Forwarder name";
                type string;
              }
              leaf terminate {
                description
                  "Terminate(Proxy)";
                type empty;
              }
            }
          }
        }
      }
    }
  }

  grouping service-chain-grouping {
    leaf description {
      description
        "Service function forwarder description";
      type string {
        length "1..256";
      }
    }
    container ip {
      description
        "IP address for Service Function Forwarder";
      leaf address {
        description
          "Set IPv4 address";
        type inet:ipv4-address;
      }
    }
  }

  grouping config-service-chain-grouping {
    list service-function {
      description
        "Service function details";
      key "name";
      leaf name {
        description
          "WORD;;Service function name";
        type string;
      }
      container config-service-chain-sf-mode {
        leaf description {
          description
            "Service function description";
          type string {
            length "1..256";
          }
        }
        container encapsulation {
          description
            "Service node encapsulation";
          choice mode-choice {
            container gre {
              description
                "Service node encapsulation type";
              presence "true";
              leaf enhanced {
                description
                  "Add enhanced NSH TLV information";
                type enumeration {
                  enum "copy";
                  enum "divert";
                }
              }
            }
            leaf none {
              description
                "Service node encapsulation type";
              type empty;
            }
          }
        }
        container ip {
          description
            "Service node";
          leaf address {
            type inet:ipv4-address;
          }
        }
      }
    }
    container service-function-forwarder {
      description
        "Service function forwarder details";
      list service-ff-name {
        key "name";
        leaf name {
          description
            "WORD;;Service function forwarder name";
          type string;
        }
        uses service-chain-grouping;
      }
      container local {
        description
          "Local service function forwarder";
        presence "true";
        uses service-chain-grouping;
      }
    }
    list service-path {
      description
        "Service Path Entries";
      key "service-path-id";
      leaf service-path-id {
        type uint32 {
          range "0..16777215";
        }
      }
      container config-service-chain-path-mode {
        leaf description {
          description
            "Path Description";
          type string {
            length "1..256";
          }
        }
        container service-index {
          description
            "Service Index";
          list services {
            key "service-index-id";
            leaf service-index-id {
              type uint8 {
                range "2..255";
              }
            }
            choice service-type-choice {
              leaf service-function {
                description
                  "Service Function name";
                type string;
              }
              leaf service-function-forwarder {
                description
                  "Service Function Forwarder name";
                type string;
              }
              leaf terminate {
                description
                  "Terminate(Proxy)";
                type empty;
              }
            }
          }
        }
      }
    }
  }

  augment "/ncs:devices/ncs:template/ncs:config/ios:native/ios:service-chain" {
    uses ncs_template_config-service-chain-grouping;
  }
  augment "/ncs:devices/ncs:device/ncs:live-status/ios:native/ios:service-chain" {
    uses live_ncs_config-service-chain-grouping {
      refine service-path {
        tailf:ncs-device-type "netconf";
        tailf:display-when "not(../../../ncs:module) or ../../../ncs:module[ncs:name='Cisco-IOS-XE-service-chain'] or (../../../ncs:live-status-protocol[not(ncs:capability)]) or (../../../ncs:live-status-protocol/ncs:capability/ncs:module[.='Cisco-IOS-XE-service-chain'])";
      }
      refine service-function-forwarder {
        tailf:ncs-device-type "netconf";
        tailf:display-when "not(../../../../ncs:module) or ../../../../ncs:module[ncs:name='Cisco-IOS-XE-service-chain'] or (../../../../ncs:live-status-protocol[not(ncs:capability)]) or (../../../../ncs:live-status-protocol/ncs:capability/ncs:module[.='Cisco-IOS-XE-service-chain'])";
      }
      refine service-function {
        tailf:ncs-device-type "netconf";
        tailf:display-when "not(../../../ncs:module) or ../../../ncs:module[ncs:name='Cisco-IOS-XE-service-chain'] or (../../../ncs:live-status-protocol[not(ncs:capability)]) or (../../../ncs:live-status-protocol/ncs:capability/ncs:module[.='Cisco-IOS-XE-service-chain'])";
      }
    }
  }
  augment "/ncs:devices/ncs:device/ncs:config/ios:native/ios:service-chain" {
    uses config-service-chain-grouping {
      refine service-path {
        tailf:ncs-device-type "netconf";
        tailf:display-when "not(../../../ncs:module) or ../../../ncs:module[ncs:name='Cisco-IOS-XE-service-chain']";
      }
      refine service-function-forwarder {
        tailf:ncs-device-type "netconf";
        tailf:display-when "not(../../../../ncs:module) or ../../../../ncs:module[ncs:name='Cisco-IOS-XE-service-chain']";
      }
      refine service-function {
        tailf:ncs-device-type "netconf";
        tailf:display-when "not(../../../ncs:module) or ../../../ncs:module[ncs:name='Cisco-IOS-XE-service-chain']";
      }
    }
  }
}
