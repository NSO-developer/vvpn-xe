module Cisco-IOS-XE-service-discovery {
  // Generated by yanger -t ncs
  tailf:ncs-device-type "netconf";

  namespace "http://cisco.com/ns/yang/Cisco-IOS-XE-service-discovery";
  prefix ios-sd;

  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Service Discovery Yang model.
     Copyright (c) 2016 by Cisco Systems, Inc.
     All rights reserved.";

  revision 2017-02-07 {
    description
      "Initial revision";
  }

  grouping ncs_template_service-list-match-grouping {
    container match {
      description
        "Configure parameters for service-list name";
      leaf learnt-interface {
        description
          "match the interface where service is learnt";
        type empty;
      }
      container location {
        description
          "match location information";
        presence "true";
        leaf civic {
          description
            "Civic location";
          type string;
        }
      }
      container message-type {
        description
          "To set the message type";
        presence "true";
        leaf announcement {
          description
            "Match Announcement/Responses";
          type empty;
        }
        leaf query {
          description
            "Match Query";
          type empty;
        }
        leaf any {
          description
            "Match Any";
          type empty;
        }
      }
      leaf service-instance {
        description
          "To set the Service Instance";
        type string;
      }
      leaf service-type {
        description
          "match mDNS service type string";
        type string;
      }
    }
  }

  grouping ncs_template_config-service-list-grouping {
    container service-list {
      description
        "Enter the service list";
      list mdns-sd {
        // NCS patched for predictable order
        ordered-by user;
        description
          "Service-list for mdns-sd";
        key "service-list-name";
        leaf service-list-name {
          description
            "service-list name";
          type string;
        }
        list deny {
          // NCS patched for predictable order
          ordered-by user;
          description
            "Specify packets to reject";
          key "deny-pack";
          leaf deny-pack {
            type string;
          }
          uses ncs_template_service-list-match-grouping;
        }
        list permit {
          // NCS patched for predictable order
          ordered-by user;
          description
            "Specify packets to forward";
          key "deny-pack";
          leaf deny-pack {
            type string;
          }
          uses ncs_template_service-list-match-grouping;
        }
        container query {
          description
            "Service-list Query for mdns-sd";
          leaf service-type {
            description
              "Configure periodicity for each service-type";
            type string;
          }
        }
      }
    }
  }

  grouping ncs_rpc_notif_service-list-match-grouping {
    container match {
      description
        "Configure parameters for service-list name";
      leaf learnt-interface {
        description
          "match the interface where service is learnt";
        type empty;
      }
      container location {
        description
          "match location information";
        presence "true";
        leaf civic {
          description
            "Civic location";
          type string;
        }
      }
      container message-type {
        description
          "To set the message type";
        presence "true";
        leaf announcement {
          description
            "Match Announcement/Responses";
          type empty;
        }
        leaf query {
          description
            "Match Query";
          type empty;
        }
        leaf any {
          description
            "Match Any";
          type empty;
        }
      }
      leaf service-instance {
        description
          "To set the Service Instance";
        type string;
      }
      leaf service-type {
        description
          "match mDNS service type string";
        type string;
      }
    }
  }

  grouping ncs_rpc_notif_config-service-list-grouping {
    container service-list {
      description
        "Enter the service list";
      list mdns-sd {
        description
          "Service-list for mdns-sd";
        key "service-list-name";
        leaf service-list-name {
          description
            "service-list name";
          type string;
        }
        list deny {
          description
            "Specify packets to reject";
          key "deny-pack";
          leaf deny-pack {
            type uint8 {
              range "0..100";
            }
          }
          uses ncs_rpc_notif_service-list-match-grouping;
        }
        list permit {
          description
            "Specify packets to forward";
          key "deny-pack";
          leaf deny-pack {
            type uint8 {
              range "0..100";
            }
          }
          uses ncs_rpc_notif_service-list-match-grouping;
        }
        container query {
          description
            "Service-list Query for mdns-sd";
          leaf service-type {
            description
              "Configure periodicity for each service-type";
            type string;
          }
        }
      }
    }
  }

  grouping live_ncs_service-list-match-grouping {
    container match {
      description
        "Configure parameters for service-list name";
      leaf learnt-interface {
        description
          "match the interface where service is learnt";
        type empty;
      }
      container location {
        description
          "match location information";
        presence "true";
        leaf civic {
          description
            "Civic location";
          type string;
        }
      }
      container message-type {
        description
          "To set the message type";
        presence "true";
        leaf announcement {
          description
            "Match Announcement/Responses";
          type empty;
        }
        leaf query {
          description
            "Match Query";
          type empty;
        }
        leaf any {
          description
            "Match Any";
          type empty;
        }
      }
      leaf service-instance {
        description
          "To set the Service Instance";
        type string;
      }
      leaf service-type {
        description
          "match mDNS service type string";
        type string;
      }
    }
  }

  grouping live_ncs_config-service-list-grouping {
    container service-list {
      description
        "Enter the service list";
      list mdns-sd {
        description
          "Service-list for mdns-sd";
        key "service-list-name";
        leaf service-list-name {
          description
            "service-list name";
          type string;
        }
        list deny {
          description
            "Specify packets to reject";
          key "deny-pack";
          leaf deny-pack {
            type uint8 {
              range "0..100";
            }
          }
          uses live_ncs_service-list-match-grouping;
        }
        list permit {
          description
            "Specify packets to forward";
          key "deny-pack";
          leaf deny-pack {
            type uint8 {
              range "0..100";
            }
          }
          uses live_ncs_service-list-match-grouping;
        }
        container query {
          description
            "Service-list Query for mdns-sd";
          leaf service-type {
            description
              "Configure periodicity for each service-type";
            type string;
          }
        }
      }
    }
  }

  grouping service-list-match-grouping {
    container match {
      description
        "Configure parameters for service-list name";
      leaf learnt-interface {
        description
          "match the interface where service is learnt";
        type empty;
      }
      container location {
        description
          "match location information";
        presence "true";
        leaf civic {
          description
            "Civic location";
          type string;
        }
      }
      container message-type {
        description
          "To set the message type";
        presence "true";
        leaf announcement {
          description
            "Match Announcement/Responses";
          type empty;
        }
        leaf query {
          description
            "Match Query";
          type empty;
        }
        leaf any {
          description
            "Match Any";
          type empty;
        }
      }
      leaf service-instance {
        description
          "To set the Service Instance";
        type string;
      }
      leaf service-type {
        description
          "match mDNS service type string";
        type string;
      }
    }
  }

  grouping config-service-list-grouping {
    container service-list {
      description
        "Enter the service list";
      list mdns-sd {
        description
          "Service-list for mdns-sd";
        key "service-list-name";
        leaf service-list-name {
          description
            "service-list name";
          type string;
        }
        list deny {
          description
            "Specify packets to reject";
          key "deny-pack";
          leaf deny-pack {
            type uint8 {
              range "0..100";
            }
          }
          uses service-list-match-grouping;
        }
        list permit {
          description
            "Specify packets to forward";
          key "deny-pack";
          leaf deny-pack {
            type uint8 {
              range "0..100";
            }
          }
          uses service-list-match-grouping;
        }
        container query {
          description
            "Service-list Query for mdns-sd";
          leaf service-type {
            description
              "Configure periodicity for each service-type";
            type string;
          }
        }
      }
    }
  }

  augment "/ncs:devices/ncs:template/ncs:config/ios:native" {
    uses ncs_template_config-service-list-grouping;
  }
  augment "/ncs:devices/ncs:device/ncs:live-status/ios:native" {
    uses live_ncs_config-service-list-grouping {
      refine service-list {
        tailf:ncs-device-type "netconf";
        tailf:display-when "not(../../../ncs:module) or ../../../ncs:module[ncs:name='Cisco-IOS-XE-service-discovery'] or (../../../ncs:live-status-protocol[not(ncs:capability)]) or (../../../ncs:live-status-protocol/ncs:capability/ncs:module[.='Cisco-IOS-XE-service-discovery'])";
      }
    }
  }
  augment "/ncs:devices/ncs:device/ncs:config/ios:native" {
    uses config-service-list-grouping {
      refine service-list {
        tailf:ncs-device-type "netconf";
        tailf:display-when "not(../../../ncs:module) or ../../../ncs:module[ncs:name='Cisco-IOS-XE-service-discovery']";
      }
    }
  }
}
