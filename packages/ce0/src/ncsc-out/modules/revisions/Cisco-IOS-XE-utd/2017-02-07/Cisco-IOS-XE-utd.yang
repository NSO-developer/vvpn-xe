module Cisco-IOS-XE-utd {
  // Generated by yanger -t ncs
  tailf:ncs-device-type "netconf";

  namespace "http://cisco.com/ns/yang/Cisco-IOS-XE-utd";
  prefix ios-utd;

  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Unified Threat Defense (UTD) Yang model.
     Copyright (c) 2016 by Cisco Systems, Inc.
     All rights reserved.";

  revision 2017-02-07 {
    description
      "Initial revision";
  }

  typedef syslog-level-type {
    type enumeration {
      enum "alert";
      enum "crit";
      enum "debug";
      enum "emerg";
      enum "err";
      enum "info";
      enum "notice";
      enum "warning";
    }
  }

  grouping ncs_template_hour-minute-grouping {
    leaf hours {
      type string;
    }
    leaf minutes {
      type string;
    }
  }

  grouping ncs_template_username-password-grouping {
    leaf username {
      description
        "Provide the username for authentication";
      type string;
    }
    leaf password {
      description
        "Provide the password for authentication";
      type string;
    }
  }

  grouping ncs_template_utd-engine-standard-grouping {
    container logging {
      description
        "Provide config options for logging the alerts";
      container server {
        description
          "Log the alerts to a server";
        leaf name {
          type string;
        }
        leaf level {
          description
            "Provide the log level";
          type string;
        }
        leaf syslog {
          description
            "Log the alerts to IOS syslogs";
          type empty;
        }
      }
      container syslog {
        description
          "Log the alerts to IOS syslogs";
        presence "true";
        leaf level {
          description
            "Provide the log level";
          type string;
        }
      }
    }
    leaf policy {
      description
        "Provide the policy option (default=balanced)";
      type string;
    }
    container signature {
      description
        "Provide config options for the signatures";
      container update {
        description
          "Provide config options for the signature updates";
        container occur-at {
          description
            "Specify update occurence by calendar time";
          container daily {
            description
              "Option for daily update";
            uses ncs_template_hour-minute-grouping;
          }
          container monthly {
            description
              "Option for monthly update";
            leaf days {
              type string;
            }
            uses ncs_template_hour-minute-grouping;
          }
          container weekly {
            description
              "Option for weekly update";
            leaf days {
              type string;
            }
            uses ncs_template_hour-minute-grouping;
          }
        }
        container server {
          description
            "Provide config options for the signature update server";
          container cisco {
            description
              "Use Cisco site to provide updates";
            uses ncs_template_username-password-grouping;
          }
          container url {
            description
              "Enter the complete URL for the path to the update server";
            choice url-uname-passwd {
              case all-case {
                container all {
                  leaf name {
                    type string;
                  }
                  uses ncs_template_username-password-grouping;
                }
              }
              case name-only {
                leaf name {
                  type string;
                }
              }
            }
          }
        }
      }
    }
    leaf threat {
      description
        "Provide the threat detection/protection option (default=detection)";
      type string;
    }
    leaf whitelist {
      description
        "Enable whitelisting under the utd engine";
      type empty;
    }
  }

  grouping ncs_template_config-utd-engine-grouping {
    container utd-engine {
      description
        "Global Unified Threat Defense Engine";
      container utd {
        container engine {
          description
            "UTD engine";
          container advanced {
            description
              "UTD engine advanced";
            container default {
              description
                "Set a command to its defaults";
              container threat {
                description
                  "Provide threat detection";
                presence "true";
              }
            }
            container threat {
              description
                "Provide threat detection";
              presence "true";
              leaf detection {
                description
                  "Provide threat detection";
                type empty;
              }
            }
          }
          container standard {
            description
              "UTD engine standard";
            status deprecated;
            container default {
              description
                "Set a command to its defaults";
              leaf policy {
                description
                  "Provide the policy option (default=balanced)";
                type empty;
              }
              leaf threat {
                description
                  "Provide the threat detection/protection option (default=detection)";
                type empty;
              }
            }
            uses ncs_template_utd-engine-standard-grouping;
          }
        }
        container whitelist {
          description
            "UTD whitelist config submode";
          status deprecated;
          container signature {
            description
              "Provide signatures for the whitelist";
            leaf id {
              description
                "Provide signature id for the whitelist";
              type string;
            }
            leaf comment {
              description
                "Provide a comment for the signature";
              type string;
            }
          }
        }
      }
    }
  }

  grouping ncs_template_config-utd-grouping {
    container utd {
      description
        "Global Unified Threat Defense";
      presence "true";
    }
  }

  grouping ncs_rpc_notif_hour-minute-grouping {
    leaf hours {
      type uint8 {
        range "0..23";
      }
    }
    leaf minutes {
      type uint8 {
        range "0..59";
      }
    }
  }

  grouping ncs_rpc_notif_username-password-grouping {
    leaf username {
      description
        "Provide the username for authentication";
      type string;
    }
    leaf password {
      description
        "Provide the password for authentication";
      type string;
    }
  }

  grouping ncs_rpc_notif_utd-engine-standard-grouping {
    container logging {
      description
        "Provide config options for logging the alerts";
      container server {
        description
          "Log the alerts to a server";
        leaf name {
          type string;
        }
        leaf level {
          description
            "Provide the log level";
          type syslog-level-type;
        }
        leaf syslog {
          description
            "Log the alerts to IOS syslogs";
          type empty;
        }
      }
      container syslog {
        description
          "Log the alerts to IOS syslogs";
        presence "true";
        leaf level {
          description
            "Provide the log level";
          type syslog-level-type;
        }
      }
    }
    leaf policy {
      description
        "Provide the policy option (default=balanced)";
      type enumeration {
        enum "balanced";
        enum "connectivity";
        enum "security";
      }
    }
    container signature {
      description
        "Provide config options for the signatures";
      container update {
        description
          "Provide config options for the signature updates";
        container occur-at {
          description
            "Specify update occurence by calendar time";
          container daily {
            description
              "Option for daily update";
            uses ncs_rpc_notif_hour-minute-grouping;
          }
          container monthly {
            description
              "Option for monthly update";
            leaf days {
              type string;
            }
            uses ncs_rpc_notif_hour-minute-grouping;
          }
          container weekly {
            description
              "Option for weekly update";
            leaf days {
              type string;
            }
            uses ncs_rpc_notif_hour-minute-grouping;
          }
        }
        container server {
          description
            "Provide config options for the signature update server";
          container cisco {
            description
              "Use Cisco site to provide updates";
            uses ncs_rpc_notif_username-password-grouping;
          }
          container url {
            description
              "Enter the complete URL for the path to the update server";
            choice url-uname-passwd {
              case all-case {
                container all {
                  leaf name {
                    type string;
                  }
                  uses ncs_rpc_notif_username-password-grouping;
                }
              }
              case name-only {
                leaf name {
                  type string;
                }
              }
            }
          }
        }
      }
    }
    leaf threat {
      description
        "Provide the threat detection/protection option (default=detection)";
      type enumeration {
        enum "detection";
        enum "protection";
      }
    }
    leaf whitelist {
      description
        "Enable whitelisting under the utd engine";
      type empty;
    }
  }

  grouping ncs_rpc_notif_config-utd-engine-grouping {
    container utd-engine {
      description
        "Global Unified Threat Defense Engine";
      container utd {
        container engine {
          description
            "UTD engine";
          container advanced {
            description
              "UTD engine advanced";
            container default {
              description
                "Set a command to its defaults";
              container threat {
                description
                  "Provide threat detection";
                presence "true";
              }
            }
            container threat {
              description
                "Provide threat detection";
              presence "true";
              leaf detection {
                description
                  "Provide threat detection";
                type empty;
              }
            }
          }
          container standard {
            description
              "UTD engine standard";
            status deprecated;
            container default {
              description
                "Set a command to its defaults";
              leaf policy {
                description
                  "Provide the policy option (default=balanced)";
                type empty;
              }
              leaf threat {
                description
                  "Provide the threat detection/protection option (default=detection)";
                type empty;
              }
            }
            uses ncs_rpc_notif_utd-engine-standard-grouping;
          }
        }
        container whitelist {
          description
            "UTD whitelist config submode";
          status deprecated;
          container signature {
            description
              "Provide signatures for the whitelist";
            leaf id {
              description
                "Provide signature id for the whitelist";
              type uint64 {
                range "0..4294967295";
              }
            }
            leaf comment {
              description
                "Provide a comment for the signature";
              type string;
            }
          }
        }
      }
    }
  }

  grouping ncs_rpc_notif_config-utd-grouping {
    container utd {
      description
        "Global Unified Threat Defense";
      presence "true";
    }
  }

  grouping live_ncs_hour-minute-grouping {
    leaf hours {
      type uint8 {
        range "0..23";
      }
    }
    leaf minutes {
      type uint8 {
        range "0..59";
      }
    }
  }

  grouping live_ncs_username-password-grouping {
    leaf username {
      description
        "Provide the username for authentication";
      type string;
    }
    leaf password {
      description
        "Provide the password for authentication";
      type string;
    }
  }

  grouping live_ncs_utd-engine-standard-grouping {
    container logging {
      description
        "Provide config options for logging the alerts";
      container server {
        description
          "Log the alerts to a server";
        leaf name {
          type string;
        }
        leaf level {
          description
            "Provide the log level";
          type syslog-level-type;
        }
        leaf syslog {
          description
            "Log the alerts to IOS syslogs";
          type empty;
        }
      }
      container syslog {
        description
          "Log the alerts to IOS syslogs";
        presence "true";
        leaf level {
          description
            "Provide the log level";
          type syslog-level-type;
        }
      }
    }
    leaf policy {
      description
        "Provide the policy option (default=balanced)";
      type enumeration {
        enum "balanced";
        enum "connectivity";
        enum "security";
      }
    }
    container signature {
      description
        "Provide config options for the signatures";
      container update {
        description
          "Provide config options for the signature updates";
        container occur-at {
          description
            "Specify update occurence by calendar time";
          container daily {
            description
              "Option for daily update";
            uses live_ncs_hour-minute-grouping;
          }
          container monthly {
            description
              "Option for monthly update";
            leaf days {
              type string;
            }
            uses live_ncs_hour-minute-grouping;
          }
          container weekly {
            description
              "Option for weekly update";
            leaf days {
              type string;
            }
            uses live_ncs_hour-minute-grouping;
          }
        }
        container server {
          description
            "Provide config options for the signature update server";
          container cisco {
            description
              "Use Cisco site to provide updates";
            uses live_ncs_username-password-grouping;
          }
          container url {
            description
              "Enter the complete URL for the path to the update server";
            choice url-uname-passwd {
              case all-case {
                container all {
                  leaf name {
                    type string;
                  }
                  uses live_ncs_username-password-grouping;
                }
              }
              case name-only {
                leaf name {
                  type string;
                }
              }
            }
          }
        }
      }
    }
    leaf threat {
      description
        "Provide the threat detection/protection option (default=detection)";
      type enumeration {
        enum "detection";
        enum "protection";
      }
    }
    leaf whitelist {
      description
        "Enable whitelisting under the utd engine";
      type empty;
    }
  }

  grouping live_ncs_config-utd-engine-grouping {
    container utd-engine {
      description
        "Global Unified Threat Defense Engine";
      container utd {
        container engine {
          description
            "UTD engine";
          container advanced {
            description
              "UTD engine advanced";
            container default {
              description
                "Set a command to its defaults";
              container threat {
                description
                  "Provide threat detection";
                presence "true";
              }
            }
            container threat {
              description
                "Provide threat detection";
              presence "true";
              leaf detection {
                description
                  "Provide threat detection";
                type empty;
              }
            }
          }
          container standard {
            description
              "UTD engine standard";
            status deprecated;
            container default {
              description
                "Set a command to its defaults";
              leaf policy {
                description
                  "Provide the policy option (default=balanced)";
                type empty;
              }
              leaf threat {
                description
                  "Provide the threat detection/protection option (default=detection)";
                type empty;
              }
            }
            uses live_ncs_utd-engine-standard-grouping;
          }
        }
        container whitelist {
          description
            "UTD whitelist config submode";
          status deprecated;
          container signature {
            description
              "Provide signatures for the whitelist";
            leaf id {
              description
                "Provide signature id for the whitelist";
              type uint64 {
                range "0..4294967295";
              }
            }
            leaf comment {
              description
                "Provide a comment for the signature";
              type string;
            }
          }
        }
      }
    }
  }

  grouping live_ncs_config-utd-grouping {
    container utd {
      description
        "Global Unified Threat Defense";
      presence "true";
    }
  }

  grouping hour-minute-grouping {
    leaf hours {
      type uint8 {
        range "0..23";
      }
    }
    leaf minutes {
      type uint8 {
        range "0..59";
      }
    }
  }

  grouping username-password-grouping {
    leaf username {
      description
        "Provide the username for authentication";
      type string;
    }
    leaf password {
      description
        "Provide the password for authentication";
      type string;
    }
  }

  grouping utd-engine-standard-grouping {
    container logging {
      description
        "Provide config options for logging the alerts";
      container server {
        description
          "Log the alerts to a server";
        leaf name {
          type string;
        }
        leaf level {
          description
            "Provide the log level";
          type syslog-level-type;
        }
        leaf syslog {
          description
            "Log the alerts to IOS syslogs";
          type empty;
        }
      }
      container syslog {
        description
          "Log the alerts to IOS syslogs";
        presence "true";
        leaf level {
          description
            "Provide the log level";
          type syslog-level-type;
        }
      }
    }
    leaf policy {
      description
        "Provide the policy option (default=balanced)";
      type enumeration {
        enum "balanced";
        enum "connectivity";
        enum "security";
      }
    }
    container signature {
      description
        "Provide config options for the signatures";
      container update {
        description
          "Provide config options for the signature updates";
        container occur-at {
          description
            "Specify update occurence by calendar time";
          container daily {
            description
              "Option for daily update";
            uses hour-minute-grouping;
          }
          container monthly {
            description
              "Option for monthly update";
            leaf days {
              type string;
            }
            uses hour-minute-grouping;
          }
          container weekly {
            description
              "Option for weekly update";
            leaf days {
              type string;
            }
            uses hour-minute-grouping;
          }
        }
        container server {
          description
            "Provide config options for the signature update server";
          container cisco {
            description
              "Use Cisco site to provide updates";
            uses username-password-grouping;
          }
          container url {
            description
              "Enter the complete URL for the path to the update server";
            choice url-uname-passwd {
              case all-case {
                container all {
                  leaf name {
                    type string;
                  }
                  uses username-password-grouping;
                }
              }
              case name-only {
                leaf name {
                  type string;
                }
              }
            }
          }
        }
      }
    }
    leaf threat {
      description
        "Provide the threat detection/protection option (default=detection)";
      type enumeration {
        enum "detection";
        enum "protection";
      }
    }
    leaf whitelist {
      description
        "Enable whitelisting under the utd engine";
      type empty;
    }
  }

  grouping config-utd-engine-grouping {
    container utd-engine {
      description
        "Global Unified Threat Defense Engine";
      container utd {
        container engine {
          description
            "UTD engine";
          container advanced {
            description
              "UTD engine advanced";
            container default {
              description
                "Set a command to its defaults";
              container threat {
                description
                  "Provide threat detection";
                presence "true";
              }
            }
            container threat {
              description
                "Provide threat detection";
              presence "true";
              leaf detection {
                description
                  "Provide threat detection";
                type empty;
              }
            }
          }
          container standard {
            description
              "UTD engine standard";
            status deprecated;
            container default {
              description
                "Set a command to its defaults";
              leaf policy {
                description
                  "Provide the policy option (default=balanced)";
                type empty;
              }
              leaf threat {
                description
                  "Provide the threat detection/protection option (default=detection)";
                type empty;
              }
            }
            uses utd-engine-standard-grouping;
          }
        }
        container whitelist {
          description
            "UTD whitelist config submode";
          status deprecated;
          container signature {
            description
              "Provide signatures for the whitelist";
            leaf id {
              description
                "Provide signature id for the whitelist";
              type uint64 {
                range "0..4294967295";
              }
            }
            leaf comment {
              description
                "Provide a comment for the signature";
              type string;
            }
          }
        }
      }
    }
  }

  grouping config-utd-grouping {
    container utd {
      description
        "Global Unified Threat Defense";
      presence "true";
    }
  }

  augment "/ncs:devices/ncs:template/ncs:config/ios:native" {
    uses ncs_template_config-utd-grouping;
    uses ncs_template_config-utd-engine-grouping;
  }
  augment "/ncs:devices/ncs:device/ncs:live-status/ios:native" {
    uses live_ncs_config-utd-grouping {
      refine utd {
        tailf:ncs-device-type "netconf";
        tailf:display-when "not(../../../ncs:module) or ../../../ncs:module[ncs:name='Cisco-IOS-XE-utd'] or (../../../ncs:live-status-protocol[not(ncs:capability)]) or (../../../ncs:live-status-protocol/ncs:capability/ncs:module[.='Cisco-IOS-XE-utd'])";
      }
    }
    uses live_ncs_config-utd-engine-grouping {
      refine utd-engine {
        tailf:ncs-device-type "netconf";
        tailf:display-when "not(../../../ncs:module) or ../../../ncs:module[ncs:name='Cisco-IOS-XE-utd'] or (../../../ncs:live-status-protocol[not(ncs:capability)]) or (../../../ncs:live-status-protocol/ncs:capability/ncs:module[.='Cisco-IOS-XE-utd'])";
      }
    }
  }
  augment "/ncs:devices/ncs:device/ncs:config/ios:native" {
    uses config-utd-grouping {
      refine utd {
        tailf:ncs-device-type "netconf";
        tailf:display-when "not(../../../ncs:module) or ../../../ncs:module[ncs:name='Cisco-IOS-XE-utd']";
      }
    }
    uses config-utd-engine-grouping {
      refine utd-engine {
        tailf:ncs-device-type "netconf";
        tailf:display-when "not(../../../ncs:module) or ../../../ncs:module[ncs:name='Cisco-IOS-XE-utd']";
      }
    }
  }
}
