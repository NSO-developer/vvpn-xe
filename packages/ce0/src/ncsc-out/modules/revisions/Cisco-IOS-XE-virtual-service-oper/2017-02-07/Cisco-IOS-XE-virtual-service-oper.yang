module Cisco-IOS-XE-virtual-service-oper {
  // Generated by yanger -t ncs
  tailf:ncs-device-type "netconf";

  yang-version "1";
  namespace "http://cisco.com/ns/yang/Cisco-IOS-XE-virtual-service-oper";
  prefix virtual-service-ios-xe-oper;

  import ietf-yang-types {
    prefix yang;
  }
  import tailf-ncs {
    prefix ncs;
  }
  import tailf-common {
    prefix tailf;
  }

  organization "Cisco Systems, Inc.";
  contact
    " Cisco Systems, Inc. Customer Service Postal: 170 W Tasman Drive
     San Jose, CA 95134 Tel: +1 1800 553-NETS E-mail: cs-yang@cisco.com";
  description
    "This module contains a collection of YANG definitions for monitoring
     virtual services in a Network Element.Copyright (c) 2016-2017 by Cisco Systems, Inc.All rights reserved.";

  revision 2017-02-07 {
    description
      "Initial revision";
  }

  grouping ncs_template_application {
    leaf name {
      type string;
      description
        "Name of the application.";
    }
    leaf installed-version {
      type string;
      description
        "Version of the application.";
    }
    leaf description {
      type string;
      description
        "Description of the application.";
    }
  }

  grouping ncs_template_signing {
    leaf key-type {
      type string;
      description
        "The Type of the signed key.";
    }
    leaf method {
      type string;
      description
        "The method the key was signed.";
    }
  }

  grouping ncs_template_licensing {
    leaf name {
      type string;
      description
        "The name of the license.";
    }
    leaf version {
      type string;
      description
        "The version of the license.";
    }
  }

  grouping ncs_template_package-information {
    leaf name {
      type string;
      description
        "Name of the package for the virtual-service.";
    }
    leaf path {
      type string;
      description
        "Path to the package.";
    }
    container application {
      description
        "Details of the application.";
      uses virtual-service-ios-xe-oper:ncs_template_application;
    }
    container signing {
      description
        "Details of the key signing.";
      uses virtual-service-ios-xe-oper:ncs_template_signing;
    }
    container licensing {
      description
        "Details about the license.";
      uses virtual-service-ios-xe-oper:ncs_template_licensing;
    }
  }

  grouping ncs_template_vs-process {
    leaf name {
      type string;
      description
        "Name of the proccess.";
    }
    leaf status {
      type string;
      description
        "Status of the proccess.";
    }
    leaf pid {
      type string;
      description
        "Process ID.";
    }
    leaf uptime {
      type string;
      description
        "Up time of the proccess.";
    }
    leaf memory {
      type string;
      description
        "Memory of the proccess.";
    }
  }

  grouping ncs_template_detailed-guest-status {
    container processes {
      description
        "All the processes.";
      uses virtual-service-ios-xe-oper:ncs_template_vs-process;
    }
  }

  grouping ncs_template_resource-reservation {
    leaf disk {
      type string;
      description
        "The amount of reserverd disk space in MB.";
    }
    leaf memory {
      type string;
      description
        "The amount of reserved memory in MB.";
    }
    leaf cpu {
      type string;
      description
        "The percentage of reserved cpu.";
    }
  }

  grouping ncs_template_attached-device {
    leaf name {
      type string;
      description
        "The name of the attached device.";
    }
    leaf type {
      type string;
      description
        "The type of the attached device.";
    }
    leaf alias {
      type string;
      description
        "The alias for the attached device.";
    }
  }

  grouping ncs_template_network-interface {
    leaf mac-address {
      type string;
      description
        "The MAC address for the network interface.";
    }
    leaf attached-interface {
      type string;
      description
        "Name of the the attached interface";
    }
  }

  grouping ncs_template_guest-route {
    leaf route {
      type string;
      description
        "A guest route for a guest interface.";
    }
  }

  grouping ncs_template_resource-admission {
    leaf state {
      type string;
      description
        "Thes status the of the resource allocation.";
    }
    leaf disk-space {
      type string;
      description
        "The amount of disk space being allocated for the virtual-service.";
    }
    leaf memory {
      type string;
      description
        "The amount of memory being allocated for the virtual-service.";
    }
    leaf cpu {
      type string;
      description
        "The percentage of cpu being allocated for the virtual-service";
    }
    leaf vcpus {
      type string;
      description
        "The amount of VCPUs being allocated for the virtual-service.";
    }
  }

  grouping ncs_template_details {
    leaf state {
      type string;
      description
        "State of the virtual service.";
    }
    container package-information {
      description
        "Details of the package for the virtual-service.";
      uses virtual-service-ios-xe-oper:ncs_template_package-information;
    }
    container detailed-guest-status {
      description
        "Details on the guest status.";
      uses virtual-service-ios-xe-oper:ncs_template_detailed-guest-status;
    }
    leaf activated-profile-name {
      type string;
      description
        "The activated profile name.";
    }
    container resource-reservation {
      description
        "Details of the resources reserved for this virtual service.";
      uses virtual-service-ios-xe-oper:ncs_template_resource-reservation;
    }
    leaf guest-interface {
      type string;
      description
        "The name of a guest interface.";
    }
    container resource-admission {
      description
        "Resources being allocated for the virtual-service.";
      uses virtual-service-ios-xe-oper:ncs_template_resource-admission;
    }
  }

  grouping ncs_template_cpu-util {
    leaf requested-application-util {
      type string;
      description
        "Percentage of requested CPU utilization by the virtual-service.";
    }
    leaf actual-application-util {
      type string;
      description
        "Percetnage of CPU actual utilization for the virtual-service.";
    }
    leaf cpu-state {
      type string;
      description
        "The state of the CPU utilization for the virtual-service.";
    }
  }

  grouping ncs_template_memory-util {
    leaf memory-allocation {
      type string;
      description
        "Amount of memory being allocated for the virtual-service in KB.";
    }
    leaf memory-used {
      type string;
      description
        "Amount of memory being used for the virtual-service in KB.";
    }
  }

  grouping ncs_template_network-util {
    leaf name {
      type string;
      description
        "The name of the network that is being used for the virtual-service.";
    }
    leaf alias {
      type string;
      description
        "The alias of the network that is being used for the virtual-service.";
    }
    leaf rx-packets {
      type string;
      description
        "The number of rx packets being utilized for the virtual-service.";
    }
    leaf rx-bytes {
      type string;
      description
        "The number of rx bytes being utilized for the virtual-service.";
    }
    leaf rx-errors {
      type string;
      description
        "The number of rx errors.";
    }
    leaf tx-packets {
      type string;
      description
        "The number of tx packets being utilized for the virtual-service.";
    }
    leaf tx-bytes {
      type string;
      description
        "The number of tx bytes being utilized for the virtual-service.";
    }
    leaf tx-errors {
      type string;
      description
        "The number of tx errors.";
    }
  }

  grouping ncs_template_storage-util {
    leaf name {
      type string;
      description
        "The name of the storage process being used for the virtual-service.";
    }
    leaf alias {
      type string;
      description
        "The alias of the storage process being used for the virtual-service.";
    }
    leaf rd-bytes {
      type string;
      description
        "The number of RD bytes being used for the virtual-service.";
    }
    leaf rd-requests {
      type string;
      description
        "The number of rd requests being used for the virtual-service.";
    }
    leaf errors {
      type string;
      description
        "The name of errors on the storage process.";
    }
    leaf wr-bytes {
      type string;
      description
        "The number of WR bytes for the virtual-service.";
    }
    leaf wr-requests {
      type string;
      description
        "The number of WR requests for the virtual-service.";
    }
    leaf capacity {
      type string;
      description
        "The storage capactity in 1K blocks.";
    }
    leaf available {
      type string;
      description
        "The available storage in 1K blocks.";
    }
    leaf used {
      type string;
      description
        "The number of 1K blocks being used.";
    }
    leaf usage {
      type string;
      description
        "The percetage of storage capactiy being used.";
    }
  }

  grouping ncs_template_utilization {
    leaf name {
      type string;
      description
        "The name of the virtual service.";
    }
    container cpu-util {
      description
        "Details on the CPU utilization for the virtual-service.";
      uses virtual-service-ios-xe-oper:ncs_template_cpu-util;
    }
    container memory-util {
      description
        "Details on the memory usage for the virtual-service.";
      uses virtual-service-ios-xe-oper:ncs_template_memory-util;
    }
  }

  grouping ncs_template_virtual-service {
    leaf name {
      type string;
      description
        "The name of the virtual service.";
    }
    container details {
      description
        "Details of the virtual service.";
      uses virtual-service-ios-xe-oper:ncs_template_details;
    }
    container utilization {
      description
        "Utilization of device resources for a virtual-service.";
      uses virtual-service-ios-xe-oper:ncs_template_utilization;
    }
    container network-utils {
      description
        "list of the network utilizations for the virtual-service.";
      list network-util {
        // NCS patched for predictable order
        ordered-by user;
        key "name alias";
        description
          "Details on a network utilization for the virtual-service.";
        uses virtual-service-ios-xe-oper:ncs_template_network-util;
      }
    }
    container storage-utils {
      description
        "List of the storage utilizations for the virtual-service.";
      list storage-util {
        // NCS patched for predictable order
        ordered-by user;
        key "name alias";
        description
          "Details on a storage utilization for the virtual-service.";
        uses virtual-service-ios-xe-oper:ncs_template_storage-util;
      }
    }
    container attached-devices {
      description
        "Details for the devices attached to this virtual service.";
      list attached-device {
        // NCS patched for predictable order
        ordered-by user;
        key "name";
        description
          "List of attached devices.";
        uses virtual-service-ios-xe-oper:ncs_template_attached-device;
      }
    }
    container network-interfaces {
      description
        "Details for the network interfaces.";
      list network-interface {
        // NCS patched for predictable order
        ordered-by user;
        key "mac-address";
        description
          "Details for a network interface.";
        uses virtual-service-ios-xe-oper:ncs_template_network-interface;
      }
    }
    container guest-routes {
      description
        "Routes for the guest interface.";
      list guest-route {
        // NCS patched for predictable order
        ordered-by user;
        key "route";
        description
          "List of guest routes for a guest interface.";
        uses virtual-service-ios-xe-oper:ncs_template_guest-route;
      }
    }
  }

  grouping ncs_rpc_notif_application {
    leaf name {
      type string;
      description
        "Name of the application.";
    }
    leaf installed-version {
      type string;
      description
        "Version of the application.";
    }
    leaf description {
      type string;
      description
        "Description of the application.";
    }
  }

  grouping ncs_rpc_notif_signing {
    leaf key-type {
      type string;
      description
        "The Type of the signed key.";
    }
    leaf method {
      type string;
      description
        "The method the key was signed.";
    }
  }

  grouping ncs_rpc_notif_licensing {
    leaf name {
      type string;
      description
        "The name of the license.";
    }
    leaf version {
      type string;
      description
        "The version of the license.";
    }
  }

  grouping ncs_rpc_notif_package-information {
    leaf name {
      type string;
      description
        "Name of the package for the virtual-service.";
    }
    leaf path {
      type string;
      description
        "Path to the package.";
    }
    container application {
      description
        "Details of the application.";
      uses virtual-service-ios-xe-oper:ncs_rpc_notif_application;
    }
    container signing {
      description
        "Details of the key signing.";
      uses virtual-service-ios-xe-oper:ncs_rpc_notif_signing;
    }
    container licensing {
      description
        "Details about the license.";
      uses virtual-service-ios-xe-oper:ncs_rpc_notif_licensing;
    }
  }

  grouping ncs_rpc_notif_vs-process {
    leaf name {
      type string;
      description
        "Name of the proccess.";
    }
    leaf status {
      type string;
      description
        "Status of the proccess.";
    }
    leaf pid {
      type string;
      description
        "Process ID.";
    }
    leaf uptime {
      type string;
      description
        "Up time of the proccess.";
    }
    leaf memory {
      type string;
      description
        "Memory of the proccess.";
    }
  }

  grouping ncs_rpc_notif_detailed-guest-status {
    container processes {
      description
        "All the processes.";
      uses virtual-service-ios-xe-oper:ncs_rpc_notif_vs-process;
    }
  }

  grouping ncs_rpc_notif_resource-reservation {
    leaf disk {
      type uint64;
      description
        "The amount of reserverd disk space in MB.";
    }
    leaf memory {
      type uint64;
      description
        "The amount of reserved memory in MB.";
    }
    leaf cpu {
      type uint64;
      description
        "The percentage of reserved cpu.";
    }
  }

  grouping ncs_rpc_notif_attached-device {
    leaf name {
      type string;
      description
        "The name of the attached device.";
    }
    leaf type {
      type string;
      description
        "The type of the attached device.";
    }
    leaf alias {
      type string;
      description
        "The alias for the attached device.";
    }
  }

  grouping ncs_rpc_notif_network-interface {
    leaf mac-address {
      type yang:mac-address;
      description
        "The MAC address for the network interface.";
    }
    leaf attached-interface {
      type string;
      description
        "Name of the the attached interface";
    }
  }

  grouping ncs_rpc_notif_guest-route {
    leaf route {
      type string;
      description
        "A guest route for a guest interface.";
    }
  }

  grouping ncs_rpc_notif_resource-admission {
    leaf state {
      type string;
      description
        "Thes status the of the resource allocation.";
    }
    leaf disk-space {
      type string;
      description
        "The amount of disk space being allocated for the virtual-service.";
    }
    leaf memory {
      type string;
      description
        "The amount of memory being allocated for the virtual-service.";
    }
    leaf cpu {
      type uint64;
      description
        "The percentage of cpu being allocated for the virtual-service";
    }
    leaf vcpus {
      type string;
      description
        "The amount of VCPUs being allocated for the virtual-service.";
    }
  }

  grouping ncs_rpc_notif_details {
    leaf state {
      type string;
      description
        "State of the virtual service.";
    }
    container package-information {
      description
        "Details of the package for the virtual-service.";
      uses virtual-service-ios-xe-oper:ncs_rpc_notif_package-information;
    }
    container detailed-guest-status {
      description
        "Details on the guest status.";
      uses virtual-service-ios-xe-oper:ncs_rpc_notif_detailed-guest-status;
    }
    leaf activated-profile-name {
      type string;
      description
        "The activated profile name.";
    }
    container resource-reservation {
      description
        "Details of the resources reserved for this virtual service.";
      uses virtual-service-ios-xe-oper:ncs_rpc_notif_resource-reservation;
    }
    leaf guest-interface {
      type string;
      description
        "The name of a guest interface.";
    }
    container resource-admission {
      description
        "Resources being allocated for the virtual-service.";
      uses virtual-service-ios-xe-oper:ncs_rpc_notif_resource-admission;
    }
  }

  grouping ncs_rpc_notif_cpu-util {
    leaf requested-application-util {
      type uint64;
      description
        "Percentage of requested CPU utilization by the virtual-service.";
    }
    leaf actual-application-util {
      type uint64;
      description
        "Percetnage of CPU actual utilization for the virtual-service.";
    }
    leaf cpu-state {
      type string;
      description
        "The state of the CPU utilization for the virtual-service.";
    }
  }

  grouping ncs_rpc_notif_memory-util {
    leaf memory-allocation {
      type string;
      description
        "Amount of memory being allocated for the virtual-service in KB.";
    }
    leaf memory-used {
      type string;
      description
        "Amount of memory being used for the virtual-service in KB.";
    }
  }

  grouping ncs_rpc_notif_network-util {
    leaf name {
      type string;
      description
        "The name of the network that is being used for the virtual-service.";
    }
    leaf alias {
      type string;
      description
        "The alias of the network that is being used for the virtual-service.";
    }
    leaf rx-packets {
      type uint64;
      description
        "The number of rx packets being utilized for the virtual-service.";
    }
    leaf rx-bytes {
      type uint64;
      description
        "The number of rx bytes being utilized for the virtual-service.";
    }
    leaf rx-errors {
      type uint64;
      description
        "The number of rx errors.";
    }
    leaf tx-packets {
      type uint64;
      description
        "The number of tx packets being utilized for the virtual-service.";
    }
    leaf tx-bytes {
      type uint64;
      description
        "The number of tx bytes being utilized for the virtual-service.";
    }
    leaf tx-errors {
      type uint64;
      description
        "The number of tx errors.";
    }
  }

  grouping ncs_rpc_notif_storage-util {
    leaf name {
      type string;
      description
        "The name of the storage process being used for the virtual-service.";
    }
    leaf alias {
      type string;
      description
        "The alias of the storage process being used for the virtual-service.";
    }
    leaf rd-bytes {
      type uint64;
      description
        "The number of RD bytes being used for the virtual-service.";
    }
    leaf rd-requests {
      type uint64;
      description
        "The number of rd requests being used for the virtual-service.";
    }
    leaf errors {
      type uint64;
      description
        "The name of errors on the storage process.";
    }
    leaf wr-bytes {
      type uint64;
      description
        "The number of WR bytes for the virtual-service.";
    }
    leaf wr-requests {
      type uint64;
      description
        "The number of WR requests for the virtual-service.";
    }
    leaf capacity {
      type uint64;
      description
        "The storage capactity in 1K blocks.";
    }
    leaf available {
      type string;
      description
        "The available storage in 1K blocks.";
    }
    leaf used {
      type uint64;
      description
        "The number of 1K blocks being used.";
    }
    leaf usage {
      type string;
      description
        "The percetage of storage capactiy being used.";
    }
  }

  grouping ncs_rpc_notif_utilization {
    leaf name {
      type string;
      description
        "The name of the virtual service.";
    }
    container cpu-util {
      description
        "Details on the CPU utilization for the virtual-service.";
      uses virtual-service-ios-xe-oper:ncs_rpc_notif_cpu-util;
    }
    container memory-util {
      description
        "Details on the memory usage for the virtual-service.";
      uses virtual-service-ios-xe-oper:ncs_rpc_notif_memory-util;
    }
  }

  grouping ncs_rpc_notif_virtual-service {
    leaf name {
      type string;
      description
        "The name of the virtual service.";
    }
    container details {
      description
        "Details of the virtual service.";
      uses virtual-service-ios-xe-oper:ncs_rpc_notif_details;
    }
    container utilization {
      description
        "Utilization of device resources for a virtual-service.";
      uses virtual-service-ios-xe-oper:ncs_rpc_notif_utilization;
    }
    container network-utils {
      description
        "list of the network utilizations for the virtual-service.";
      list network-util {
        key "name alias";
        description
          "Details on a network utilization for the virtual-service.";
        uses virtual-service-ios-xe-oper:ncs_rpc_notif_network-util;
      }
    }
    container storage-utils {
      description
        "List of the storage utilizations for the virtual-service.";
      list storage-util {
        key "name alias";
        description
          "Details on a storage utilization for the virtual-service.";
        uses virtual-service-ios-xe-oper:ncs_rpc_notif_storage-util;
      }
    }
    container attached-devices {
      description
        "Details for the devices attached to this virtual service.";
      list attached-device {
        key "name";
        description
          "List of attached devices.";
        uses virtual-service-ios-xe-oper:ncs_rpc_notif_attached-device;
      }
    }
    container network-interfaces {
      description
        "Details for the network interfaces.";
      list network-interface {
        key "mac-address";
        description
          "Details for a network interface.";
        uses virtual-service-ios-xe-oper:ncs_rpc_notif_network-interface;
      }
    }
    container guest-routes {
      description
        "Routes for the guest interface.";
      list guest-route {
        key "route";
        description
          "List of guest routes for a guest interface.";
        uses virtual-service-ios-xe-oper:ncs_rpc_notif_guest-route;
      }
    }
  }

  grouping live_ncs_application {
    leaf name {
      type string;
      description
        "Name of the application.";
    }
    leaf installed-version {
      type string;
      description
        "Version of the application.";
    }
    leaf description {
      type string;
      description
        "Description of the application.";
    }
  }

  grouping live_ncs_signing {
    leaf key-type {
      type string;
      description
        "The Type of the signed key.";
    }
    leaf method {
      type string;
      description
        "The method the key was signed.";
    }
  }

  grouping live_ncs_licensing {
    leaf name {
      type string;
      description
        "The name of the license.";
    }
    leaf version {
      type string;
      description
        "The version of the license.";
    }
  }

  grouping live_ncs_package-information {
    leaf name {
      type string;
      description
        "Name of the package for the virtual-service.";
    }
    leaf path {
      type string;
      description
        "Path to the package.";
    }
    container application {
      description
        "Details of the application.";
      uses virtual-service-ios-xe-oper:live_ncs_application;
    }
    container signing {
      description
        "Details of the key signing.";
      uses virtual-service-ios-xe-oper:live_ncs_signing;
    }
    container licensing {
      description
        "Details about the license.";
      uses virtual-service-ios-xe-oper:live_ncs_licensing;
    }
  }

  grouping live_ncs_vs-process {
    leaf name {
      type string;
      description
        "Name of the proccess.";
    }
    leaf status {
      type string;
      description
        "Status of the proccess.";
    }
    leaf pid {
      type string;
      description
        "Process ID.";
    }
    leaf uptime {
      type string;
      description
        "Up time of the proccess.";
    }
    leaf memory {
      type string;
      description
        "Memory of the proccess.";
    }
  }

  grouping live_ncs_detailed-guest-status {
    container processes {
      description
        "All the processes.";
      uses virtual-service-ios-xe-oper:live_ncs_vs-process;
    }
  }

  grouping live_ncs_resource-reservation {
    leaf disk {
      type uint64;
      description
        "The amount of reserverd disk space in MB.";
    }
    leaf memory {
      type uint64;
      description
        "The amount of reserved memory in MB.";
    }
    leaf cpu {
      type uint64;
      description
        "The percentage of reserved cpu.";
    }
  }

  grouping live_ncs_attached-device {
    leaf name {
      type string;
      description
        "The name of the attached device.";
    }
    leaf type {
      type string;
      description
        "The type of the attached device.";
    }
    leaf alias {
      type string;
      description
        "The alias for the attached device.";
    }
  }

  grouping live_ncs_network-interface {
    leaf mac-address {
      type yang:mac-address;
      description
        "The MAC address for the network interface.";
    }
    leaf attached-interface {
      type string;
      description
        "Name of the the attached interface";
    }
  }

  grouping live_ncs_guest-route {
    leaf route {
      type string;
      description
        "A guest route for a guest interface.";
    }
  }

  grouping live_ncs_resource-admission {
    leaf state {
      type string;
      description
        "Thes status the of the resource allocation.";
    }
    leaf disk-space {
      type string;
      description
        "The amount of disk space being allocated for the virtual-service.";
    }
    leaf memory {
      type string;
      description
        "The amount of memory being allocated for the virtual-service.";
    }
    leaf cpu {
      type uint64;
      description
        "The percentage of cpu being allocated for the virtual-service";
    }
    leaf vcpus {
      type string;
      description
        "The amount of VCPUs being allocated for the virtual-service.";
    }
  }

  grouping live_ncs_details {
    leaf state {
      type string;
      description
        "State of the virtual service.";
    }
    container package-information {
      description
        "Details of the package for the virtual-service.";
      uses virtual-service-ios-xe-oper:live_ncs_package-information;
    }
    container detailed-guest-status {
      description
        "Details on the guest status.";
      uses virtual-service-ios-xe-oper:live_ncs_detailed-guest-status;
    }
    leaf activated-profile-name {
      type string;
      description
        "The activated profile name.";
    }
    container resource-reservation {
      description
        "Details of the resources reserved for this virtual service.";
      uses virtual-service-ios-xe-oper:live_ncs_resource-reservation;
    }
    leaf guest-interface {
      type string;
      description
        "The name of a guest interface.";
    }
    container resource-admission {
      description
        "Resources being allocated for the virtual-service.";
      uses virtual-service-ios-xe-oper:live_ncs_resource-admission;
    }
  }

  grouping live_ncs_cpu-util {
    leaf requested-application-util {
      type uint64;
      description
        "Percentage of requested CPU utilization by the virtual-service.";
    }
    leaf actual-application-util {
      type uint64;
      description
        "Percetnage of CPU actual utilization for the virtual-service.";
    }
    leaf cpu-state {
      type string;
      description
        "The state of the CPU utilization for the virtual-service.";
    }
  }

  grouping live_ncs_memory-util {
    leaf memory-allocation {
      type string;
      description
        "Amount of memory being allocated for the virtual-service in KB.";
    }
    leaf memory-used {
      type string;
      description
        "Amount of memory being used for the virtual-service in KB.";
    }
  }

  grouping live_ncs_network-util {
    leaf name {
      type string;
      description
        "The name of the network that is being used for the virtual-service.";
    }
    leaf alias {
      type string;
      description
        "The alias of the network that is being used for the virtual-service.";
    }
    leaf rx-packets {
      type uint64;
      description
        "The number of rx packets being utilized for the virtual-service.";
    }
    leaf rx-bytes {
      type uint64;
      description
        "The number of rx bytes being utilized for the virtual-service.";
    }
    leaf rx-errors {
      type uint64;
      description
        "The number of rx errors.";
    }
    leaf tx-packets {
      type uint64;
      description
        "The number of tx packets being utilized for the virtual-service.";
    }
    leaf tx-bytes {
      type uint64;
      description
        "The number of tx bytes being utilized for the virtual-service.";
    }
    leaf tx-errors {
      type uint64;
      description
        "The number of tx errors.";
    }
  }

  grouping live_ncs_storage-util {
    leaf name {
      type string;
      description
        "The name of the storage process being used for the virtual-service.";
    }
    leaf alias {
      type string;
      description
        "The alias of the storage process being used for the virtual-service.";
    }
    leaf rd-bytes {
      type uint64;
      description
        "The number of RD bytes being used for the virtual-service.";
    }
    leaf rd-requests {
      type uint64;
      description
        "The number of rd requests being used for the virtual-service.";
    }
    leaf errors {
      type uint64;
      description
        "The name of errors on the storage process.";
    }
    leaf wr-bytes {
      type uint64;
      description
        "The number of WR bytes for the virtual-service.";
    }
    leaf wr-requests {
      type uint64;
      description
        "The number of WR requests for the virtual-service.";
    }
    leaf capacity {
      type uint64;
      description
        "The storage capactity in 1K blocks.";
    }
    leaf available {
      type string;
      description
        "The available storage in 1K blocks.";
    }
    leaf used {
      type uint64;
      description
        "The number of 1K blocks being used.";
    }
    leaf usage {
      type string;
      description
        "The percetage of storage capactiy being used.";
    }
  }

  grouping live_ncs_utilization {
    leaf name {
      type string;
      description
        "The name of the virtual service.";
    }
    container cpu-util {
      description
        "Details on the CPU utilization for the virtual-service.";
      uses virtual-service-ios-xe-oper:live_ncs_cpu-util;
    }
    container memory-util {
      description
        "Details on the memory usage for the virtual-service.";
      uses virtual-service-ios-xe-oper:live_ncs_memory-util;
    }
  }

  grouping live_ncs_virtual-service {
    leaf name {
      type string;
      description
        "The name of the virtual service.";
    }
    container details {
      description
        "Details of the virtual service.";
      uses virtual-service-ios-xe-oper:live_ncs_details;
    }
    container utilization {
      description
        "Utilization of device resources for a virtual-service.";
      uses virtual-service-ios-xe-oper:live_ncs_utilization;
    }
    container network-utils {
      description
        "list of the network utilizations for the virtual-service.";
      list network-util {
        key "name alias";
        description
          "Details on a network utilization for the virtual-service.";
        uses virtual-service-ios-xe-oper:live_ncs_network-util;
      }
    }
    container storage-utils {
      description
        "List of the storage utilizations for the virtual-service.";
      list storage-util {
        key "name alias";
        description
          "Details on a storage utilization for the virtual-service.";
        uses virtual-service-ios-xe-oper:live_ncs_storage-util;
      }
    }
    container attached-devices {
      description
        "Details for the devices attached to this virtual service.";
      list attached-device {
        key "name";
        description
          "List of attached devices.";
        uses virtual-service-ios-xe-oper:live_ncs_attached-device;
      }
    }
    container network-interfaces {
      description
        "Details for the network interfaces.";
      list network-interface {
        key "mac-address";
        description
          "Details for a network interface.";
        uses virtual-service-ios-xe-oper:live_ncs_network-interface;
      }
    }
    container guest-routes {
      description
        "Routes for the guest interface.";
      list guest-route {
        key "route";
        description
          "List of guest routes for a guest interface.";
        uses virtual-service-ios-xe-oper:live_ncs_guest-route;
      }
    }
  }

  grouping application {
    leaf name {
      type string;
      description
        "Name of the application.";
    }
    leaf installed-version {
      type string;
      description
        "Version of the application.";
    }
    leaf description {
      type string;
      description
        "Description of the application.";
    }
  }

  grouping signing {
    leaf key-type {
      type string;
      description
        "The Type of the signed key.";
    }
    leaf method {
      type string;
      description
        "The method the key was signed.";
    }
  }

  grouping licensing {
    leaf name {
      type string;
      description
        "The name of the license.";
    }
    leaf version {
      type string;
      description
        "The version of the license.";
    }
  }

  grouping package-information {
    leaf name {
      type string;
      description
        "Name of the package for the virtual-service.";
    }
    leaf path {
      type string;
      description
        "Path to the package.";
    }
    container application {
      description
        "Details of the application.";
      uses virtual-service-ios-xe-oper:application;
    }
    container signing {
      description
        "Details of the key signing.";
      uses virtual-service-ios-xe-oper:signing;
    }
    container licensing {
      description
        "Details about the license.";
      uses virtual-service-ios-xe-oper:licensing;
    }
  }

  grouping vs-process {
    leaf name {
      type string;
      description
        "Name of the proccess.";
    }
    leaf status {
      type string;
      description
        "Status of the proccess.";
    }
    leaf pid {
      type string;
      description
        "Process ID.";
    }
    leaf uptime {
      type string;
      description
        "Up time of the proccess.";
    }
    leaf memory {
      type string;
      description
        "Memory of the proccess.";
    }
  }

  grouping detailed-guest-status {
    container processes {
      description
        "All the processes.";
      uses virtual-service-ios-xe-oper:vs-process;
    }
  }

  grouping resource-reservation {
    leaf disk {
      type uint64;
      description
        "The amount of reserverd disk space in MB.";
    }
    leaf memory {
      type uint64;
      description
        "The amount of reserved memory in MB.";
    }
    leaf cpu {
      type uint64;
      description
        "The percentage of reserved cpu.";
    }
  }

  grouping attached-device {
    leaf name {
      type string;
      description
        "The name of the attached device.";
    }
    leaf type {
      type string;
      description
        "The type of the attached device.";
    }
    leaf alias {
      type string;
      description
        "The alias for the attached device.";
    }
  }

  grouping network-interface {
    leaf mac-address {
      type yang:mac-address;
      description
        "The MAC address for the network interface.";
    }
    leaf attached-interface {
      type string;
      description
        "Name of the the attached interface";
    }
  }

  grouping guest-route {
    leaf route {
      type string;
      description
        "A guest route for a guest interface.";
    }
  }

  grouping resource-admission {
    leaf state {
      type string;
      description
        "Thes status the of the resource allocation.";
    }
    leaf disk-space {
      type string;
      description
        "The amount of disk space being allocated for the virtual-service.";
    }
    leaf memory {
      type string;
      description
        "The amount of memory being allocated for the virtual-service.";
    }
    leaf cpu {
      type uint64;
      description
        "The percentage of cpu being allocated for the virtual-service";
    }
    leaf vcpus {
      type string;
      description
        "The amount of VCPUs being allocated for the virtual-service.";
    }
  }

  grouping details {
    leaf state {
      type string;
      description
        "State of the virtual service.";
    }
    container package-information {
      description
        "Details of the package for the virtual-service.";
      uses virtual-service-ios-xe-oper:package-information;
    }
    container detailed-guest-status {
      description
        "Details on the guest status.";
      uses virtual-service-ios-xe-oper:detailed-guest-status;
    }
    leaf activated-profile-name {
      type string;
      description
        "The activated profile name.";
    }
    container resource-reservation {
      description
        "Details of the resources reserved for this virtual service.";
      uses virtual-service-ios-xe-oper:resource-reservation;
    }
    leaf guest-interface {
      type string;
      description
        "The name of a guest interface.";
    }
    container resource-admission {
      description
        "Resources being allocated for the virtual-service.";
      uses virtual-service-ios-xe-oper:resource-admission;
    }
  }

  grouping cpu-util {
    leaf requested-application-util {
      type uint64;
      description
        "Percentage of requested CPU utilization by the virtual-service.";
    }
    leaf actual-application-util {
      type uint64;
      description
        "Percetnage of CPU actual utilization for the virtual-service.";
    }
    leaf cpu-state {
      type string;
      description
        "The state of the CPU utilization for the virtual-service.";
    }
  }

  grouping memory-util {
    leaf memory-allocation {
      type string;
      description
        "Amount of memory being allocated for the virtual-service in KB.";
    }
    leaf memory-used {
      type string;
      description
        "Amount of memory being used for the virtual-service in KB.";
    }
  }

  grouping network-util {
    leaf name {
      type string;
      description
        "The name of the network that is being used for the virtual-service.";
    }
    leaf alias {
      type string;
      description
        "The alias of the network that is being used for the virtual-service.";
    }
    leaf rx-packets {
      type uint64;
      description
        "The number of rx packets being utilized for the virtual-service.";
    }
    leaf rx-bytes {
      type uint64;
      description
        "The number of rx bytes being utilized for the virtual-service.";
    }
    leaf rx-errors {
      type uint64;
      description
        "The number of rx errors.";
    }
    leaf tx-packets {
      type uint64;
      description
        "The number of tx packets being utilized for the virtual-service.";
    }
    leaf tx-bytes {
      type uint64;
      description
        "The number of tx bytes being utilized for the virtual-service.";
    }
    leaf tx-errors {
      type uint64;
      description
        "The number of tx errors.";
    }
  }

  grouping storage-util {
    leaf name {
      type string;
      description
        "The name of the storage process being used for the virtual-service.";
    }
    leaf alias {
      type string;
      description
        "The alias of the storage process being used for the virtual-service.";
    }
    leaf rd-bytes {
      type uint64;
      description
        "The number of RD bytes being used for the virtual-service.";
    }
    leaf rd-requests {
      type uint64;
      description
        "The number of rd requests being used for the virtual-service.";
    }
    leaf errors {
      type uint64;
      description
        "The name of errors on the storage process.";
    }
    leaf wr-bytes {
      type uint64;
      description
        "The number of WR bytes for the virtual-service.";
    }
    leaf wr-requests {
      type uint64;
      description
        "The number of WR requests for the virtual-service.";
    }
    leaf capacity {
      type uint64;
      description
        "The storage capactity in 1K blocks.";
    }
    leaf available {
      type string;
      description
        "The available storage in 1K blocks.";
    }
    leaf used {
      type uint64;
      description
        "The number of 1K blocks being used.";
    }
    leaf usage {
      type string;
      description
        "The percetage of storage capactiy being used.";
    }
  }

  grouping utilization {
    leaf name {
      type string;
      description
        "The name of the virtual service.";
    }
    container cpu-util {
      description
        "Details on the CPU utilization for the virtual-service.";
      uses virtual-service-ios-xe-oper:cpu-util;
    }
    container memory-util {
      description
        "Details on the memory usage for the virtual-service.";
      uses virtual-service-ios-xe-oper:memory-util;
    }
  }

  grouping virtual-service {
    leaf name {
      type string;
      description
        "The name of the virtual service.";
    }
    container details {
      description
        "Details of the virtual service.";
      uses virtual-service-ios-xe-oper:details;
    }
    container utilization {
      description
        "Utilization of device resources for a virtual-service.";
      uses virtual-service-ios-xe-oper:utilization;
    }
    container network-utils {
      description
        "list of the network utilizations for the virtual-service.";
      list network-util {
        key "name alias";
        description
          "Details on a network utilization for the virtual-service.";
        uses virtual-service-ios-xe-oper:network-util;
      }
    }
    container storage-utils {
      description
        "List of the storage utilizations for the virtual-service.";
      list storage-util {
        key "name alias";
        description
          "Details on a storage utilization for the virtual-service.";
        uses virtual-service-ios-xe-oper:storage-util;
      }
    }
    container attached-devices {
      description
        "Details for the devices attached to this virtual service.";
      list attached-device {
        key "name";
        description
          "List of attached devices.";
        uses virtual-service-ios-xe-oper:attached-device;
      }
    }
    container network-interfaces {
      description
        "Details for the network interfaces.";
      list network-interface {
        key "mac-address";
        description
          "Details for a network interface.";
        uses virtual-service-ios-xe-oper:network-interface;
      }
    }
    container guest-routes {
      description
        "Routes for the guest interface.";
      list guest-route {
        key "route";
        description
          "List of guest routes for a guest interface.";
        uses virtual-service-ios-xe-oper:guest-route;
      }
    }
  }

  augment "/ncs:devices/ncs:device/ncs:config" {
    // NCS drop config false container 'virtual-services'
  }
  augment "/ncs:devices/ncs:device/ncs:live-status" {
    container virtual-services {
      tailf:ncs-device-type "netconf";
      tailf:display-when "not(../../ncs:module) or ../../ncs:module[ncs:name='Cisco-IOS-XE-virtual-service-oper'] or (../../ncs:live-status-protocol[not(ncs:capability)]) or (../../ncs:live-status-protocol/ncs:capability/ncs:module[.='Cisco-IOS-XE-virtual-service-oper'])";
      description
        "Names and Status of virtual services on the device";
      list virtual-service {
        key "name";
        description
          "A virtual service.";
        uses virtual-service-ios-xe-oper:live_ncs_virtual-service;
      }
    }
  }
  augment "/ncs:devices/ncs:template/ncs:config" {
    // NCS drop config false container 'virtual-services'
  }
}
