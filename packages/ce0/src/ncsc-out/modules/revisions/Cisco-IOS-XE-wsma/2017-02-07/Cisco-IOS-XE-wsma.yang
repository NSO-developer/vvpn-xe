module Cisco-IOS-XE-wsma {
  // Generated by yanger -t ncs
  tailf:ncs-device-type "netconf";

  namespace "http://cisco.com/ns/yang/Cisco-IOS-XE-wsma";
  prefix ios-wsma;

  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Web Services Management Agent (WSMA) Yang model.
     Copyright (c) 2016 by Cisco Systems, Inc.
     All rights reserved.";

  revision 2017-02-07 {
    description
      "Initial revision";
  }

  grouping ncs_template_config-wsma-grouping {
    container agent {
      description
        "Configure WSMA agents";
      container exec {
        description
          "Start WSMA exec agent";
        leaf-list profile {
          // NCS patched for predictable order
          ordered-by user;
          type string;
        }
      }
      container config {
        description
          "Start WSMA config agent";
        leaf-list profile {
          // NCS patched for predictable order
          ordered-by user;
          type string;
        }
      }
      container filesys {
        description
          "Start WSMA file system agent";
        leaf-list profile {
          // NCS patched for predictable order
          ordered-by user;
          type string;
        }
      }
      container notify {
        description
          "Start WSMA notify agent";
        leaf-list profile {
          // NCS patched for predictable order
          ordered-by user;
          type string;
        }
      }
    }
    container profile {
      description
        "Configure WSMA profile";
      list listener {
        // NCS patched for predictable order
        ordered-by user;
        description
          "Configure a listener profile";
        key "name";
        leaf name {
          type string;
        }
        leaf transport {
          description
            "The transport to use";
          type string;
        }
      }
    }
  }

  grouping ncs_rpc_notif_config-wsma-grouping {
    container agent {
      description
        "Configure WSMA agents";
      container exec {
        description
          "Start WSMA exec agent";
        leaf-list profile {
          type string;
        }
      }
      container config {
        description
          "Start WSMA config agent";
        leaf-list profile {
          type string;
        }
      }
      container filesys {
        description
          "Start WSMA file system agent";
        leaf-list profile {
          type string;
        }
      }
      container notify {
        description
          "Start WSMA notify agent";
        leaf-list profile {
          type string;
        }
      }
    }
    container profile {
      description
        "Configure WSMA profile";
      list listener {
        description
          "Configure a listener profile";
        key "name";
        leaf name {
          type string;
        }
        leaf transport {
          description
            "The transport to use";
          type enumeration {
            enum "http";
            enum "https";
            enum "ssh";
            enum "tls";
          }
        }
      }
    }
  }

  grouping live_ncs_config-wsma-grouping {
    container agent {
      description
        "Configure WSMA agents";
      container exec {
        description
          "Start WSMA exec agent";
        leaf-list profile {
          type string;
        }
      }
      container config {
        description
          "Start WSMA config agent";
        leaf-list profile {
          type string;
        }
      }
      container filesys {
        description
          "Start WSMA file system agent";
        leaf-list profile {
          type string;
        }
      }
      container notify {
        description
          "Start WSMA notify agent";
        leaf-list profile {
          type string;
        }
      }
    }
    container profile {
      description
        "Configure WSMA profile";
      list listener {
        description
          "Configure a listener profile";
        key "name";
        leaf name {
          type string;
        }
        leaf transport {
          description
            "The transport to use";
          type enumeration {
            enum "http";
            enum "https";
            enum "ssh";
            enum "tls";
          }
        }
      }
    }
  }

  grouping config-wsma-grouping {
    container agent {
      description
        "Configure WSMA agents";
      container exec {
        description
          "Start WSMA exec agent";
        leaf-list profile {
          type string;
        }
      }
      container config {
        description
          "Start WSMA config agent";
        leaf-list profile {
          type string;
        }
      }
      container filesys {
        description
          "Start WSMA file system agent";
        leaf-list profile {
          type string;
        }
      }
      container notify {
        description
          "Start WSMA notify agent";
        leaf-list profile {
          type string;
        }
      }
    }
    container profile {
      description
        "Configure WSMA profile";
      list listener {
        description
          "Configure a listener profile";
        key "name";
        leaf name {
          type string;
        }
        leaf transport {
          description
            "The transport to use";
          type enumeration {
            enum "http";
            enum "https";
            enum "ssh";
            enum "tls";
          }
        }
      }
    }
  }

  augment "/ncs:devices/ncs:template/ncs:config/ios:native/ios:wsma" {
    uses ncs_template_config-wsma-grouping;
  }
  augment "/ncs:devices/ncs:device/ncs:live-status/ios:native/ios:wsma" {
    uses live_ncs_config-wsma-grouping {
      refine profile {
        tailf:ncs-device-type "netconf";
        tailf:display-when "not(../../../../ncs:module) or ../../../../ncs:module[ncs:name='Cisco-IOS-XE-wsma'] or (../../../../ncs:live-status-protocol[not(ncs:capability)]) or (../../../../ncs:live-status-protocol/ncs:capability/ncs:module[.='Cisco-IOS-XE-wsma'])";
      }
      refine agent {
        tailf:ncs-device-type "netconf";
        tailf:display-when "not(../../../../ncs:module) or ../../../../ncs:module[ncs:name='Cisco-IOS-XE-wsma'] or (../../../../ncs:live-status-protocol[not(ncs:capability)]) or (../../../../ncs:live-status-protocol/ncs:capability/ncs:module[.='Cisco-IOS-XE-wsma'])";
      }
    }
  }
  augment "/ncs:devices/ncs:device/ncs:config/ios:native/ios:wsma" {
    uses config-wsma-grouping {
      refine profile {
        tailf:ncs-device-type "netconf";
        tailf:display-when "not(../../../../ncs:module) or ../../../../ncs:module[ncs:name='Cisco-IOS-XE-wsma']";
      }
      refine agent {
        tailf:ncs-device-type "netconf";
        tailf:display-when "not(../../../../ncs:module) or ../../../../ncs:module[ncs:name='Cisco-IOS-XE-wsma']";
      }
    }
  }
}
