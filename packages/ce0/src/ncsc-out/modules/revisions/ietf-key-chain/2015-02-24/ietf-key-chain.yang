module ietf-key-chain {
  // Generated by yanger -t ncs
  tailf:ncs-device-type "netconf";

  namespace "urn:ietf:params:xml:ns:yang:ietf-key-chain";
  prefix key-chain;

  import ietf-yang-types {
    prefix yang;
  }
  import tailf-ncs {
    prefix ncs;
  }
  import tailf-common {
    prefix tailf;
  }

  organization
    "Cisco Systems
     170 West Tasman Drive
     San Jose, CA 95134-1706
     USA";
  contact
    "Acee Lindem - acee@cisco.com";
  description
    "This YANG module defines the generic configuration
     data for key-chain. It is intended that the module
     will be extended by vendors to define vendor-specific
     key-chain configuration parameters.
    ";

  revision 2015-02-24 {
    description
      "Initial revision.";
    reference "RFC XXXX: A YANG Data Model for key-chain";
  }

  typedef key-chain-ref {
    type leafref {
      path "/ncs:devices/ncs:device/ncs:config/key-chain:key-chains/key-chain:name" {
        tailf:xpath-root 3;
      }
    }
    description
      "This type is used by data models that need to reference
       configured key-chains.";
  }

  grouping ncs_template_lifetime {
    description
      "Key lifetime specification.";
    choice lifetime {
      // NCS drop default statement
      description
        "Options for specifying key accept or send lifetimes";
      case always {
        leaf always {
          type empty;
          description
            "Indicates key lifetime is always valid.";
        }
      }
      case start-end-time {
        leaf start-date-time {
          type string;
          description
            "Start time.";
        }
        choice end-time {
          // NCS drop default statement
          description
            "End-time setting.";
          case infinite {
            leaf no-end-time {
              type empty;
              description
                "Indicates key lifetime end-time in infinite.";
            }
          }
          case duration {
            leaf duration {
              type string;
              units "seconds";
              description
                "Key lifetime duration, in seconds";
            }
          }
          case end-date-time {
            leaf end-date-time {
              type string;
              description
                "End time.";
            }
          }
        }
      }
    }
  }

  grouping ncs_template_crypto-algorithm-types {
    description
      "Cryptographic algorithm types.";
    choice algorithm {
      description
        "Options for crytographic algorithm specification.";
      case hmac-sha1-12 {
        leaf hmac-sha1-12 {
          type empty;
          description
            "The HMAC-SHA1-12 algorithm.";
        }
      }
      case hmac-sha1-20 {
        leaf hmac-sha1-20 {
          type empty;
          description
            "The HMAC-SHA1-20 algorithm.";
        }
      }
      case md5 {
        leaf md5 {
          type empty;
          description
            "The MD5 algorithm.";
        }
      }
      case sha-1 {
        leaf sha-1 {
          type empty;
          description
            "The SHA-1 algorithm.";
        }
      }
      case hmac-sha-1 {
        leaf hmac-sha-1 {
          type empty;
          description
            "HMAC-SHA-1 authentication algorithm.";
        }
      }
      case hmac-sha-256 {
        leaf hmac-sha-256 {
          type empty;
          description
            "HMAC-SHA-256 authentication algorithm.";
        }
      }
      case hmac-sha-384 {
        leaf hmac-sha-384 {
          type empty;
          description
            "HMAC-SHA-384 authentication algorithm.";
        }
      }
      case hmac-sha-512 {
        leaf hmac-sha-512 {
          type empty;
          description
            "HMAC-SHA-512 authentication algorithm.";
        }
      }
    }
  }

  grouping ncs_template_key-chain {
    description
      "key-chain specification grouping.";
    leaf name {
      type string;
      description
        "Name of the key-chain.";
    }
    container accept-tolerance {
      // NCS drop if-feature statement
      description
        "Tolerance for key lifetime acceptance (seconds).";
      leaf duration {
        type string;
        units "seconds";
        // NCS drop default statement
        description
          "Tolerance range, in seconds.";
      }
    }
    list key {
      // NCS patched for predictable order
      ordered-by user;
      key "key-id";
      description
        "One key.";
      leaf key-id {
        type string;
        description
          "Key id.";
      }
      container key-string {
        description
          "The key string.";
        choice key-string-style {
          description
            "Key string styles";
          case keystring {
            leaf keystring {
              type string;
              description
                "Key string in ASCII format.";
            }
          }
          case hexadecimal {
            // NCS drop if-feature statement
            leaf hexadecimal-string {
              type string;
              description
                "Key in hexadecimal string format.";
            }
          }
        }
      }
      container lifetime {
        description
          "Specify a key's lifetime.";
        choice lifetime {
          description
            "Options for specification of send and accept
             lifetimes.";
          case send-and-accept-lifetime {
            description
              "Send and accept key have the same lifetime.";
            container send-accept-lifetime {
              uses ncs_template_lifetime;
              description
                "Single lifetime specification for both send and
                 accept lifetimes.";
            }
          }
          case independent-send-accept-lifetime {
            // NCS drop if-feature statement
            description
              "Independent send and accept key lifetimes.";
            container send-lifetime {
              uses ncs_template_lifetime;
              description
                "Separate lifetime specification for send
                 lifetime.";
            }
            container accept-lifetime {
              uses ncs_template_lifetime;
              description
                "Separate lifetime specification for accept
                 lifetime.";
            }
          }
        }
      }
      container crypto-algorithm {
        uses ncs_template_crypto-algorithm-types;
        description
          "Cryptographic algorithm associated with key.";
      }
    }
  }

  grouping ncs_rpc_notif_lifetime {
    description
      "Key lifetime specification.";
    choice lifetime {
      default "always";
      description
        "Options for specifying key accept or send lifetimes";
      case always {
        leaf always {
          type empty;
          description
            "Indicates key lifetime is always valid.";
        }
      }
      case start-end-time {
        leaf start-date-time {
          type yang:date-and-time;
          description
            "Start time.";
        }
        choice end-time {
          default "infinite";
          description
            "End-time setting.";
          case infinite {
            leaf no-end-time {
              type empty;
              description
                "Indicates key lifetime end-time in infinite.";
            }
          }
          case duration {
            leaf duration {
              type uint32 {
                range "1..2147483646";
              }
              units "seconds";
              description
                "Key lifetime duration, in seconds";
            }
          }
          case end-date-time {
            leaf end-date-time {
              type yang:date-and-time;
              description
                "End time.";
            }
          }
        }
      }
    }
  }

  grouping ncs_rpc_notif_crypto-algorithm-types {
    description
      "Cryptographic algorithm types.";
    choice algorithm {
      description
        "Options for crytographic algorithm specification.";
      case hmac-sha1-12 {
        leaf hmac-sha1-12 {
          type empty;
          description
            "The HMAC-SHA1-12 algorithm.";
        }
      }
      case hmac-sha1-20 {
        leaf hmac-sha1-20 {
          type empty;
          description
            "The HMAC-SHA1-20 algorithm.";
        }
      }
      case md5 {
        leaf md5 {
          type empty;
          description
            "The MD5 algorithm.";
        }
      }
      case sha-1 {
        leaf sha-1 {
          type empty;
          description
            "The SHA-1 algorithm.";
        }
      }
      case hmac-sha-1 {
        leaf hmac-sha-1 {
          type empty;
          description
            "HMAC-SHA-1 authentication algorithm.";
        }
      }
      case hmac-sha-256 {
        leaf hmac-sha-256 {
          type empty;
          description
            "HMAC-SHA-256 authentication algorithm.";
        }
      }
      case hmac-sha-384 {
        leaf hmac-sha-384 {
          type empty;
          description
            "HMAC-SHA-384 authentication algorithm.";
        }
      }
      case hmac-sha-512 {
        leaf hmac-sha-512 {
          type empty;
          description
            "HMAC-SHA-512 authentication algorithm.";
        }
      }
    }
  }

  grouping ncs_rpc_notif_key-chain {
    description
      "key-chain specification grouping.";
    leaf name {
      type string;
      description
        "Name of the key-chain.";
    }
    container accept-tolerance {
      tailf:display-when "not(../ncs:module) or boolean(/ncs:devices/ncs:device[ncs:name=current()/../ncs:name]/capability/feature='accept-tolerance')";
      description
        "Tolerance for key lifetime acceptance (seconds).";
      leaf duration {
        type uint32;
        units "seconds";
        default "0";
        description
          "Tolerance range, in seconds.";
      }
    }
    list key {
      key "key-id";
      description
        "One key.";
      leaf key-id {
        type uint64;
        description
          "Key id.";
      }
      container key-string {
        description
          "The key string.";
        choice key-string-style {
          description
            "Key string styles";
          case keystring {
            leaf keystring {
              type string;
              description
                "Key string in ASCII format.";
            }
          }
          case hexadecimal {
            // NCS drop if-feature statement
            leaf hexadecimal-string {
              type yang:hex-string;
              description
                "Key in hexadecimal string format.";
            }
          }
        }
      }
      container lifetime {
        description
          "Specify a key's lifetime.";
        choice lifetime {
          description
            "Options for specification of send and accept
             lifetimes.";
          case send-and-accept-lifetime {
            description
              "Send and accept key have the same lifetime.";
            container send-accept-lifetime {
              uses ncs_rpc_notif_lifetime;
              description
                "Single lifetime specification for both send and
                 accept lifetimes.";
            }
          }
          case independent-send-accept-lifetime {
            // NCS drop if-feature statement
            description
              "Independent send and accept key lifetimes.";
            container send-lifetime {
              uses ncs_rpc_notif_lifetime;
              description
                "Separate lifetime specification for send
                 lifetime.";
            }
            container accept-lifetime {
              uses ncs_rpc_notif_lifetime;
              description
                "Separate lifetime specification for accept
                 lifetime.";
            }
          }
        }
      }
      container crypto-algorithm {
        uses ncs_rpc_notif_crypto-algorithm-types;
        description
          "Cryptographic algorithm associated with key.";
      }
    }
  }

  grouping live_ncs_lifetime {
    description
      "Key lifetime specification.";
    choice lifetime {
      // NCS drop default statement
      description
        "Options for specifying key accept or send lifetimes";
      case always {
        leaf always {
          type empty;
          description
            "Indicates key lifetime is always valid.";
        }
      }
      case start-end-time {
        leaf start-date-time {
          type yang:date-and-time;
          description
            "Start time.";
        }
        choice end-time {
          // NCS drop default statement
          description
            "End-time setting.";
          case infinite {
            leaf no-end-time {
              type empty;
              description
                "Indicates key lifetime end-time in infinite.";
            }
          }
          case duration {
            leaf duration {
              type uint32 {
                range "1..2147483646";
              }
              units "seconds";
              description
                "Key lifetime duration, in seconds";
            }
          }
          case end-date-time {
            leaf end-date-time {
              type yang:date-and-time;
              description
                "End time.";
            }
          }
        }
      }
    }
  }

  grouping live_ncs_crypto-algorithm-types {
    description
      "Cryptographic algorithm types.";
    choice algorithm {
      description
        "Options for crytographic algorithm specification.";
      case hmac-sha1-12 {
        leaf hmac-sha1-12 {
          type empty;
          description
            "The HMAC-SHA1-12 algorithm.";
        }
      }
      case hmac-sha1-20 {
        leaf hmac-sha1-20 {
          type empty;
          description
            "The HMAC-SHA1-20 algorithm.";
        }
      }
      case md5 {
        leaf md5 {
          type empty;
          description
            "The MD5 algorithm.";
        }
      }
      case sha-1 {
        leaf sha-1 {
          type empty;
          description
            "The SHA-1 algorithm.";
        }
      }
      case hmac-sha-1 {
        leaf hmac-sha-1 {
          type empty;
          description
            "HMAC-SHA-1 authentication algorithm.";
        }
      }
      case hmac-sha-256 {
        leaf hmac-sha-256 {
          type empty;
          description
            "HMAC-SHA-256 authentication algorithm.";
        }
      }
      case hmac-sha-384 {
        leaf hmac-sha-384 {
          type empty;
          description
            "HMAC-SHA-384 authentication algorithm.";
        }
      }
      case hmac-sha-512 {
        leaf hmac-sha-512 {
          type empty;
          description
            "HMAC-SHA-512 authentication algorithm.";
        }
      }
    }
  }

  grouping live_ncs_key-chain {
    description
      "key-chain specification grouping.";
    leaf name {
      type string;
      description
        "Name of the key-chain.";
    }
    container accept-tolerance {
      // NCS drop if-feature statement
      description
        "Tolerance for key lifetime acceptance (seconds).";
      leaf duration {
        type uint32;
        units "seconds";
        // NCS drop default statement
        description
          "Tolerance range, in seconds.";
      }
    }
    list key {
      key "key-id";
      description
        "One key.";
      leaf key-id {
        type uint64;
        description
          "Key id.";
      }
      container key-string {
        description
          "The key string.";
        choice key-string-style {
          description
            "Key string styles";
          case keystring {
            leaf keystring {
              type string;
              description
                "Key string in ASCII format.";
            }
          }
          case hexadecimal {
            // NCS drop if-feature statement
            leaf hexadecimal-string {
              type yang:hex-string;
              description
                "Key in hexadecimal string format.";
            }
          }
        }
      }
      container lifetime {
        description
          "Specify a key's lifetime.";
        choice lifetime {
          description
            "Options for specification of send and accept
             lifetimes.";
          case send-and-accept-lifetime {
            description
              "Send and accept key have the same lifetime.";
            container send-accept-lifetime {
              uses live_ncs_lifetime;
              description
                "Single lifetime specification for both send and
                 accept lifetimes.";
            }
          }
          case independent-send-accept-lifetime {
            // NCS drop if-feature statement
            description
              "Independent send and accept key lifetimes.";
            container send-lifetime {
              uses live_ncs_lifetime;
              description
                "Separate lifetime specification for send
                 lifetime.";
            }
            container accept-lifetime {
              uses live_ncs_lifetime;
              description
                "Separate lifetime specification for accept
                 lifetime.";
            }
          }
        }
      }
      container crypto-algorithm {
        uses live_ncs_crypto-algorithm-types;
        description
          "Cryptographic algorithm associated with key.";
      }
    }
  }

  grouping lifetime {
    description
      "Key lifetime specification.";
    choice lifetime {
      default "always";
      description
        "Options for specifying key accept or send lifetimes";
      case always {
        leaf always {
          type empty;
          description
            "Indicates key lifetime is always valid.";
        }
      }
      case start-end-time {
        leaf start-date-time {
          type yang:date-and-time;
          description
            "Start time.";
        }
        choice end-time {
          default "infinite";
          description
            "End-time setting.";
          case infinite {
            leaf no-end-time {
              type empty;
              description
                "Indicates key lifetime end-time in infinite.";
            }
          }
          case duration {
            leaf duration {
              type uint32 {
                range "1..2147483646";
              }
              units "seconds";
              description
                "Key lifetime duration, in seconds";
            }
          }
          case end-date-time {
            leaf end-date-time {
              type yang:date-and-time;
              description
                "End time.";
            }
          }
        }
      }
    }
  }

  grouping crypto-algorithm-types {
    description
      "Cryptographic algorithm types.";
    choice algorithm {
      description
        "Options for crytographic algorithm specification.";
      case hmac-sha1-12 {
        leaf hmac-sha1-12 {
          type empty;
          description
            "The HMAC-SHA1-12 algorithm.";
        }
      }
      case hmac-sha1-20 {
        leaf hmac-sha1-20 {
          type empty;
          description
            "The HMAC-SHA1-20 algorithm.";
        }
      }
      case md5 {
        leaf md5 {
          type empty;
          description
            "The MD5 algorithm.";
        }
      }
      case sha-1 {
        leaf sha-1 {
          type empty;
          description
            "The SHA-1 algorithm.";
        }
      }
      case hmac-sha-1 {
        leaf hmac-sha-1 {
          type empty;
          description
            "HMAC-SHA-1 authentication algorithm.";
        }
      }
      case hmac-sha-256 {
        leaf hmac-sha-256 {
          type empty;
          description
            "HMAC-SHA-256 authentication algorithm.";
        }
      }
      case hmac-sha-384 {
        leaf hmac-sha-384 {
          type empty;
          description
            "HMAC-SHA-384 authentication algorithm.";
        }
      }
      case hmac-sha-512 {
        leaf hmac-sha-512 {
          type empty;
          description
            "HMAC-SHA-512 authentication algorithm.";
        }
      }
    }
  }

  grouping key-chain {
    description
      "key-chain specification grouping.";
    leaf name {
      type string;
      description
        "Name of the key-chain.";
    }
    container accept-tolerance {
      tailf:display-when "not(../ncs:module) or boolean(/ncs:devices/ncs:device[ncs:name=current()/../ncs:name]/capability/feature='accept-tolerance')";
      description
        "Tolerance for key lifetime acceptance (seconds).";
      leaf duration {
        type uint32;
        units "seconds";
        default "0";
        description
          "Tolerance range, in seconds.";
      }
    }
    list key {
      key "key-id";
      description
        "One key.";
      leaf key-id {
        type uint64;
        description
          "Key id.";
      }
      container key-string {
        description
          "The key string.";
        choice key-string-style {
          description
            "Key string styles";
          case keystring {
            leaf keystring {
              type string;
              description
                "Key string in ASCII format.";
            }
          }
          case hexadecimal {
            // NCS drop if-feature statement
            leaf hexadecimal-string {
              type yang:hex-string;
              description
                "Key in hexadecimal string format.";
            }
          }
        }
      }
      container lifetime {
        description
          "Specify a key's lifetime.";
        choice lifetime {
          description
            "Options for specification of send and accept
             lifetimes.";
          case send-and-accept-lifetime {
            description
              "Send and accept key have the same lifetime.";
            container send-accept-lifetime {
              uses lifetime;
              description
                "Single lifetime specification for both send and
                 accept lifetimes.";
            }
          }
          case independent-send-accept-lifetime {
            // NCS drop if-feature statement
            description
              "Independent send and accept key lifetimes.";
            container send-lifetime {
              uses lifetime;
              description
                "Separate lifetime specification for send
                 lifetime.";
            }
            container accept-lifetime {
              uses lifetime;
              description
                "Separate lifetime specification for accept
                 lifetime.";
            }
          }
        }
      }
      container crypto-algorithm {
        uses crypto-algorithm-types;
        description
          "Cryptographic algorithm associated with key.";
      }
    }
  }

  augment "/ncs:devices/ncs:device/ncs:config" {
    list key-chains {
      tailf:ncs-device-type "netconf";
      tailf:display-when "not(../ncs:module) or ../ncs:module[ncs:name='ietf-key-chain']";
      key "name";
      description
        "A key-chain is a sequence of keys that are collectively
         managed for authentication.";
      uses key-chain;
    }
  }
  augment "/ncs:devices/ncs:device/ncs:live-status" {
    list key-chains {
      tailf:ncs-device-type "netconf";
      tailf:display-when "not(../ncs:module) or ../ncs:module[ncs:name='ietf-key-chain'] or (../ncs:live-status-protocol[not(ncs:capability)]) or (../ncs:live-status-protocol/ncs:capability/ncs:module[.='ietf-key-chain'])";
      key "name";
      description
        "A key-chain is a sequence of keys that are collectively
         managed for authentication.";
      uses live_ncs_key-chain;
    }
  }
  augment "/ncs:devices/ncs:template/ncs:config" {
    list key-chains {
      // NCS patched for predictable order
      ordered-by user;
      key "name";
      description
        "A key-chain is a sequence of keys that are collectively
         managed for authentication.";
      uses ncs_template_key-chain;
    }
  }

  feature independent-send-accept-lifetime {
    description
      "Support for independent send and accept key lifetimes.";
  }

  feature accept-tolerance {
    description
      "To specify the tolerance or acceptance limit.";
  }

  feature hex-key-string {
    description
      "Support hexadecimal key string.";
  }
}
