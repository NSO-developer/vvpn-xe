module Cisco-IOS-XE-bfd {
  // Generated by yanger -t ncs
  tailf:ncs-device-type "netconf";

  namespace "http://cisco.com/ns/yang/Cisco-IOS-XE-bfd";
  prefix ios-bfd;

  import ietf-inet-types {
    prefix inet;
  }
  import Cisco-IOS-XE-native {
    prefix ios;
  }
  import Cisco-IOS-XE-types {
    prefix ios-types;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Bidirectional Forwarding Detection (BFD) Yang Model.
     Copyright (c) 2016-2017 by Cisco Systems, Inc.
     All rights reserved.";

  revision 2017-04-28 {
    description
      "inet:ipv6-prefix changed to ios-types:ipv6-prefix";
  }
  revision 2017-02-07 {
    description
      "Initial revision";
  }

  grouping ncs_template_config-interface-bfd-grouping {
    leaf template {
      description
        "BFD template";
      type string;
    }
    container interval {
      description
        "Transmit interval between BFD packets";
      leaf msecs {
        type string;
      }
      leaf min_rx {
        description
          "Minimum receive interval capability";
        type string;
      }
      leaf multiplier {
        description
          "Multiplier value used to compute holddown";
        type string;
      }
    }
    leaf echo {
      description
        "Use echo adjunct as bfd detection mechanism";
      type string;
    }
  }

  grouping ncs_template_config-bfd-grouping {
    leaf l2cos {
      description
        "Value of L2 COS for BFD Pkts over VLAN interfaces";
      type string;
    }
    container map {
      description
        "configure bfd map entry for multi-hop sessions";
      container ipv4 {
        description
          "IPv4 Address Family";
        container no-vrf {
          leaf dest-ip {
            type string;
          }
          leaf src-ip {
            type string;
          }
          leaf template-name {
            type string;
          }
        }
        container vrf {
          description
            "Destination VRF name";
          list dst-vrf {
            // NCS patched for predictable order
            ordered-by user;
            key "dst-vrf";
            leaf dst-vrf {
              description
                "Destination VRF instance name";
              type string;
            }
            leaf A_PERIOD_B_PERIOD_C_PERIOD_D_SLASH_nn {
              description
                "Destination IP prefix/len";
              type empty;
            }
          }
        }
      }
      container ipv6 {
        description
          "IPv6 Address Family";
        list dp-ipv6_prefix {
          // NCS patched for predictable order
          ordered-by user;
          key "dp-ipv6_prefix";
          leaf dp-ipv6_prefix {
            description
              "Destination IPv6 prefix/len";
            type string;
          }
          leaf bfd-nm {
            description
              "bfd template name";
            type string;
          }
          list src-ipv6_prefix0 {
            // NCS patched for predictable order
            ordered-by user;
            key "src-ipv6_prefix0";
            leaf src-ipv6_prefix0 {
              description
                "Source IPv6 prefix/len";
              type string;
            }
            leaf bfd-name {
              description
                "bfd template name";
              type string;
            }
          }
          container vrf {
            description
              "Source VRF name";
            list src-vrf {
              // NCS patched for predictable order
              ordered-by user;
              key "src-vrf";
              leaf src-vrf {
                description
                  "Source VRF instance name";
                type string;
              }
              leaf src-ipv6_prefix {
                description
                  "Source IPv6 prefix/len";
                type string;
              }
            }
          }
        }
        container vrf {
          description
            "Destination VRF name";
          list dst-vrf {
            // NCS patched for predictable order
            ordered-by user;
            key "dst-vrf";
            leaf dst-vrf {
              description
                "Destination VRF instance name";
              type string;
            }
            leaf dst-ipv6_prefix {
              description
                "Destination IPv6 prefix/len";
              type string;
            }
          }
        }
      }
    }
    leaf slow-timers {
      description
        "Value in ms to use for slow timers";
      type string;
    }
  }

  grouping ncs_template_config-bfd-template-grouping {
    container single-hop {
      description
        "Single-hop template";
      leaf name {
        type string;
      }
      container interval {
        description
          "Transmit interval between BFD packets";
        container microseconds {
          description
            "Specify BFD timers in microseconds";
          leaf min-tx {
            description
              "Minimum transmit interval capability";
            type string;
          }
          leaf min-rx {
            description
              "Minimum receive interval capability";
            type string;
          }
          leaf multiplier {
            description
              "Multiplier value used to compute holddown";
            type string;
          }
        }
      }
    }
  }

  grouping ncs_rpc_notif_config-interface-bfd-grouping {
    leaf template {
      description
        "BFD template";
      type string;
    }
    container interval {
      description
        "Transmit interval between BFD packets";
      leaf msecs {
        type uint16 {
          range "50..9999";
        }
      }
      leaf min_rx {
        description
          "Minimum receive interval capability";
        type uint16 {
          range "50..9999";
        }
      }
      leaf multiplier {
        description
          "Multiplier value used to compute holddown";
        type uint8 {
          range "3..50";
        }
      }
    }
    leaf echo {
      description
        "Use echo adjunct as bfd detection mechanism";
      type boolean;
    }
  }

  grouping ncs_rpc_notif_config-bfd-grouping {
    leaf l2cos {
      description
        "Value of L2 COS for BFD Pkts over VLAN interfaces";
      type uint8 {
        range "0..6";
      }
    }
    container map {
      description
        "configure bfd map entry for multi-hop sessions";
      container ipv4 {
        description
          "IPv4 Address Family";
        container no-vrf {
          leaf dest-ip {
            type inet:ipv4-prefix;
          }
          leaf src-ip {
            type inet:ipv4-prefix;
          }
          leaf template-name {
            type string;
          }
        }
        container vrf {
          description
            "Destination VRF name";
          list dst-vrf {
            key "dst-vrf";
            leaf dst-vrf {
              description
                "Destination VRF instance name";
              type string;
            }
            leaf A_PERIOD_B_PERIOD_C_PERIOD_D_SLASH_nn {
              description
                "Destination IP prefix/len";
              type empty;
            }
          }
        }
      }
      container ipv6 {
        description
          "IPv6 Address Family";
        list dp-ipv6_prefix {
          key "dp-ipv6_prefix";
          leaf dp-ipv6_prefix {
            description
              "Destination IPv6 prefix/len";
            type ios-types:ipv6-prefix;
          }
          leaf bfd-nm {
            description
              "bfd template name";
            type string;
          }
          list src-ipv6_prefix0 {
            key "src-ipv6_prefix0";
            leaf src-ipv6_prefix0 {
              description
                "Source IPv6 prefix/len";
              type ios-types:ipv6-prefix;
            }
            leaf bfd-name {
              description
                "bfd template name";
              type string;
            }
          }
          container vrf {
            description
              "Source VRF name";
            list src-vrf {
              key "src-vrf";
              leaf src-vrf {
                description
                  "Source VRF instance name";
                type string;
              }
              leaf src-ipv6_prefix {
                description
                  "Source IPv6 prefix/len";
                type ios-types:ipv6-prefix;
              }
            }
          }
        }
        container vrf {
          description
            "Destination VRF name";
          list dst-vrf {
            key "dst-vrf";
            leaf dst-vrf {
              description
                "Destination VRF instance name";
              type string;
            }
            leaf dst-ipv6_prefix {
              description
                "Destination IPv6 prefix/len";
              type ios-types:ipv6-prefix;
            }
          }
        }
      }
    }
    leaf slow-timers {
      description
        "Value in ms to use for slow timers";
      type uint16 {
        range "1000..30000";
      }
    }
  }

  grouping ncs_rpc_notif_config-bfd-template-grouping {
    container single-hop {
      description
        "Single-hop template";
      leaf name {
        type string;
      }
      container interval {
        description
          "Transmit interval between BFD packets";
        container microseconds {
          description
            "Specify BFD timers in microseconds";
          leaf min-tx {
            description
              "Minimum transmit interval capability";
            type uint32 {
              range "3300..999000";
            }
          }
          leaf min-rx {
            description
              "Minimum receive interval capability";
            type uint32 {
              range "3300..999000";
            }
          }
          leaf multiplier {
            description
              "Multiplier value used to compute holddown";
            type uint8 {
              range "3..50";
            }
          }
        }
      }
    }
  }

  grouping live_ncs_config-interface-bfd-grouping {
    leaf template {
      description
        "BFD template";
      type string;
    }
    container interval {
      description
        "Transmit interval between BFD packets";
      leaf msecs {
        type uint16 {
          range "50..9999";
        }
      }
      leaf min_rx {
        description
          "Minimum receive interval capability";
        type uint16 {
          range "50..9999";
        }
      }
      leaf multiplier {
        description
          "Multiplier value used to compute holddown";
        type uint8 {
          range "3..50";
        }
      }
    }
    leaf echo {
      description
        "Use echo adjunct as bfd detection mechanism";
      type boolean;
    }
  }

  grouping live_ncs_config-bfd-grouping {
    leaf l2cos {
      description
        "Value of L2 COS for BFD Pkts over VLAN interfaces";
      type uint8 {
        range "0..6";
      }
    }
    container map {
      description
        "configure bfd map entry for multi-hop sessions";
      container ipv4 {
        description
          "IPv4 Address Family";
        container no-vrf {
          leaf dest-ip {
            type inet:ipv4-prefix;
          }
          leaf src-ip {
            type inet:ipv4-prefix;
          }
          leaf template-name {
            type string;
          }
        }
        container vrf {
          description
            "Destination VRF name";
          list dst-vrf {
            key "dst-vrf";
            leaf dst-vrf {
              description
                "Destination VRF instance name";
              type string;
            }
            leaf A_PERIOD_B_PERIOD_C_PERIOD_D_SLASH_nn {
              description
                "Destination IP prefix/len";
              type empty;
            }
          }
        }
      }
      container ipv6 {
        description
          "IPv6 Address Family";
        list dp-ipv6_prefix {
          key "dp-ipv6_prefix";
          leaf dp-ipv6_prefix {
            description
              "Destination IPv6 prefix/len";
            type ios-types:ipv6-prefix;
          }
          leaf bfd-nm {
            description
              "bfd template name";
            type string;
          }
          list src-ipv6_prefix0 {
            key "src-ipv6_prefix0";
            leaf src-ipv6_prefix0 {
              description
                "Source IPv6 prefix/len";
              type ios-types:ipv6-prefix;
            }
            leaf bfd-name {
              description
                "bfd template name";
              type string;
            }
          }
          container vrf {
            description
              "Source VRF name";
            list src-vrf {
              key "src-vrf";
              leaf src-vrf {
                description
                  "Source VRF instance name";
                type string;
              }
              leaf src-ipv6_prefix {
                description
                  "Source IPv6 prefix/len";
                type ios-types:ipv6-prefix;
              }
            }
          }
        }
        container vrf {
          description
            "Destination VRF name";
          list dst-vrf {
            key "dst-vrf";
            leaf dst-vrf {
              description
                "Destination VRF instance name";
              type string;
            }
            leaf dst-ipv6_prefix {
              description
                "Destination IPv6 prefix/len";
              type ios-types:ipv6-prefix;
            }
          }
        }
      }
    }
    leaf slow-timers {
      description
        "Value in ms to use for slow timers";
      type uint16 {
        range "1000..30000";
      }
    }
  }

  grouping live_ncs_config-bfd-template-grouping {
    container single-hop {
      description
        "Single-hop template";
      leaf name {
        type string;
      }
      container interval {
        description
          "Transmit interval between BFD packets";
        container microseconds {
          description
            "Specify BFD timers in microseconds";
          leaf min-tx {
            description
              "Minimum transmit interval capability";
            type uint32 {
              range "3300..999000";
            }
          }
          leaf min-rx {
            description
              "Minimum receive interval capability";
            type uint32 {
              range "3300..999000";
            }
          }
          leaf multiplier {
            description
              "Multiplier value used to compute holddown";
            type uint8 {
              range "3..50";
            }
          }
        }
      }
    }
  }

  grouping config-interface-bfd-grouping {
    leaf template {
      description
        "BFD template";
      type string;
    }
    container interval {
      description
        "Transmit interval between BFD packets";
      leaf msecs {
        type uint16 {
          range "50..9999";
        }
      }
      leaf min_rx {
        description
          "Minimum receive interval capability";
        type uint16 {
          range "50..9999";
        }
      }
      leaf multiplier {
        description
          "Multiplier value used to compute holddown";
        type uint8 {
          range "3..50";
        }
      }
    }
    leaf echo {
      description
        "Use echo adjunct as bfd detection mechanism";
      type boolean;
    }
  }

  grouping config-bfd-grouping {
    leaf l2cos {
      description
        "Value of L2 COS for BFD Pkts over VLAN interfaces";
      type uint8 {
        range "0..6";
      }
    }
    container map {
      description
        "configure bfd map entry for multi-hop sessions";
      container ipv4 {
        description
          "IPv4 Address Family";
        container no-vrf {
          leaf dest-ip {
            type inet:ipv4-prefix;
          }
          leaf src-ip {
            type inet:ipv4-prefix;
          }
          leaf template-name {
            type string;
          }
        }
        container vrf {
          description
            "Destination VRF name";
          list dst-vrf {
            key "dst-vrf";
            leaf dst-vrf {
              description
                "Destination VRF instance name";
              type string;
            }
            leaf A_PERIOD_B_PERIOD_C_PERIOD_D_SLASH_nn {
              description
                "Destination IP prefix/len";
              type empty;
            }
          }
        }
      }
      container ipv6 {
        description
          "IPv6 Address Family";
        list dp-ipv6_prefix {
          key "dp-ipv6_prefix";
          leaf dp-ipv6_prefix {
            description
              "Destination IPv6 prefix/len";
            type ios-types:ipv6-prefix;
          }
          leaf bfd-nm {
            description
              "bfd template name";
            type string;
          }
          list src-ipv6_prefix0 {
            key "src-ipv6_prefix0";
            leaf src-ipv6_prefix0 {
              description
                "Source IPv6 prefix/len";
              type ios-types:ipv6-prefix;
            }
            leaf bfd-name {
              description
                "bfd template name";
              type string;
            }
          }
          container vrf {
            description
              "Source VRF name";
            list src-vrf {
              key "src-vrf";
              leaf src-vrf {
                description
                  "Source VRF instance name";
                type string;
              }
              leaf src-ipv6_prefix {
                description
                  "Source IPv6 prefix/len";
                type ios-types:ipv6-prefix;
              }
            }
          }
        }
        container vrf {
          description
            "Destination VRF name";
          list dst-vrf {
            key "dst-vrf";
            leaf dst-vrf {
              description
                "Destination VRF instance name";
              type string;
            }
            leaf dst-ipv6_prefix {
              description
                "Destination IPv6 prefix/len";
              type ios-types:ipv6-prefix;
            }
          }
        }
      }
    }
    leaf slow-timers {
      description
        "Value in ms to use for slow timers";
      type uint16 {
        range "1000..30000";
      }
    }
  }

  grouping config-bfd-template-grouping {
    container single-hop {
      description
        "Single-hop template";
      leaf name {
        type string;
      }
      container interval {
        description
          "Transmit interval between BFD packets";
        container microseconds {
          description
            "Specify BFD timers in microseconds";
          leaf min-tx {
            description
              "Minimum transmit interval capability";
            type uint32 {
              range "3300..999000";
            }
          }
          leaf min-rx {
            description
              "Minimum receive interval capability";
            type uint32 {
              range "3300..999000";
            }
          }
          leaf multiplier {
            description
              "Multiplier value used to compute holddown";
            type uint8 {
              range "3..50";
            }
          }
        }
      }
    }
  }

  augment "/ncs:devices/ncs:template/ncs:config/ios:native/ios:bfd" {
    uses ncs_template_config-bfd-grouping;
  }
  augment "/ncs:devices/ncs:device/ncs:live-status/ios:native/ios:bfd" {
    uses live_ncs_config-bfd-grouping {
      refine slow-timers {
        tailf:ncs-device-type "netconf";
        tailf:display-when "not(../../../../ncs:module) or ../../../../ncs:module[ncs:name='Cisco-IOS-XE-bfd'] or (../../../../ncs:live-status-protocol[not(ncs:capability)]) or (../../../../ncs:live-status-protocol/ncs:capability/ncs:module[.='Cisco-IOS-XE-bfd'])";
      }
      refine map {
        tailf:ncs-device-type "netconf";
        tailf:display-when "not(../../../../ncs:module) or ../../../../ncs:module[ncs:name='Cisco-IOS-XE-bfd'] or (../../../../ncs:live-status-protocol[not(ncs:capability)]) or (../../../../ncs:live-status-protocol/ncs:capability/ncs:module[.='Cisco-IOS-XE-bfd'])";
      }
      refine l2cos {
        tailf:ncs-device-type "netconf";
        tailf:display-when "not(../../../../ncs:module) or ../../../../ncs:module[ncs:name='Cisco-IOS-XE-bfd'] or (../../../../ncs:live-status-protocol[not(ncs:capability)]) or (../../../../ncs:live-status-protocol/ncs:capability/ncs:module[.='Cisco-IOS-XE-bfd'])";
      }
    }
  }
  augment "/ncs:devices/ncs:device/ncs:config/ios:native/ios:bfd" {
    uses config-bfd-grouping {
      refine slow-timers {
        tailf:ncs-device-type "netconf";
        tailf:display-when "not(../../../../ncs:module) or ../../../../ncs:module[ncs:name='Cisco-IOS-XE-bfd']";
      }
      refine map {
        tailf:ncs-device-type "netconf";
        tailf:display-when "not(../../../../ncs:module) or ../../../../ncs:module[ncs:name='Cisco-IOS-XE-bfd']";
      }
      refine l2cos {
        tailf:ncs-device-type "netconf";
        tailf:display-when "not(../../../../ncs:module) or ../../../../ncs:module[ncs:name='Cisco-IOS-XE-bfd']";
      }
    }
  }
  augment "/ncs:devices/ncs:template/ncs:config/ios:native/ios:bfd-template" {
    uses ncs_template_config-bfd-template-grouping;
  }
  augment "/ncs:devices/ncs:device/ncs:live-status/ios:native/ios:bfd-template" {
    uses live_ncs_config-bfd-template-grouping {
      refine single-hop {
        tailf:ncs-device-type "netconf";
        tailf:display-when "not(../../../../ncs:module) or ../../../../ncs:module[ncs:name='Cisco-IOS-XE-bfd'] or (../../../../ncs:live-status-protocol[not(ncs:capability)]) or (../../../../ncs:live-status-protocol/ncs:capability/ncs:module[.='Cisco-IOS-XE-bfd'])";
      }
    }
  }
  augment "/ncs:devices/ncs:device/ncs:config/ios:native/ios:bfd-template" {
    uses config-bfd-template-grouping {
      refine single-hop {
        tailf:ncs-device-type "netconf";
        tailf:display-when "not(../../../../ncs:module) or ../../../../ncs:module[ncs:name='Cisco-IOS-XE-bfd']";
      }
    }
  }
  augment "/ncs:devices/ncs:template/ncs:config/ios:native/ios:interface/ios:FastEthernet/ios:bfd" {
    uses ncs_template_config-interface-bfd-grouping;
  }
  augment "/ncs:devices/ncs:device/ncs:live-status/ios:native/ios:interface/ios:FastEthernet/ios:bfd" {
    uses live_ncs_config-interface-bfd-grouping {
      refine echo {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
      refine interval {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
      refine template {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
    }
  }
  augment "/ncs:devices/ncs:device/ncs:config/ios:native/ios:interface/ios:FastEthernet/ios:bfd" {
    uses config-interface-bfd-grouping {
      refine echo {
        tailf:ncs-device-type "netconf";
        tailf:display-when "not(../../../../../../ncs:module) or ../../../../../../ncs:module[ncs:name='Cisco-IOS-XE-bfd']";
      }
      refine interval {
        tailf:ncs-device-type "netconf";
        tailf:display-when "not(../../../../../../ncs:module) or ../../../../../../ncs:module[ncs:name='Cisco-IOS-XE-bfd']";
      }
      refine template {
        tailf:ncs-device-type "netconf";
        tailf:display-when "not(../../../../../../ncs:module) or ../../../../../../ncs:module[ncs:name='Cisco-IOS-XE-bfd']";
      }
    }
  }
  augment "/ncs:devices/ncs:template/ncs:config/ios:native/ios:interface/ios:GigabitEthernet/ios:bfd" {
    uses ncs_template_config-interface-bfd-grouping;
  }
  augment "/ncs:devices/ncs:device/ncs:live-status/ios:native/ios:interface/ios:GigabitEthernet/ios:bfd" {
    uses live_ncs_config-interface-bfd-grouping {
      refine echo {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
      refine interval {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
      refine template {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
    }
  }
  augment "/ncs:devices/ncs:device/ncs:config/ios:native/ios:interface/ios:GigabitEthernet/ios:bfd" {
    uses config-interface-bfd-grouping {
      refine echo {
        tailf:ncs-device-type "netconf";
        tailf:display-when "not(../../../../../../ncs:module) or ../../../../../../ncs:module[ncs:name='Cisco-IOS-XE-bfd']";
      }
      refine interval {
        tailf:ncs-device-type "netconf";
        tailf:display-when "not(../../../../../../ncs:module) or ../../../../../../ncs:module[ncs:name='Cisco-IOS-XE-bfd']";
      }
      refine template {
        tailf:ncs-device-type "netconf";
        tailf:display-when "not(../../../../../../ncs:module) or ../../../../../../ncs:module[ncs:name='Cisco-IOS-XE-bfd']";
      }
    }
  }
  augment "/ncs:devices/ncs:template/ncs:config/ios:native/ios:interface/ios:TenGigabitEthernet/ios:bfd" {
    uses ncs_template_config-interface-bfd-grouping;
  }
  augment "/ncs:devices/ncs:device/ncs:live-status/ios:native/ios:interface/ios:TenGigabitEthernet/ios:bfd" {
    uses live_ncs_config-interface-bfd-grouping {
      refine echo {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
      refine interval {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
      refine template {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
    }
  }
  augment "/ncs:devices/ncs:device/ncs:config/ios:native/ios:interface/ios:TenGigabitEthernet/ios:bfd" {
    uses config-interface-bfd-grouping {
      refine echo {
        tailf:ncs-device-type "netconf";
        tailf:display-when "not(../../../../../../ncs:module) or ../../../../../../ncs:module[ncs:name='Cisco-IOS-XE-bfd']";
      }
      refine interval {
        tailf:ncs-device-type "netconf";
        tailf:display-when "not(../../../../../../ncs:module) or ../../../../../../ncs:module[ncs:name='Cisco-IOS-XE-bfd']";
      }
      refine template {
        tailf:ncs-device-type "netconf";
        tailf:display-when "not(../../../../../../ncs:module) or ../../../../../../ncs:module[ncs:name='Cisco-IOS-XE-bfd']";
      }
    }
  }
  augment "/ncs:devices/ncs:template/ncs:config/ios:native/ios:interface/ios:Tunnel/ios:bfd" {
    uses ncs_template_config-interface-bfd-grouping;
  }
  augment "/ncs:devices/ncs:device/ncs:live-status/ios:native/ios:interface/ios:Tunnel/ios:bfd" {
    uses live_ncs_config-interface-bfd-grouping {
      refine echo {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
      refine interval {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
      refine template {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
    }
  }
  augment "/ncs:devices/ncs:device/ncs:config/ios:native/ios:interface/ios:Tunnel/ios:bfd" {
    uses config-interface-bfd-grouping {
      refine echo {
        tailf:ncs-device-type "netconf";
        tailf:display-when "not(../../../../../../ncs:module) or ../../../../../../ncs:module[ncs:name='Cisco-IOS-XE-bfd']";
      }
      refine interval {
        tailf:ncs-device-type "netconf";
        tailf:display-when "not(../../../../../../ncs:module) or ../../../../../../ncs:module[ncs:name='Cisco-IOS-XE-bfd']";
      }
      refine template {
        tailf:ncs-device-type "netconf";
        tailf:display-when "not(../../../../../../ncs:module) or ../../../../../../ncs:module[ncs:name='Cisco-IOS-XE-bfd']";
      }
    }
  }
  augment "/ncs:devices/ncs:template/ncs:config/ios:native/ios:interface/ios:Port-channel/ios:bfd" {
    uses ncs_template_config-interface-bfd-grouping;
  }
  augment "/ncs:devices/ncs:device/ncs:live-status/ios:native/ios:interface/ios:Port-channel/ios:bfd" {
    uses live_ncs_config-interface-bfd-grouping {
      refine echo {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
      refine interval {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
      refine template {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
    }
  }
  augment "/ncs:devices/ncs:device/ncs:config/ios:native/ios:interface/ios:Port-channel/ios:bfd" {
    uses config-interface-bfd-grouping {
      refine echo {
        tailf:ncs-device-type "netconf";
        tailf:display-when "not(../../../../../../ncs:module) or ../../../../../../ncs:module[ncs:name='Cisco-IOS-XE-bfd']";
      }
      refine interval {
        tailf:ncs-device-type "netconf";
        tailf:display-when "not(../../../../../../ncs:module) or ../../../../../../ncs:module[ncs:name='Cisco-IOS-XE-bfd']";
      }
      refine template {
        tailf:ncs-device-type "netconf";
        tailf:display-when "not(../../../../../../ncs:module) or ../../../../../../ncs:module[ncs:name='Cisco-IOS-XE-bfd']";
      }
    }
  }
  augment "/ncs:devices/ncs:template/ncs:config/ios:native/ios:interface/ios:VirtualPortGroup/ios:bfd" {
    uses ncs_template_config-interface-bfd-grouping;
  }
  augment "/ncs:devices/ncs:device/ncs:live-status/ios:native/ios:interface/ios:VirtualPortGroup/ios:bfd" {
    uses live_ncs_config-interface-bfd-grouping {
      refine echo {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
      refine interval {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
      refine template {
        tailf:ncs-device-type "netconf";
        tailf:display-when "not(../../../../../../ncs:module) or ../../../../../../ncs:module[ncs:name='Cisco-IOS-XE-bfd'] or (../../../../../../ncs:live-status-protocol[not(ncs:capability)]) or (../../../../../../ncs:live-status-protocol/ncs:capability/ncs:module[.='Cisco-IOS-XE-bfd'])";
      }
    }
  }
  augment "/ncs:devices/ncs:device/ncs:config/ios:native/ios:interface/ios:VirtualPortGroup/ios:bfd" {
    uses config-interface-bfd-grouping {
      refine echo {
        tailf:ncs-device-type "netconf";
        tailf:display-when "not(../../../../../../ncs:module) or ../../../../../../ncs:module[ncs:name='Cisco-IOS-XE-bfd']";
      }
      refine interval {
        tailf:ncs-device-type "netconf";
        tailf:display-when "not(../../../../../../ncs:module) or ../../../../../../ncs:module[ncs:name='Cisco-IOS-XE-bfd']";
      }
      refine template {
        tailf:ncs-device-type "netconf";
        tailf:display-when "not(../../../../../../ncs:module) or ../../../../../../ncs:module[ncs:name='Cisco-IOS-XE-bfd']";
      }
    }
  }
}
