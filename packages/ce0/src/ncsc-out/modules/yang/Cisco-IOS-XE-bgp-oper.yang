module Cisco-IOS-XE-bgp-oper {
  // Generated by yanger -t ncs
  tailf:ncs-device-type "netconf";

  yang-version "1";
  namespace "http://cisco.com/ns/yang/Cisco-IOS-XE-bgp-oper";
  prefix bgp-ios-xe-oper;

  import Cisco-IOS-XE-bgp-common-oper {
    prefix bgp-common-ios-xe-oper;
  }
  import Cisco-IOS-XE-bgp-route-oper {
    prefix bgp-route-ios-xe-oper;
  }
  import ietf-inet-types {
    prefix inet;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for bgp operational data.
     Copyright (c) 2016-2017 by Cisco Systems, Inc.
     All rights reserved.";

  revision 2017-04-01 {
    description
      "Top level container name change. Enum name changes.";
    reference "2.0.0";
  }
  revision 2017-02-07 {
    description
      "Initial revision";
    reference "1.0.0";
  }

  typedef bgp-mode {
    type enumeration {
      enum "mode-active" {
        value 0;
        description
          "active connection";
      }
      enum "mode-passive" {
        value 1;
        description
          "passive connection";
      }
    }
    description
      "BGP mode";
  }

  typedef bgp-fsm-state {
    type enumeration {
      enum "fsm-idle" {
        value 0;
        description
          "neighbor is in Idle state";
      }
      enum "fsm-connect" {
        value 1;
        description
          "neighbor is in Connect state";
      }
      enum "fsm-active" {
        value 2;
        description
          "neighbor is in Active state";
      }
      enum "fsm-opensent" {
        value 3;
        description
          "neighbor is in OpenSent state";
      }
      enum "fsm-openconfirm" {
        value 4;
        description
          "neighbor is in OpenConfirm state";
      }
      enum "fsm-established" {
        value 5;
        description
          "neighbor is in Established state";
      }
      enum "fsm-nonnegotiated" {
        value 6;
        description
          "neighbor is Non Negotiated";
      }
    }
    description
      "BGP FSM State";
  }

  typedef bgp-link {
    type enumeration {
      enum "internal" {
        value 0;
        description
          "iBGP neighbors";
      }
      enum "external" {
        value 1;
        description
          "eBGP neighbors";
      }
    }
    description
      "Operational state relevent to bgp global neighbor";
  }

  grouping ncs_template_bgp-message-counters {
    description
      "BGP message counters";
    leaf opens {
      type string;
      description
        "OPEN message count";
    }
    leaf updates {
      type string;
      description
        "UPDATE message count";
    }
    leaf notifications {
      type string;
      description
        "NOTIFICATION message count";
    }
    leaf keepalives {
      type string;
      description
        "KEEPALIVE message count";
    }
    leaf route-refreshes {
      type string;
      description
        "Route refresh message count";
    }
  }

  grouping ncs_template_bgp-prefix-counters {
    description
      "Grouping for various prefix counters";
    leaf current-prefixes {
      type string;
      description
        "The current number of accepted prefixes";
    }
    leaf total-prefixes {
      type string;
      description
        "The total number of accepted prefixes";
    }
    leaf implicit-withdraw {
      type string;
      description
        "The number of times a prefix has been
         withdrawn and readvertised";
    }
    leaf explicit-withdraw {
      type string;
      description
        "The number of times a prefix has been
         withdrawn because it is no longer feasible";
    }
    leaf bestpaths {
      type string;
      description
        "The number of received prefixes installed as best paths";
    }
    leaf multipaths {
      type string;
      description
        "The number of received prefixes installed as multipaths";
    }
  }

  grouping ncs_template_negotiated-keepalive-timers {
    description
      "Neigotiated keepalive timers details";
    leaf hold-time {
      type string;
      description
        "Hold time";
    }
    leaf keepalive-interval {
      type string;
      description
        "Keepalive interval";
    }
  }

  grouping ncs_template_neighbor-summary {
    description
      "Information regarding the current state of a neighbor";
    leaf id {
      type string;
      description
        "Neighbor address";
    }
    leaf bgp-version {
      type string;
      description
        "BGP protocol version";
    }
    leaf messages-received {
      type string;
      description
        "Number of messages received from this neighbor";
    }
    leaf messages-sent {
      type string;
      description
        "Number of messages sent to this neighbor";
    }
    leaf table-version {
      type string;
      description
        "BGP table version";
    }
    leaf input-queue {
      type string;
      description
        "Number of messages in input queue";
    }
    leaf output-queue {
      type string;
      description
        "Number of messages in output queue";
    }
    leaf up-time {
      type string;
      description
        "Neighbor session uptime";
    }
    leaf state {
      type string;
      description
        "BGP session state";
    }
    leaf prefixes-received {
      type string;
      description
        "Number of prefixes received from the neighbor";
    }
    leaf dynamically-configured {
      type string;
      description
        "Indication of whether the neighbor was
         dyanmically configured";
    }
  }

  grouping ncs_template_bgp-connection {
    description
      "Data for current BGP connection state";
    leaf state {
      type string;
      description
        "TCP FSM state";
    }
    leaf mode {
      type string;
      description
        "BGP transport connection mode";
    }
    leaf total-established {
      type string;
      description
        "The number of times a TCP and BGP
         connection has been successfully established";
    }
    leaf total-dropped {
      type string;
      description
        "The number of times that a valid
         session has failed or been taken down";
    }
    leaf last-reset {
      type string;
      description
        "Time since peering session was last reset";
    }
    leaf reset-reason {
      type string;
      description
        "The reason for the last reset";
    }
  }

  grouping ncs_template_bgp-transport {
    description
      "BGP transport information";
    leaf path-mtu-discovery {
      type string;
      description
        "Indication whether path MTU discovrey is enabled";
    }
    leaf local-port {
      type string;
      description
        "Local TCP port used for TCP session";
    }
    leaf local-host {
      type string;
      description
        "Local address used for the TCP session";
    }
    leaf foreign-port {
      type string;
      description
        "Remote port used by the peer for the TCP session";
    }
    leaf foreign-host {
      type string;
      description
        "Remote address of the BGP session";
    }
    leaf mss {
      type string;
      description
        "Maximum Data segment size";
    }
  }

  grouping ncs_template_bgp-af-prefix-activity {
    description
      "Address family prefix statistics";
    container sent {
      description
        "Number of prefixes sent";
      uses bgp-ios-xe-oper:ncs_template_bgp-prefix-counters;
    }
    container received {
      description
        "Number of prefixes received";
      uses bgp-ios-xe-oper:ncs_template_bgp-prefix-counters;
    }
  }

  grouping ncs_template_bgp-neighbor-counters {
    description
      "BGP neighbor session counters";
    container sent {
      description
        "Number of mesaged sent";
      uses bgp-ios-xe-oper:ncs_template_bgp-message-counters;
    }
    container received {
      description
        "Number of mesaged received";
      uses bgp-ios-xe-oper:ncs_template_bgp-message-counters;
    }
    leaf inq-depth {
      type string;
      description
        "Input Q depth";
    }
    leaf outq-depth {
      type string;
      description
        "Output Q depth";
    }
  }

  grouping ncs_template_neighbor-key {
    description
      "Grouping for neighbor key";
    leaf afi-safi {
      type string;
      description
        "Afi-safi key";
    }
    leaf vrf-name {
      type string;
      description
        "VRF name";
    }
    leaf neighbor-id {
      type string;
      description
        "Neighbor identifier";
    }
  }

  grouping ncs_template_neighbor {
    description
      "BGP neighbor state information";
    leaf description {
      type string;
      description
        "Neighbor description string";
    }
    leaf bgp-version {
      type string;
      description
        "BGP version being used to communicate
         with the remote router";
    }
    leaf link {
      type string;
      description
        "Neighbor link type";
    }
    leaf up-time {
      type string;
      description
        "Amout of time the bgp session has been
         up since being established";
    }
    leaf last-write {
      type string;
      description
        "Time since BGP last sent a message to the neighbor";
    }
    leaf last-read {
      type string;
      description
        "Time since BGP last received a message from the neighbor";
    }
    leaf installed-prefixes {
      type string;
      description
        "The number of installed prefixes";
    }
    leaf session-state {
      type string;
      description
        "BGP neighbor session state";
    }
    container negotiated-keepalive-timers {
      description
        "Negotiated keepalive timers status of BGP neighbor";
      uses bgp-ios-xe-oper:ncs_template_negotiated-keepalive-timers;
    }
    leaf-list negotiated-cap {
      // NCS patched for predictable order
      ordered-by user;
      type string;
      description
        "Negotiated capabilities for neighbor session";
    }
    container bgp-neighbor-counters {
      description
        "BGP neighbor session counters";
      uses bgp-ios-xe-oper:ncs_template_bgp-neighbor-counters;
    }
    container connection {
      description
        "BGP neighbor connection";
      uses bgp-ios-xe-oper:ncs_template_bgp-connection;
    }
    container transport {
      description
        "BGP neighbor transport";
      uses bgp-ios-xe-oper:ncs_template_bgp-transport;
    }
    container prefix-activity {
      description
        "BGP neighbor activity";
      uses bgp-ios-xe-oper:ncs_template_bgp-af-prefix-activity;
    }
  }

  grouping ncs_template_entry-stats {
    description
      "BGP entry statistics";
    leaf total-entries {
      type string;
      description
        "The total number of prefix entries";
    }
    leaf memory-usage {
      type string;
      description
        "Total memory usage in byte";
    }
  }

  grouping ncs_template_activities {
    description
      "BGP activity information";
    leaf prefixes {
      type string;
      description
        "Total number of prefixes";
    }
    leaf paths {
      type string;
      description
        "Total number of paths";
    }
    leaf scan-interval {
      type string;
      description
        "Scan interval in seconds";
    }
  }

  grouping ncs_template_address-family-key {
    description
      "Address family key";
    leaf afi-safi {
      type string;
      description
        "Afi-safi value";
    }
    leaf vrf-name {
      type string;
      description
        "VRF name";
    }
  }

  grouping ncs_template_address-family-summary {
    description
      "Summary of address family";
    leaf router-id {
      type string;
      description
        "Router ID";
    }
    leaf bgp-table-version {
      type string;
      description
        "BGP table version number";
    }
    leaf routing-table-version {
      type string;
      description
        "Routing table version number";
    }
    container prefixes {
      description
        "Prefix entry statistics";
      uses bgp-ios-xe-oper:ncs_template_entry-stats;
    }
    container path {
      description
        "Path entry statistics";
      uses bgp-ios-xe-oper:ncs_template_entry-stats;
    }
    container as-path {
      description
        "AS path entry statistics";
      uses bgp-ios-xe-oper:ncs_template_entry-stats;
    }
    container route-map {
      description
        "Route map entry statistics";
      uses bgp-ios-xe-oper:ncs_template_entry-stats;
    }
    container filter-list {
      description
        "Filter list entry statistics";
      uses bgp-ios-xe-oper:ncs_template_entry-stats;
    }
    container activities {
      description
        "BGP activity information";
      uses bgp-ios-xe-oper:ncs_template_activities;
    }
    leaf total-memory {
      type string;
      description
        "Total memory in use";
    }
    container bgp-neighbor-summaries {
      description
        "Neighbor summary";
      list bgp-neighbor-summary {
        // NCS patched for predictable order
        ordered-by user;
        key "id";
        description
          "List of neighbor summaries";
        uses bgp-ios-xe-oper:ncs_template_neighbor-summary;
      }
    }
  }

  grouping ncs_template_bgp-state {
    description
      "BGP state informtion";
    container neighbors {
      description
        "BGP neighbor information";
      list neighbor {
        // NCS patched for predictable order
        ordered-by user;
        key "afi-safi vrf-name neighbor-id";
        description
          "List of BGP neighbors";
        uses bgp-ios-xe-oper:ncs_template_neighbor-key;
        uses bgp-ios-xe-oper:ncs_template_neighbor;
      }
    }
    container address-families {
      description
        "BGP address family";
      list address-family {
        // NCS patched for predictable order
        ordered-by user;
        key "afi-safi vrf-name";
        description
          "List of BGP address families";
        uses bgp-ios-xe-oper:ncs_template_address-family-key;
        uses bgp-ios-xe-oper:ncs_template_address-family-summary;
      }
    }
    container bgp-route-vrfs {
      description
        "BGP VRFs";
      list bgp-route-vrf {
        // NCS patched for predictable order
        ordered-by user;
        key "vrf";
        description
          "List of BGP VRFs";
        uses bgp-route-ios-xe-oper:ncs_template_vrf-record;
      }
    }
  }

  grouping ncs_rpc_notif_bgp-message-counters {
    description
      "BGP message counters";
    leaf opens {
      type uint32;
      description
        "OPEN message count";
    }
    leaf updates {
      type uint32;
      description
        "UPDATE message count";
    }
    leaf notifications {
      type uint32;
      description
        "NOTIFICATION message count";
    }
    leaf keepalives {
      type uint32;
      description
        "KEEPALIVE message count";
    }
    leaf route-refreshes {
      type uint32;
      description
        "Route refresh message count";
    }
  }

  grouping ncs_rpc_notif_bgp-prefix-counters {
    description
      "Grouping for various prefix counters";
    leaf current-prefixes {
      type uint64;
      description
        "The current number of accepted prefixes";
    }
    leaf total-prefixes {
      type uint64;
      description
        "The total number of accepted prefixes";
    }
    leaf implicit-withdraw {
      type uint64;
      description
        "The number of times a prefix has been
         withdrawn and readvertised";
    }
    leaf explicit-withdraw {
      type uint64;
      description
        "The number of times a prefix has been
         withdrawn because it is no longer feasible";
    }
    leaf bestpaths {
      type uint64;
      description
        "The number of received prefixes installed as best paths";
    }
    leaf multipaths {
      type uint64;
      description
        "The number of received prefixes installed as multipaths";
    }
  }

  grouping ncs_rpc_notif_negotiated-keepalive-timers {
    description
      "Neigotiated keepalive timers details";
    leaf hold-time {
      type uint16;
      description
        "Hold time";
    }
    leaf keepalive-interval {
      type uint16;
      description
        "Keepalive interval";
    }
  }

  grouping ncs_rpc_notif_neighbor-summary {
    description
      "Information regarding the current state of a neighbor";
    leaf id {
      type string;
      description
        "Neighbor address";
    }
    leaf bgp-version {
      type uint32;
      description
        "BGP protocol version";
    }
    leaf messages-received {
      type uint64;
      description
        "Number of messages received from this neighbor";
    }
    leaf messages-sent {
      type uint64;
      description
        "Number of messages sent to this neighbor";
    }
    leaf table-version {
      type uint64;
      description
        "BGP table version";
    }
    leaf input-queue {
      type uint64;
      description
        "Number of messages in input queue";
    }
    leaf output-queue {
      type uint64;
      description
        "Number of messages in output queue";
    }
    leaf up-time {
      type string;
      description
        "Neighbor session uptime";
    }
    leaf state {
      type bgp-ios-xe-oper:bgp-fsm-state;
      description
        "BGP session state";
    }
    leaf prefixes-received {
      type uint64;
      description
        "Number of prefixes received from the neighbor";
    }
    leaf dynamically-configured {
      type boolean;
      description
        "Indication of whether the neighbor was
         dyanmically configured";
    }
  }

  grouping ncs_rpc_notif_bgp-connection {
    description
      "Data for current BGP connection state";
    leaf state {
      type bgp-common-ios-xe-oper:tcp-fsm-state;
      description
        "TCP FSM state";
    }
    leaf mode {
      type bgp-ios-xe-oper:bgp-mode;
      description
        "BGP transport connection mode";
    }
    leaf total-established {
      type uint32;
      description
        "The number of times a TCP and BGP
         connection has been successfully established";
    }
    leaf total-dropped {
      type uint32;
      description
        "The number of times that a valid
         session has failed or been taken down";
    }
    leaf last-reset {
      type string;
      description
        "Time since peering session was last reset";
    }
    leaf reset-reason {
      type string;
      description
        "The reason for the last reset";
    }
  }

  grouping ncs_rpc_notif_bgp-transport {
    description
      "BGP transport information";
    leaf path-mtu-discovery {
      type boolean;
      description
        "Indication whether path MTU discovrey is enabled";
    }
    leaf local-port {
      type uint32;
      description
        "Local TCP port used for TCP session";
    }
    leaf local-host {
      type inet:ip-address;
      description
        "Local address used for the TCP session";
    }
    leaf foreign-port {
      type uint32;
      description
        "Remote port used by the peer for the TCP session";
    }
    leaf foreign-host {
      type inet:ip-address;
      description
        "Remote address of the BGP session";
    }
    leaf mss {
      type uint32;
      description
        "Maximum Data segment size";
    }
  }

  grouping ncs_rpc_notif_bgp-af-prefix-activity {
    description
      "Address family prefix statistics";
    container sent {
      description
        "Number of prefixes sent";
      uses bgp-ios-xe-oper:ncs_rpc_notif_bgp-prefix-counters;
    }
    container received {
      description
        "Number of prefixes received";
      uses bgp-ios-xe-oper:ncs_rpc_notif_bgp-prefix-counters;
    }
  }

  grouping ncs_rpc_notif_bgp-neighbor-counters {
    description
      "BGP neighbor session counters";
    container sent {
      description
        "Number of mesaged sent";
      uses bgp-ios-xe-oper:ncs_rpc_notif_bgp-message-counters;
    }
    container received {
      description
        "Number of mesaged received";
      uses bgp-ios-xe-oper:ncs_rpc_notif_bgp-message-counters;
    }
    leaf inq-depth {
      type uint32;
      description
        "Input Q depth";
    }
    leaf outq-depth {
      type uint32;
      description
        "Output Q depth";
    }
  }

  grouping ncs_rpc_notif_neighbor-key {
    description
      "Grouping for neighbor key";
    leaf afi-safi {
      type bgp-common-ios-xe-oper:afi-safi;
      description
        "Afi-safi key";
    }
    leaf vrf-name {
      type string;
      description
        "VRF name";
    }
    leaf neighbor-id {
      type string;
      description
        "Neighbor identifier";
    }
  }

  grouping ncs_rpc_notif_neighbor {
    description
      "BGP neighbor state information";
    leaf description {
      type string;
      description
        "Neighbor description string";
    }
    leaf bgp-version {
      type uint16;
      description
        "BGP version being used to communicate
         with the remote router";
    }
    leaf link {
      type bgp-ios-xe-oper:bgp-link;
      description
        "Neighbor link type";
    }
    leaf up-time {
      type string;
      description
        "Amout of time the bgp session has been
         up since being established";
    }
    leaf last-write {
      type string;
      description
        "Time since BGP last sent a message to the neighbor";
    }
    leaf last-read {
      type string;
      description
        "Time since BGP last received a message from the neighbor";
    }
    leaf installed-prefixes {
      type uint32;
      description
        "The number of installed prefixes";
    }
    leaf session-state {
      type bgp-ios-xe-oper:bgp-fsm-state;
      description
        "BGP neighbor session state";
    }
    container negotiated-keepalive-timers {
      description
        "Negotiated keepalive timers status of BGP neighbor";
      uses bgp-ios-xe-oper:ncs_rpc_notif_negotiated-keepalive-timers;
    }
    leaf-list negotiated-cap {
      type string;
      description
        "Negotiated capabilities for neighbor session";
    }
    container bgp-neighbor-counters {
      description
        "BGP neighbor session counters";
      uses bgp-ios-xe-oper:ncs_rpc_notif_bgp-neighbor-counters;
    }
    container connection {
      description
        "BGP neighbor connection";
      uses bgp-ios-xe-oper:ncs_rpc_notif_bgp-connection;
    }
    container transport {
      description
        "BGP neighbor transport";
      uses bgp-ios-xe-oper:ncs_rpc_notif_bgp-transport;
    }
    container prefix-activity {
      description
        "BGP neighbor activity";
      uses bgp-ios-xe-oper:ncs_rpc_notif_bgp-af-prefix-activity;
    }
  }

  grouping ncs_rpc_notif_entry-stats {
    description
      "BGP entry statistics";
    leaf total-entries {
      type uint64;
      description
        "The total number of prefix entries";
    }
    leaf memory-usage {
      type uint64;
      description
        "Total memory usage in byte";
    }
  }

  grouping ncs_rpc_notif_activities {
    description
      "BGP activity information";
    leaf prefixes {
      type uint64;
      description
        "Total number of prefixes";
    }
    leaf paths {
      type uint64;
      description
        "Total number of paths";
    }
    leaf scan-interval {
      type string;
      description
        "Scan interval in seconds";
    }
  }

  grouping ncs_rpc_notif_address-family-key {
    description
      "Address family key";
    leaf afi-safi {
      type bgp-common-ios-xe-oper:afi-safi;
      description
        "Afi-safi value";
    }
    leaf vrf-name {
      type string;
      description
        "VRF name";
    }
  }

  grouping ncs_rpc_notif_address-family-summary {
    description
      "Summary of address family";
    leaf router-id {
      type inet:ip-address;
      description
        "Router ID";
    }
    leaf bgp-table-version {
      type uint64;
      description
        "BGP table version number";
    }
    leaf routing-table-version {
      type uint64;
      description
        "Routing table version number";
    }
    container prefixes {
      description
        "Prefix entry statistics";
      uses bgp-ios-xe-oper:ncs_rpc_notif_entry-stats;
    }
    container path {
      description
        "Path entry statistics";
      uses bgp-ios-xe-oper:ncs_rpc_notif_entry-stats;
    }
    container as-path {
      description
        "AS path entry statistics";
      uses bgp-ios-xe-oper:ncs_rpc_notif_entry-stats;
    }
    container route-map {
      description
        "Route map entry statistics";
      uses bgp-ios-xe-oper:ncs_rpc_notif_entry-stats;
    }
    container filter-list {
      description
        "Filter list entry statistics";
      uses bgp-ios-xe-oper:ncs_rpc_notif_entry-stats;
    }
    container activities {
      description
        "BGP activity information";
      uses bgp-ios-xe-oper:ncs_rpc_notif_activities;
    }
    leaf total-memory {
      type uint64;
      description
        "Total memory in use";
    }
    container bgp-neighbor-summaries {
      description
        "Neighbor summary";
      list bgp-neighbor-summary {
        key "id";
        description
          "List of neighbor summaries";
        uses bgp-ios-xe-oper:ncs_rpc_notif_neighbor-summary;
      }
    }
  }

  grouping ncs_rpc_notif_bgp-state {
    description
      "BGP state informtion";
    container neighbors {
      description
        "BGP neighbor information";
      list neighbor {
        key "afi-safi vrf-name neighbor-id";
        description
          "List of BGP neighbors";
        uses bgp-ios-xe-oper:ncs_rpc_notif_neighbor-key;
        uses bgp-ios-xe-oper:ncs_rpc_notif_neighbor;
      }
    }
    container address-families {
      description
        "BGP address family";
      list address-family {
        key "afi-safi vrf-name";
        description
          "List of BGP address families";
        uses bgp-ios-xe-oper:ncs_rpc_notif_address-family-key;
        uses bgp-ios-xe-oper:ncs_rpc_notif_address-family-summary;
      }
    }
    container bgp-route-vrfs {
      description
        "BGP VRFs";
      list bgp-route-vrf {
        key "vrf";
        description
          "List of BGP VRFs";
        uses bgp-route-ios-xe-oper:ncs_rpc_notif_vrf-record;
      }
    }
  }

  grouping live_ncs_bgp-message-counters {
    description
      "BGP message counters";
    leaf opens {
      type uint32;
      description
        "OPEN message count";
    }
    leaf updates {
      type uint32;
      description
        "UPDATE message count";
    }
    leaf notifications {
      type uint32;
      description
        "NOTIFICATION message count";
    }
    leaf keepalives {
      type uint32;
      description
        "KEEPALIVE message count";
    }
    leaf route-refreshes {
      type uint32;
      description
        "Route refresh message count";
    }
  }

  grouping live_ncs_bgp-prefix-counters {
    description
      "Grouping for various prefix counters";
    leaf current-prefixes {
      type uint64;
      description
        "The current number of accepted prefixes";
    }
    leaf total-prefixes {
      type uint64;
      description
        "The total number of accepted prefixes";
    }
    leaf implicit-withdraw {
      type uint64;
      description
        "The number of times a prefix has been
         withdrawn and readvertised";
    }
    leaf explicit-withdraw {
      type uint64;
      description
        "The number of times a prefix has been
         withdrawn because it is no longer feasible";
    }
    leaf bestpaths {
      type uint64;
      description
        "The number of received prefixes installed as best paths";
    }
    leaf multipaths {
      type uint64;
      description
        "The number of received prefixes installed as multipaths";
    }
  }

  grouping live_ncs_negotiated-keepalive-timers {
    description
      "Neigotiated keepalive timers details";
    leaf hold-time {
      type uint16;
      description
        "Hold time";
    }
    leaf keepalive-interval {
      type uint16;
      description
        "Keepalive interval";
    }
  }

  grouping live_ncs_neighbor-summary {
    description
      "Information regarding the current state of a neighbor";
    leaf id {
      type string;
      description
        "Neighbor address";
    }
    leaf bgp-version {
      type uint32;
      description
        "BGP protocol version";
    }
    leaf messages-received {
      type uint64;
      description
        "Number of messages received from this neighbor";
    }
    leaf messages-sent {
      type uint64;
      description
        "Number of messages sent to this neighbor";
    }
    leaf table-version {
      type uint64;
      description
        "BGP table version";
    }
    leaf input-queue {
      type uint64;
      description
        "Number of messages in input queue";
    }
    leaf output-queue {
      type uint64;
      description
        "Number of messages in output queue";
    }
    leaf up-time {
      type string;
      description
        "Neighbor session uptime";
    }
    leaf state {
      type bgp-ios-xe-oper:bgp-fsm-state;
      description
        "BGP session state";
    }
    leaf prefixes-received {
      type uint64;
      description
        "Number of prefixes received from the neighbor";
    }
    leaf dynamically-configured {
      type boolean;
      description
        "Indication of whether the neighbor was
         dyanmically configured";
    }
  }

  grouping live_ncs_bgp-connection {
    description
      "Data for current BGP connection state";
    leaf state {
      type bgp-common-ios-xe-oper:tcp-fsm-state;
      description
        "TCP FSM state";
    }
    leaf mode {
      type bgp-ios-xe-oper:bgp-mode;
      description
        "BGP transport connection mode";
    }
    leaf total-established {
      type uint32;
      description
        "The number of times a TCP and BGP
         connection has been successfully established";
    }
    leaf total-dropped {
      type uint32;
      description
        "The number of times that a valid
         session has failed or been taken down";
    }
    leaf last-reset {
      type string;
      description
        "Time since peering session was last reset";
    }
    leaf reset-reason {
      type string;
      description
        "The reason for the last reset";
    }
  }

  grouping live_ncs_bgp-transport {
    description
      "BGP transport information";
    leaf path-mtu-discovery {
      type boolean;
      description
        "Indication whether path MTU discovrey is enabled";
    }
    leaf local-port {
      type uint32;
      description
        "Local TCP port used for TCP session";
    }
    leaf local-host {
      type inet:ip-address;
      description
        "Local address used for the TCP session";
    }
    leaf foreign-port {
      type uint32;
      description
        "Remote port used by the peer for the TCP session";
    }
    leaf foreign-host {
      type inet:ip-address;
      description
        "Remote address of the BGP session";
    }
    leaf mss {
      type uint32;
      description
        "Maximum Data segment size";
    }
  }

  grouping live_ncs_bgp-af-prefix-activity {
    description
      "Address family prefix statistics";
    container sent {
      description
        "Number of prefixes sent";
      uses bgp-ios-xe-oper:live_ncs_bgp-prefix-counters;
    }
    container received {
      description
        "Number of prefixes received";
      uses bgp-ios-xe-oper:live_ncs_bgp-prefix-counters;
    }
  }

  grouping live_ncs_bgp-neighbor-counters {
    description
      "BGP neighbor session counters";
    container sent {
      description
        "Number of mesaged sent";
      uses bgp-ios-xe-oper:live_ncs_bgp-message-counters;
    }
    container received {
      description
        "Number of mesaged received";
      uses bgp-ios-xe-oper:live_ncs_bgp-message-counters;
    }
    leaf inq-depth {
      type uint32;
      description
        "Input Q depth";
    }
    leaf outq-depth {
      type uint32;
      description
        "Output Q depth";
    }
  }

  grouping live_ncs_neighbor-key {
    description
      "Grouping for neighbor key";
    leaf afi-safi {
      type bgp-common-ios-xe-oper:afi-safi;
      description
        "Afi-safi key";
    }
    leaf vrf-name {
      type string;
      description
        "VRF name";
    }
    leaf neighbor-id {
      type string;
      description
        "Neighbor identifier";
    }
  }

  grouping live_ncs_neighbor {
    description
      "BGP neighbor state information";
    leaf description {
      type string;
      description
        "Neighbor description string";
    }
    leaf bgp-version {
      type uint16;
      description
        "BGP version being used to communicate
         with the remote router";
    }
    leaf link {
      type bgp-ios-xe-oper:bgp-link;
      description
        "Neighbor link type";
    }
    leaf up-time {
      type string;
      description
        "Amout of time the bgp session has been
         up since being established";
    }
    leaf last-write {
      type string;
      description
        "Time since BGP last sent a message to the neighbor";
    }
    leaf last-read {
      type string;
      description
        "Time since BGP last received a message from the neighbor";
    }
    leaf installed-prefixes {
      type uint32;
      description
        "The number of installed prefixes";
    }
    leaf session-state {
      type bgp-ios-xe-oper:bgp-fsm-state;
      description
        "BGP neighbor session state";
    }
    container negotiated-keepalive-timers {
      description
        "Negotiated keepalive timers status of BGP neighbor";
      uses bgp-ios-xe-oper:live_ncs_negotiated-keepalive-timers;
    }
    leaf-list negotiated-cap {
      type string;
      description
        "Negotiated capabilities for neighbor session";
    }
    container bgp-neighbor-counters {
      description
        "BGP neighbor session counters";
      uses bgp-ios-xe-oper:live_ncs_bgp-neighbor-counters;
    }
    container connection {
      description
        "BGP neighbor connection";
      uses bgp-ios-xe-oper:live_ncs_bgp-connection;
    }
    container transport {
      description
        "BGP neighbor transport";
      uses bgp-ios-xe-oper:live_ncs_bgp-transport;
    }
    container prefix-activity {
      description
        "BGP neighbor activity";
      uses bgp-ios-xe-oper:live_ncs_bgp-af-prefix-activity;
    }
  }

  grouping live_ncs_entry-stats {
    description
      "BGP entry statistics";
    leaf total-entries {
      type uint64;
      description
        "The total number of prefix entries";
    }
    leaf memory-usage {
      type uint64;
      description
        "Total memory usage in byte";
    }
  }

  grouping live_ncs_activities {
    description
      "BGP activity information";
    leaf prefixes {
      type uint64;
      description
        "Total number of prefixes";
    }
    leaf paths {
      type uint64;
      description
        "Total number of paths";
    }
    leaf scan-interval {
      type string;
      description
        "Scan interval in seconds";
    }
  }

  grouping live_ncs_address-family-key {
    description
      "Address family key";
    leaf afi-safi {
      type bgp-common-ios-xe-oper:afi-safi;
      description
        "Afi-safi value";
    }
    leaf vrf-name {
      type string;
      description
        "VRF name";
    }
  }

  grouping live_ncs_address-family-summary {
    description
      "Summary of address family";
    leaf router-id {
      type inet:ip-address;
      description
        "Router ID";
    }
    leaf bgp-table-version {
      type uint64;
      description
        "BGP table version number";
    }
    leaf routing-table-version {
      type uint64;
      description
        "Routing table version number";
    }
    container prefixes {
      description
        "Prefix entry statistics";
      uses bgp-ios-xe-oper:live_ncs_entry-stats;
    }
    container path {
      description
        "Path entry statistics";
      uses bgp-ios-xe-oper:live_ncs_entry-stats;
    }
    container as-path {
      description
        "AS path entry statistics";
      uses bgp-ios-xe-oper:live_ncs_entry-stats;
    }
    container route-map {
      description
        "Route map entry statistics";
      uses bgp-ios-xe-oper:live_ncs_entry-stats;
    }
    container filter-list {
      description
        "Filter list entry statistics";
      uses bgp-ios-xe-oper:live_ncs_entry-stats;
    }
    container activities {
      description
        "BGP activity information";
      uses bgp-ios-xe-oper:live_ncs_activities;
    }
    leaf total-memory {
      type uint64;
      description
        "Total memory in use";
    }
    container bgp-neighbor-summaries {
      description
        "Neighbor summary";
      list bgp-neighbor-summary {
        key "id";
        description
          "List of neighbor summaries";
        uses bgp-ios-xe-oper:live_ncs_neighbor-summary;
      }
    }
  }

  grouping live_ncs_bgp-state {
    description
      "BGP state informtion";
    container neighbors {
      description
        "BGP neighbor information";
      list neighbor {
        key "afi-safi vrf-name neighbor-id";
        description
          "List of BGP neighbors";
        uses bgp-ios-xe-oper:live_ncs_neighbor-key;
        uses bgp-ios-xe-oper:live_ncs_neighbor;
      }
    }
    container address-families {
      description
        "BGP address family";
      list address-family {
        key "afi-safi vrf-name";
        description
          "List of BGP address families";
        uses bgp-ios-xe-oper:live_ncs_address-family-key;
        uses bgp-ios-xe-oper:live_ncs_address-family-summary;
      }
    }
    container bgp-route-vrfs {
      description
        "BGP VRFs";
      list bgp-route-vrf {
        key "vrf";
        description
          "List of BGP VRFs";
        uses bgp-route-ios-xe-oper:live_ncs_vrf-record;
      }
    }
  }

  grouping bgp-message-counters {
    description
      "BGP message counters";
    leaf opens {
      type uint32;
      description
        "OPEN message count";
    }
    leaf updates {
      type uint32;
      description
        "UPDATE message count";
    }
    leaf notifications {
      type uint32;
      description
        "NOTIFICATION message count";
    }
    leaf keepalives {
      type uint32;
      description
        "KEEPALIVE message count";
    }
    leaf route-refreshes {
      type uint32;
      description
        "Route refresh message count";
    }
  }

  grouping bgp-prefix-counters {
    description
      "Grouping for various prefix counters";
    leaf current-prefixes {
      type uint64;
      description
        "The current number of accepted prefixes";
    }
    leaf total-prefixes {
      type uint64;
      description
        "The total number of accepted prefixes";
    }
    leaf implicit-withdraw {
      type uint64;
      description
        "The number of times a prefix has been
         withdrawn and readvertised";
    }
    leaf explicit-withdraw {
      type uint64;
      description
        "The number of times a prefix has been
         withdrawn because it is no longer feasible";
    }
    leaf bestpaths {
      type uint64;
      description
        "The number of received prefixes installed as best paths";
    }
    leaf multipaths {
      type uint64;
      description
        "The number of received prefixes installed as multipaths";
    }
  }

  grouping negotiated-keepalive-timers {
    description
      "Neigotiated keepalive timers details";
    leaf hold-time {
      type uint16;
      description
        "Hold time";
    }
    leaf keepalive-interval {
      type uint16;
      description
        "Keepalive interval";
    }
  }

  grouping neighbor-summary {
    description
      "Information regarding the current state of a neighbor";
    leaf id {
      type string;
      description
        "Neighbor address";
    }
    leaf bgp-version {
      type uint32;
      description
        "BGP protocol version";
    }
    leaf messages-received {
      type uint64;
      description
        "Number of messages received from this neighbor";
    }
    leaf messages-sent {
      type uint64;
      description
        "Number of messages sent to this neighbor";
    }
    leaf table-version {
      type uint64;
      description
        "BGP table version";
    }
    leaf input-queue {
      type uint64;
      description
        "Number of messages in input queue";
    }
    leaf output-queue {
      type uint64;
      description
        "Number of messages in output queue";
    }
    leaf up-time {
      type string;
      description
        "Neighbor session uptime";
    }
    leaf state {
      type bgp-ios-xe-oper:bgp-fsm-state;
      description
        "BGP session state";
    }
    leaf prefixes-received {
      type uint64;
      description
        "Number of prefixes received from the neighbor";
    }
    leaf dynamically-configured {
      type boolean;
      description
        "Indication of whether the neighbor was
         dyanmically configured";
    }
  }

  grouping bgp-connection {
    description
      "Data for current BGP connection state";
    leaf state {
      type bgp-common-ios-xe-oper:tcp-fsm-state;
      description
        "TCP FSM state";
    }
    leaf mode {
      type bgp-ios-xe-oper:bgp-mode;
      description
        "BGP transport connection mode";
    }
    leaf total-established {
      type uint32;
      description
        "The number of times a TCP and BGP
         connection has been successfully established";
    }
    leaf total-dropped {
      type uint32;
      description
        "The number of times that a valid
         session has failed or been taken down";
    }
    leaf last-reset {
      type string;
      description
        "Time since peering session was last reset";
    }
    leaf reset-reason {
      type string;
      description
        "The reason for the last reset";
    }
  }

  grouping bgp-transport {
    description
      "BGP transport information";
    leaf path-mtu-discovery {
      type boolean;
      description
        "Indication whether path MTU discovrey is enabled";
    }
    leaf local-port {
      type uint32;
      description
        "Local TCP port used for TCP session";
    }
    leaf local-host {
      type inet:ip-address;
      description
        "Local address used for the TCP session";
    }
    leaf foreign-port {
      type uint32;
      description
        "Remote port used by the peer for the TCP session";
    }
    leaf foreign-host {
      type inet:ip-address;
      description
        "Remote address of the BGP session";
    }
    leaf mss {
      type uint32;
      description
        "Maximum Data segment size";
    }
  }

  grouping bgp-af-prefix-activity {
    description
      "Address family prefix statistics";
    container sent {
      description
        "Number of prefixes sent";
      uses bgp-ios-xe-oper:bgp-prefix-counters;
    }
    container received {
      description
        "Number of prefixes received";
      uses bgp-ios-xe-oper:bgp-prefix-counters;
    }
  }

  grouping bgp-neighbor-counters {
    description
      "BGP neighbor session counters";
    container sent {
      description
        "Number of mesaged sent";
      uses bgp-ios-xe-oper:bgp-message-counters;
    }
    container received {
      description
        "Number of mesaged received";
      uses bgp-ios-xe-oper:bgp-message-counters;
    }
    leaf inq-depth {
      type uint32;
      description
        "Input Q depth";
    }
    leaf outq-depth {
      type uint32;
      description
        "Output Q depth";
    }
  }

  grouping neighbor-key {
    description
      "Grouping for neighbor key";
    leaf afi-safi {
      type bgp-common-ios-xe-oper:afi-safi;
      description
        "Afi-safi key";
    }
    leaf vrf-name {
      type string;
      description
        "VRF name";
    }
    leaf neighbor-id {
      type string;
      description
        "Neighbor identifier";
    }
  }

  grouping neighbor {
    description
      "BGP neighbor state information";
    leaf description {
      type string;
      description
        "Neighbor description string";
    }
    leaf bgp-version {
      type uint16;
      description
        "BGP version being used to communicate
         with the remote router";
    }
    leaf link {
      type bgp-ios-xe-oper:bgp-link;
      description
        "Neighbor link type";
    }
    leaf up-time {
      type string;
      description
        "Amout of time the bgp session has been
         up since being established";
    }
    leaf last-write {
      type string;
      description
        "Time since BGP last sent a message to the neighbor";
    }
    leaf last-read {
      type string;
      description
        "Time since BGP last received a message from the neighbor";
    }
    leaf installed-prefixes {
      type uint32;
      description
        "The number of installed prefixes";
    }
    leaf session-state {
      type bgp-ios-xe-oper:bgp-fsm-state;
      description
        "BGP neighbor session state";
    }
    container negotiated-keepalive-timers {
      description
        "Negotiated keepalive timers status of BGP neighbor";
      uses bgp-ios-xe-oper:negotiated-keepalive-timers;
    }
    leaf-list negotiated-cap {
      type string;
      description
        "Negotiated capabilities for neighbor session";
    }
    container bgp-neighbor-counters {
      description
        "BGP neighbor session counters";
      uses bgp-ios-xe-oper:bgp-neighbor-counters;
    }
    container connection {
      description
        "BGP neighbor connection";
      uses bgp-ios-xe-oper:bgp-connection;
    }
    container transport {
      description
        "BGP neighbor transport";
      uses bgp-ios-xe-oper:bgp-transport;
    }
    container prefix-activity {
      description
        "BGP neighbor activity";
      uses bgp-ios-xe-oper:bgp-af-prefix-activity;
    }
  }

  grouping entry-stats {
    description
      "BGP entry statistics";
    leaf total-entries {
      type uint64;
      description
        "The total number of prefix entries";
    }
    leaf memory-usage {
      type uint64;
      description
        "Total memory usage in byte";
    }
  }

  grouping activities {
    description
      "BGP activity information";
    leaf prefixes {
      type uint64;
      description
        "Total number of prefixes";
    }
    leaf paths {
      type uint64;
      description
        "Total number of paths";
    }
    leaf scan-interval {
      type string;
      description
        "Scan interval in seconds";
    }
  }

  grouping address-family-key {
    description
      "Address family key";
    leaf afi-safi {
      type bgp-common-ios-xe-oper:afi-safi;
      description
        "Afi-safi value";
    }
    leaf vrf-name {
      type string;
      description
        "VRF name";
    }
  }

  grouping address-family-summary {
    description
      "Summary of address family";
    leaf router-id {
      type inet:ip-address;
      description
        "Router ID";
    }
    leaf bgp-table-version {
      type uint64;
      description
        "BGP table version number";
    }
    leaf routing-table-version {
      type uint64;
      description
        "Routing table version number";
    }
    container prefixes {
      description
        "Prefix entry statistics";
      uses bgp-ios-xe-oper:entry-stats;
    }
    container path {
      description
        "Path entry statistics";
      uses bgp-ios-xe-oper:entry-stats;
    }
    container as-path {
      description
        "AS path entry statistics";
      uses bgp-ios-xe-oper:entry-stats;
    }
    container route-map {
      description
        "Route map entry statistics";
      uses bgp-ios-xe-oper:entry-stats;
    }
    container filter-list {
      description
        "Filter list entry statistics";
      uses bgp-ios-xe-oper:entry-stats;
    }
    container activities {
      description
        "BGP activity information";
      uses bgp-ios-xe-oper:activities;
    }
    leaf total-memory {
      type uint64;
      description
        "Total memory in use";
    }
    container bgp-neighbor-summaries {
      description
        "Neighbor summary";
      list bgp-neighbor-summary {
        key "id";
        description
          "List of neighbor summaries";
        uses bgp-ios-xe-oper:neighbor-summary;
      }
    }
  }

  grouping bgp-state {
    description
      "BGP state informtion";
    container neighbors {
      description
        "BGP neighbor information";
      list neighbor {
        key "afi-safi vrf-name neighbor-id";
        description
          "List of BGP neighbors";
        uses bgp-ios-xe-oper:neighbor-key;
        uses bgp-ios-xe-oper:neighbor;
      }
    }
    container address-families {
      description
        "BGP address family";
      list address-family {
        key "afi-safi vrf-name";
        description
          "List of BGP address families";
        uses bgp-ios-xe-oper:address-family-key;
        uses bgp-ios-xe-oper:address-family-summary;
      }
    }
    container bgp-route-vrfs {
      description
        "BGP VRFs";
      list bgp-route-vrf {
        key "vrf";
        description
          "List of BGP VRFs";
        uses bgp-route-ios-xe-oper:vrf-record;
      }
    }
  }

  augment "/ncs:devices/ncs:device/ncs:config" {
    // NCS drop config false container 'bgp-state-data'
  }
  augment "/ncs:devices/ncs:device/ncs:live-status" {
    container bgp-state-data {
      tailf:ncs-device-type "netconf";
      tailf:display-when "not(../../ncs:module) or ../../ncs:module[ncs:name='Cisco-IOS-XE-bgp-oper'] or (../../ncs:live-status-protocol[not(ncs:capability)]) or (../../ncs:live-status-protocol/ncs:capability/ncs:module[.='Cisco-IOS-XE-bgp-oper'])";
      description
        "BGP operational state data";
      uses bgp-ios-xe-oper:live_ncs_bgp-state;
    }
  }
  augment "/ncs:devices/ncs:template/ncs:config" {
    // NCS drop config false container 'bgp-state-data'
  }
}
