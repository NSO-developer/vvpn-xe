module Cisco-IOS-XE-bgp {
  // Generated by yanger -t ncs
  tailf:ncs-device-type "netconf";

  namespace "http://cisco.com/ns/yang/Cisco-IOS-XE-bgp";
  prefix ios-bgp;

  import ietf-inet-types {
    prefix inet;
  }
  import Cisco-IOS-XE-types {
    prefix ios-types;
  }
  import Cisco-IOS-XE-features {
    prefix ios-features;
  }
  import Cisco-IOS-XE-interface-common {
    prefix ios-ifc;
  }
  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Border Gateway Protocol (BGP) Yang model.
     Copyright (c) 2017 by Cisco Systems, Inc.
     All rights reserved.";

  revision 2017-04-28 {
    description
      "inet:ipv6-prefix changed to ios-types:ipv6-prefix";
  }
  revision 2017-03-02 {
    description
      "NED extension - add version4 for bgp template peer-session";
  }
  revision 2017-02-08 {
    description
      "NED extension - router bgp address-family options -
                   soo, max paths, import path";
  }
  revision 2017-02-07 {
    description
      "Initial revision";
  }

  grouping ncs_template_address-family-no-vrf-grouping {
    container no-vrf {
      list ipv4 {
        // NCS patched for predictable order
        ordered-by user;
        description
          "Address family";
        key "af-name";
        leaf af-name {
          type string;
        }
        uses ncs_template_bgp-ipv4-af-aggregate-address-grouping;
        uses ncs_template_bgp-address-family-grouping;
      }
      list ipv6 {
        // NCS patched for predictable order
        ordered-by user;
        description
          "Address family";
        key "af-name";
        leaf af-name {
          type string;
        }
        uses ncs_template_bgp-ipv6-af-aggregate-address-grouping;
        uses ncs_template_bgp-address-family-grouping;
      }
      list vpnv4 {
        // NCS patched for predictable order
        ordered-by user;
        description
          "Address family";
        key "af-name";
        leaf af-name {
          type string;
        }
        uses ncs_template_bgp-address-family-grouping;
      }
      list vpnv6 {
        // NCS patched for predictable order
        ordered-by user;
        description
          "Address family";
        key "af-name";
        leaf af-name {
          type string;
        }
        uses ncs_template_bgp-address-family-grouping;
      }
      list nsap {
        // NCS patched for predictable order
        ordered-by user;
        description
          "Address family";
        key "af-name";
        leaf af-name {
          type string;
        }
        uses ncs_template_bgp-address-family-grouping;
      }
      list l2vpn {
        // NCS patched for predictable order
        ordered-by user;
        // NCS drop if-feature statement
        description
          "Address family";
        key "af-name";
        leaf af-name {
          type string;
        }
        uses ncs_template_bgp-address-family-grouping;
      }
      list rtfilter {
        // NCS patched for predictable order
        ordered-by user;
        description
          "Address family";
        key "af-name";
        leaf af-name {
          type string;
        }
        uses ncs_template_bgp-address-family-grouping;
      }
    }
  }

  grouping ncs_template_neighbor-description-grouping {
    leaf description {
      description
        "Neighbor specific description";
      type string;
    }
  }

  grouping ncs_template_neighbor-password-grouping {
    container password {
      description
        "Set a password";
      leaf enctype {
        type string;
      }
      leaf text {
        type string;
      }
    }
  }

  grouping ncs_template_neighbor-peer-group-grouping {
    container peer-group {
      description
        "Member of the peer-group";
      presence "true";
      leaf peer-group-name {
        description
          "WORD;;peer-group name";
        type string;
      }
    }
  }

  grouping ncs_template_neighbor-remote-as-grouping {
    leaf remote-as {
      description
        "Specify a BGP neighbor";
      type string;
    }
  }

  grouping ncs_template_neighbor-update-source-grouping {
    container update-source {
      description
        "Source of routing updates";
      uses ios-ifc:ncs_template_interface-grouping;
    }
  }

  grouping ncs_template_neighbor-version-grouping {
    leaf version {
      description
        "Set the BGP version to match a neighbor";
      type string;
    }
  }

  grouping ncs_template_ip-community-list-standard-grouping {
    container deny {
      description
        "Specify community to reject";
      leaf-list deny-list {
        // NCS patched for predictable order
        ordered-by user;
        type string;
      }
    }
    container permit {
      description
        "Specify community to accept";
      leaf-list permit-list {
        // NCS patched for predictable order
        ordered-by user;
        type string;
      }
    }
  }

  grouping ncs_template_ip-community-list-expanded-grouping {
    container deny {
      description
        "Specify community to reject";
      leaf-list deny-list {
        // NCS patched for predictable order
        ordered-by user;
        type string;
      }
    }
    container permit {
      description
        "Specify community to accept";
      leaf-list permit-list {
        // NCS patched for predictable order
        ordered-by user;
        type string;
      }
    }
  }

  grouping ncs_template_ip-extcommunity-list-standard-grouping {
    container deny {
      description
        "Specify community to reject";
      list rt {
        // NCS patched for predictable order
        ordered-by user;
        description
          "Route Target extended community";
        key "name";
        leaf name {
          type string;
        }
      }
      list soo {
        // NCS patched for predictable order
        ordered-by user;
        description
          "Site-of-Origin extended community";
        key "name";
        leaf name {
          type string;
        }
      }
      list vpn-distinguisher {
        // NCS patched for predictable order
        ordered-by user;
        description
          "VPN Distinguisher extcomm";
        key "name";
        leaf name {
          type string;
        }
      }
    }
    container permit {
      description
        "Specify community to accept";
      list rt {
        // NCS patched for predictable order
        ordered-by user;
        description
          "Route Target extended community";
        key "name";
        leaf name {
          type string;
        }
      }
      list soo {
        // NCS patched for predictable order
        ordered-by user;
        description
          "Site-of-Origin extended community";
        key "name";
        leaf name {
          type string;
        }
      }
      list vpn-distinguisher {
        // NCS patched for predictable order
        ordered-by user;
        description
          "VPN Distinguisher extcomm";
        key "name";
        leaf name {
          type string;
        }
      }
    }
  }

  grouping ncs_template_config-ip-community-list-grouping {
    container community-list {
      description
        "Add a community list entry";
      list number-standard {
        // NCS patched for predictable order
        ordered-by user;
        key "no";
        leaf no {
          type string;
        }
        uses ncs_template_ip-community-list-standard-grouping;
      }
      list number-expanded {
        // NCS patched for predictable order
        ordered-by user;
        key "no";
        leaf no {
          type string;
        }
        uses ncs_template_ip-community-list-expanded-grouping;
      }
      list expanded {
        // NCS patched for predictable order
        ordered-by user;
        description
          "Add an expanded community-list entry";
        key "name";
        leaf name {
          type string;
        }
        uses ncs_template_ip-community-list-expanded-grouping;
      }
      list standard {
        // NCS patched for predictable order
        ordered-by user;
        description
          "Add a standard community-list entry";
        key "name";
        leaf name {
          type string;
        }
        uses ncs_template_ip-community-list-standard-grouping;
      }
    }
  }

  grouping ncs_template_config-ip-extcommunity-list-grouping {
    container extcommunity-list {
      description
        "Extended a community list entry";
      list number-standard {
        // NCS patched for predictable order
        ordered-by user;
        key "no";
        leaf no {
          type string;
        }
        uses ncs_template_ip-extcommunity-list-standard-grouping;
      }
      list number-expanded {
        // NCS patched for predictable order
        ordered-by user;
        key "no";
        leaf no {
          type string;
        }
        uses ncs_template_ip-community-list-expanded-grouping;
      }
      list expanded {
        // NCS patched for predictable order
        ordered-by user;
        description
          "Extended an expanded community-list entry";
        key "name";
        leaf name {
          type string;
        }
        uses ncs_template_ip-community-list-expanded-grouping;
      }
      list standard {
        // NCS patched for predictable order
        ordered-by user;
        description
          "Extended a standard community-list entry";
        key "name";
        leaf name {
          type string;
        }
        uses ncs_template_ip-extcommunity-list-standard-grouping;
      }
    }
  }

  grouping ncs_template_config-ip-as-path-grouping {
    list access-list {
      // NCS patched for predictable order
      ordered-by user;
      description
        "Specify an access list number";
      key "name";
      leaf name {
        type string;
      }
      uses ncs_template_ip-community-list-expanded-grouping;
    }
  }

  grouping ncs_template_max-path-grouping {
    container max-path {
      leaf max {
        type string;
      }
    }
    container external-rtfilter {
      description
        "VPN prefix multipath on external RTFilter peers";
      leaf max {
        type string;
      }
    }
  }

  grouping ncs_template_metric-route-map-grouping {
    leaf metric {
      description
        "Metric for redistributed routes";
      type string;
    }
    leaf route-map {
      description
        "Route map reference";
      type string;
    }
  }

  grouping ncs_template_route-map-metric-grouping {
    leaf route-map {
      description
        "Route map reference";
      type string;
    }
    leaf metric {
      description
        "Metric for redistributed routes";
      type string;
    }
  }

  grouping ncs_template_redistribute-isis-grouping {
    choice osi-ip-choice {
      leaf ip {
        description
          "Redistribution of IP dynamic routes";
        type empty;
      }
      leaf clns {
        description
          "Redistribution of OSI dynamic routes";
        type empty;
      }
    }
    leaf routes {
      type string;
    }
    uses ncs_template_metric-route-map-grouping;
  }

  grouping ncs_template_bgp-ipv4-af-aggregate-address-grouping {
    container aggregate-address {
      description
        "Configure BGP aggregate entries";
      leaf ipv4-address {
        type string;
      }
      leaf ipv4-mask {
        type string;
      }
      leaf advertise-map {
        description
          "Set condition to advertise attribute";
        type string;
      }
      leaf as-set {
        description
          "Generate AS set path information";
        type empty;
      }
      leaf attribute-map {
        type string;
      }
      leaf as-override {
        description
          "Override matching AS-number while sending update";
        type empty;
      }
      leaf route-map {
        type string;
      }
      leaf summary-only {
        description
          "Filter more specific routes from updates";
        type empty;
      }
      leaf suppress-map {
        description
          "Conditionally filter more specific routes from updates";
        type string;
      }
    }
  }

  grouping ncs_template_bgp-ipv6-af-aggregate-address-grouping {
    container aggregate-address {
      description
        "Configure BGP aggregate entries";
      leaf ipv6-address {
        type string;
      }
      leaf advertise-map {
        description
          "Set condition to advertise attribute";
        type string;
      }
      leaf as-set {
        description
          "Generate AS set path information";
        type empty;
      }
      leaf attribute-map {
        type string;
      }
      leaf as-override {
        description
          "Override matching AS-number while sending update";
        type empty;
      }
      leaf route-map {
        type string;
      }
      leaf summary-only {
        description
          "Filter more specific routes from updates";
        type empty;
      }
      leaf suppress-map {
        description
          "Conditionally filter more specific routes from updates";
        type string;
      }
    }
  }

  grouping ncs_template_bgp-address-family-grouping {
    container import {
      description
        "Configure path import";
      container path {
        description
          "Path selection and path limit";
        leaf limit {
          description
            "Per net imported path limit";
          type string;
        }
      }
    }
    container bgp {
      description
        "BGP specific commands";
      leaf router-id {
        description
          "Override configured router identifier (peers will reset)";
        type string;
      }
      leaf always-compare-med {
        description
          "Allow comparing MED from different neighbors";
        type empty;
      }
      leaf aggregate-timer {
        description
          "Timer interval";
        type string;
      }
      container asnotation {
        description
          "Change the default asplain notation";
        leaf dot {
          description
            "asdot notation";
          type empty;
        }
      }
      container nopeerup-delay {
        description
          "Set how long BGP will wait for the first peer to come up before beginning the update delay or graceful restart timers (in seconds)";
        leaf cold-boot {
          description
            "Delay in seconds";
          type string;
        }
        leaf nsf-switchover {
          description
            "Delay in seconds";
          type string;
        }
        leaf post-boot {
          description
            "Delay in seconds";
          type string;
        }
        leaf user-initiated {
          description
            "Delay in seconds";
          type string;
        }
      }
      container recursion {
        description
          "recursion rule for the nexthops";
        leaf host {
          description
            "recursion via host for the nexthops";
          type empty;
        }
      }
      leaf advertise-best-external {
        description
          "Advertise best external path to internal peers";
        type empty;
      }
      container additional-paths {
        description
          "Additional paths in the BGP table";
        leaf install {
          description
            "Additional paths to install into RIB";
          type empty;
        }
        leaf receive {
          description
            "Receive additional paths from neighbors";
          type empty;
        }
        container select {
          description
            "Selection criteria to pick the paths";
          container all {
            description
              "Select all available paths";
            presence "true";
            container best {
              description
                "Select best N paths";
              list range {
                // NCS patched for predictable order
                ordered-by user;
                key "range";
                leaf range {
                  description
                    "Number of best paths in additional paths to be selected";
                  type string;
                }
                leaf group-best {
                  description
                    "Select group-best path";
                  type empty;
                }
              }
            }
            container group-best {
              description
                "Select group-best path";
              presence "true";
              leaf best {
                description
                  "Number of best paths in additional paths to be selected";
                type string;
              }
            }
          }
          container backup {
            description
              "Select backup path";
            presence "true";
            leaf best-external {
              description
                "Select best-external path";
              type empty;
            }
          }
          container best {
            description
              "Select best N paths";
            list range {
              // NCS patched for predictable order
              ordered-by user;
              key "range";
              leaf range {
                description
                  "Number of best paths in additional paths to be selected";
                type string;
              }
              leaf all {
                description
                  "Select all available paths";
                type empty;
              }
              container group-best {
                description
                  "Select group-best path";
                presence "true";
                leaf all {
                  description
                    "Select all available paths";
                  type empty;
                }
              }
            }
          }
          container best-external {
            description
              "Select best-external path";
            presence "true";
            leaf backup {
              description
                "Select backup path";
              type empty;
            }
          }
          container group-best {
            description
              "Select group-best path";
            presence "true";
            leaf all {
              description
                "Select all available paths";
              type empty;
            }
            leaf best {
              description
                "Number of best paths in additional paths to be selected";
              type string;
            }
          }
        }
        container send {
          description
            "Send additional paths to neighbors";
          presence "true";
          leaf receive {
            description
              "Receive additional paths from neighbors";
            type empty;
          }
        }
      }
      container bestpath {
        description
          "Change the default bestpath selection";
        leaf compare-routerid {
          type empty;
        }
        container cost-community {
          description
            "cost community";
          leaf ignore {
            description
              "Ignore cost communities in bestpath selection";
            type empty;
          }
        }
        container igp-metric {
          description
            "igp metric";
          leaf ignore {
            description
              "Ignore igp metric in bestpath selection";
            type empty;
          }
        }
        container med {
          description
            "MED attribute";
          choice med-choice {
            container confed {
              description
                "Compare MED among confederation paths";
              presence "Compare MED among confederation paths";
              leaf missing-at-worst {
                description
                  "Treat missing MED as the least preferred one";
                type empty;
              }
            }
            leaf missing-at-worst {
              description
                "Treat missing MED as the least preferred one";
              type empty;
            }
          }
        }
      }
      container client-to-client {
        description
          "Configure client to client route reflection";
        leaf reflection {
          description
            "reflection of routes allowed";
          type empty;
        }
      }
      leaf cluster-id {
        type string;
      }
      container confederation {
        description
          "AS confederation parameters";
        leaf identifier {
          type string;
        }
        container peers {
          description
            "Peer ASs in BGP confederation";
          leaf-list peers-as {
            // NCS patched for predictable order
            ordered-by user;
            type string;
          }
        }
      }
      container consistency-checker {
        description
          "Consistency-checker";
        container auto-repair {
          description
            "Auto-Repair";
          presence "true";
          leaf interval {
            description
              "Interval (minutes)";
            type string;
          }
        }
        container error-message {
          description
            "Log Error-Msg";
          presence "true";
          leaf interval {
            description
              "Interval (minutes)";
            type string;
          }
        }
      }
      container dampening {
        description
          "Enable route-flap dampening";
        presence "enable bgp route-flap dampening";
        choice dampening-choice {
          leaf route-map {
            description
              "Route-map to specify criteria for dampening";
            type string;
          }
          container dampen {
            leaf half-life-time {
              type string;
            }
            leaf reuse-time {
              type string;
            }
            leaf suppress-time {
              type string;
            }
            leaf max-suppress-time {
              type string;
            }
          }
        }
      }
      container default {
        description
          "Configure BGP defaults";
        choice default-choice {
          leaf ipv4-unicast {
            description
              "Activate ipv4-unicast for a peer by default";
            type string;
          }
          leaf ipv6-nexthop {
            description
              "Default IPv6 nexthop format";
            type empty;
          }
          leaf local-preference {
            description
              "local preference (higher=more preferred)";
            type string;
          }
          leaf route-target {
            description
              "Control behavior based on Route-Target attributes";
            type string;
          }
        }
      }
      leaf deterministic-med {
        description
          "Pick the best-MED path among paths advertised from the neighboring AS";
        type empty;
      }
      leaf dmzlink-bw {
        description
          "Use DMZ Link Bandwidth as weight for BGP multipaths";
        type empty;
      }
      leaf enforce-first-as {
        description
          "Enforce the first AS for EBGP routes(default)";
        type empty;
      }
      leaf enhanced-error {
        description
          "Enabled BGP Enhanced error handling";
        type empty;
      }
      leaf fast-external-fallover {
        description
          "Immediately reset session if a link to a directly connected external peer goes down";
        type string;
      }
      container graceful-restart {
        description
          "Graceful restart capability parameters";
        presence "Graceful restart capability parameters";
        leaf extended {
          type empty;
        }
        leaf restart-time {
          description
            "Set the max time needed to restart and come back up";
          type string;
        }
        leaf stalepath-time {
          description
            "Set the max time to hold onto restarting peer's stale paths";
          type string;
        }
      }
      container ha-mode {
        description
          "Select BGP High Availability mode";
        container sso {
          description
            "BGP High Availability NSR sso mode";
          presence "true";
          leaf prefer {
            description
              "Perfer BGP High Availability NSR sso mode";
            type empty;
          }
        }
      }
      list inject-map {
        // NCS patched for predictable order
        ordered-by user;
        description
          "Routemap which specifies prefixes to inject";
        key "name";
        leaf name {
          type string;
        }
        leaf exist-map {
          description
            "Routemap which specifies exist condition";
          type string;
        }
        leaf copy-attributes {
          description
            "Copy attributes from aggregate";
          type empty;
        }
      }
      leaf log-neighbor-changes {
        description
          "Log neighbor up/down and reset reason";
        type empty;
      }
      leaf maxas-limit {
        description
          "Allow AS-PATH attribute from any neighbor imposing a limit on number of ASes";
        type string;
      }
      leaf maxcommunity-limit {
        description
          "Number of communities in the COMMUNITY attribute";
        type string;
      }
      container route-map {
        description
          "bgp route-map commands";
        leaf priority {
          description
            "Have route-map set commands take priority over BGP commands such ";
          type empty;
        }
      }
      container slow-peer {
        description
          "Configure slow-peer";
        container detection {
          description
            "Slow-peer detection";
          presence "true";
          leaf disable {
            description
              "Disable slow-peer detection";
            type empty;
          }
          leaf threshold {
            description
              "Threshold value (seconds)";
            type string;
          }
        }
        container split-update-group {
          description
            "Configure slow-peer split-update-group";
          container dynamic {
            description
              "Dynamically split the slow peer to slow-update group";
            presence "true";
            leaf permanent {
              description
                "Keep the slow-peer permanently in slow-update group";
              type empty;
            }
          }
        }
      }
      container update-group {
        description
          "Manage peers in bgp update groups";
        container split {
          description
            "Split update groups based on Policy";
          leaf as-override {
            description
              "Keep peers with as-override in different update groups";
            type empty;
          }
        }
      }
      container nexthop {
        description
          "Nexthop tracking commands";
        container trigger {
          description
            "Nexthop triggering";
          leaf delay {
            description
              "Set the delay to tigger nexthop tracking";
            type string;
          }
          leaf enable {
            description
              "Enable nexthop tracking";
            type string;
          }
        }
        leaf route-map {
          description
            "Route map for valid nexthops";
          type string;
        }
      }
      leaf redistribute-internal {
        description
          "Allow redistribution of iBGP into IGPs (dangerous)";
        type empty;
      }
      container regexp {
        description
          "Select regular expression engine";
        leaf deterministic {
          description
            "Enable bounded-execution-time regular expression engine";
          type empty;
        }
      }
      leaf scan-time {
        description
          "Configure background scanner interval";
        type string;
      }
      leaf soft-reconfig-backup {
        description
          "Use soft-reconfiguration inbound only when route-refresh is not negotiated";
        type empty;
      }
      leaf suppress-inactive {
        description
          "Suppress routes that are not in the routing table";
        type empty;
      }
      container transport {
        description
          "Transport options";
        leaf path-mtu-discovery {
          description
            "Use transport path MTU discovery";
          type string;
        }
      }
      leaf update-delay {
        description
          "Set the max initial delay for sending update";
        type string;
      }
    }
    container default-information {
      description
        "Control distribution of default information";
      leaf originate {
        description
          "Distribute a default route";
        type empty;
      }
    }
    leaf default-metric {
      description
        "Set metric of redistributed routes";
      type string;
    }
    container distance {
      description
        "Define an administrative distance";
      container bgp {
        description
          "BGP distance";
        leaf extern-as {
          type string;
        }
        leaf internal-as {
          type string;
        }
        leaf local {
          type string;
        }
      }
      list adm-distance {
        // NCS patched for predictable order
        ordered-by user;
        key "distance srcip wildbits";
        leaf distance {
          type string;
        }
        leaf srcip {
          type string;
        }
        leaf wildbits {
          type string;
        }
        leaf acl {
          type string;
        }
      }
    }
    list distribute-list {
      // NCS patched for predictable order
      ordered-by user;
      description
        "Filter networks in routing updates";
      key "id";
      leaf id {
        type string;
      }
      choice in-out-choice {
        container in {
          presence "enable incoming routing updates";
          description
            "Filter incoming routing updates";
          leaf interface {
            type string;
          }
        }
        container out {
          presence "enable outgoing routing updates";
          description
            "Filter outgoing routing updates";
          leaf interface {
            type string;
          }
        }
      }
    }
    container maximum-paths {
      description
        "Forward packets over multiple paths";
      uses ncs_template_max-path-grouping;
      choice max-path-choice {
        leaf eibgp {
          description
            "Both eBGP and iBGP paths as multipath";
          type string;
        }
        container ibgp {
          description
            "iBGP-multipath";
          choice ibgp-choice {
            leaf unequal-cost {
              description
                "Perform Un-Equal cost multipath selection";
              type string;
            }
            leaf max {
              type string;
            }
          }
        }
      }
    }
    list neighbor {
      // NCS patched for predictable order
      ordered-by user;
      description
        "Specify a neighbor router";
      // NCS drop must statement
      key "id";
      leaf id {
        type string;
      }
      uses ncs_template_neighbor-peer-group-grouping;
      uses ncs_template_neighbor-remote-as-grouping;
      container local-as {
        description
          "Specify a local-as number";
        presence "Specify a local-as number";
        leaf as-no {
          type string;
        }
        leaf no-prepend {
          description
            "Do not prepend local-as to updates from ebgp peers";
          type empty;
        }
        leaf replace-as {
          description
            "Replace real AS with local AS in the EBGP updates";
          type empty;
        }
        leaf dual-as {
          description
            "Accept either real AS or local AS from the ebgp peer";
          type empty;
        }
      }
      leaf activate {
        description
          "Enable the Address Family for this Neighbor";
        type empty;
      }
      container additional-paths {
        leaf disable {
          description
            "Disable additional paths for this neighbor";
          type empty;
        }
        leaf receive {
          description
            "Receive additional paths from neighbors";
          type empty;
        }
        container send {
          description
            "Send additional paths to this neighbor";
          presence "true";
          leaf receive {
            description
              "Receive additional paths from this neighbor";
            type empty;
          }
        }
      }
      container advertise {
        description
          "Advertise to this neighbor";
        container additional-paths {
          description
            "Advertise additional paths";
          container all {
            description
              "Select all available paths";
            presence "true";
            container best {
              description
                "Select best N paths";
              list best-range {
                // NCS patched for predictable order
                ordered-by user;
                key "range";
                leaf range {
                  description
                    "Number of best paths in additional paths to be selected";
                  type string;
                }
                leaf group-best {
                  description
                    "Select group-best paths";
                  type empty;
                }
              }
            }
            container group-best {
              description
                "Select group-best paths";
              presence "true";
              leaf best {
                description
                  "Number of best paths in additional paths to be selected";
                type string;
              }
            }
          }
          container best {
            description
              "Select best N paths";
            list best-range {
              // NCS patched for predictable order
              ordered-by user;
              key "range";
              leaf range {
                description
                  "Number of best paths in additional paths to be selected";
                type string;
              }
              leaf all {
                description
                  "Select all available paths";
                type empty;
              }
              container group-best {
                description
                  "Select group-best paths";
                presence "true";
                leaf all {
                  description
                    "Select all available paths";
                  type empty;
                }
              }
            }
          }
          container group-best {
            description
              "Select group-best paths";
            presence "true";
            leaf all {
              description
                "Select all available paths";
              type empty;
            }
            leaf best {
              description
                "Number of best paths in additional paths to be selected";
              type string;
            }
          }
        }
        leaf best-external {
          description
            "Advertise best-external (at RRs best-internal) path";
          type empty;
        }
        container diverse-path {
          description
            "Advertise diverse path";
          container backup {
            description
              "Diverse path can be backup path";
            presence "true";
            leaf mpath {
              description
                "Diverse path can be multipath";
              type empty;
            }
          }
          leaf mpath {
            description
              "Diverse path can be multipath";
            type empty;
          }
        }
      }
      container advertise-map {
        description
          "specify route-map for conditional advertisement";
        list name {
          // NCS patched for predictable order
          ordered-by user;
          key "word";
          leaf word {
            description
              "advertise route-map name";
            type string;
          }
          leaf exist-map {
            description
              "condition route-map name";
            type string;
          }
          leaf non-exist-map {
            description
              "condition route-map name";
            type string;
          }
        }
      }
      container aigp {
        description
          "Enable a AIGP on neighbor";
        presence "true";
        container send {
          description
            "Cost community or MED carrying AIGP VALUE";
          container cost-community {
            description
              "Cost extended community carrying AIGP Value";
            list cc-range {
              // NCS patched for predictable order
              ordered-by user;
              key "range";
              leaf range {
                description
                  "Community ID";
                type string;
              }
              container poi {
                description
                  "Point of Insertion";
                container igp-cost {
                  description
                    "Point of Insertion After IGP";
                  presence "true";
                  leaf transitive {
                    description
                      "Cost community is Transitive";
                    type empty;
                  }
                }
                container pre-bestpath {
                  description
                    "Point of Insertion At Beginning";
                  presence "true";
                  leaf transitive {
                    description
                      "Cost community is Transitive";
                    type empty;
                  }
                }
              }
            }
          }
          leaf med {
            description
              "Med carrying AIGP Value";
            type empty;
          }
        }
      }
      leaf allow-policy {
        description
          "Enable the policy support for this IBGP Neighbor";
        type empty;
      }
      container announce {
        description
          "Announce RPKI State using an Extended Community";
        container rpki {
          description
            "Announce RPKI information using an Extended Community";
          leaf state {
            description
              "Announce RPKI State information using an Extended Community";
            type empty;
          }
        }
      }
      leaf advertisement-interval {
        description
          "Minimum interval between sending BGP routing updates";
        type string;
      }
      container allowas-in {
        description
          "Accept as-path with my AS present in it";
        presence "accept as-paths";
        leaf as-number {
          type string;
        }
      }
      container as-override {
        description
          "Override matching AS-number while sending update";
        presence "true";
        leaf disable {
          type empty;
        }
      }
      container capability {
        description
          "Advertise capability to the peer";
        container orf {
          description
            "Advertise ORF capability to the peer";
          leaf-list prefix-list {
            // NCS patched for predictable order
            ordered-by user;
            description
              "Advertise prefixlist ORF capability to this neighbor";
            // NCS drop max-elements statement
            type string;
          }
        }
      }
      leaf cluster-id {
        type string;
      }
      container default-originate {
        description
          "Originate default route to this neighbour";
        presence "enable originate default route to this neighbour";
        leaf route-map {
          description
            "Route-map to specify criteria to originate default";
          type string;
        }
      }
      uses ncs_template_neighbor-description-grouping;
      leaf disable-connected-check {
        description
          "One-hop away EBGP peer using loopback address";
        type empty;
      }
      list distribute-list {
        // NCS patched for predictable order
        ordered-by user;
        description
          "Filter updates to/from this neighbor";
        key "inout";
        leaf inout {
          type string;
        }
        leaf accesslist {
          type string;
          // NCS drop mandatory statement
        }
      }
      leaf dmzlink-bw {
        description
          "Propagate the DMZ link bandwidth";
        type empty;
      }
      container ebgp-multihop {
        description
          "Allow EBGP neighbors not on directly connected networks";
        presence "Allow EBGP neighbors not on directly connected networks";
        leaf max-hop {
          type string;
        }
      }
      container fall-over {
        description
          "session fall on peer route lost";
        container bfd {
          description
            "Use BFD to detect failure";
          presence "true";
        }
      }
      list filter-list {
        // NCS patched for predictable order
        ordered-by user;
        description
          "Establish BGP filters";
        key "inout";
        leaf inout {
          type string;
        }
        leaf as-path-list {
          type string;
          // NCS drop mandatory statement
        }
      }
      container inherit {
        description
          "Inherit a template";
        leaf peer-policy {
          description
            "Inherit a peer-policy template";
          type string;
        }
        leaf peer-session {
          description
            "Inherit a peer-session template";
          type string;
        }
      }
      container log-neighbor-changes {
        description
          "Log neighbor up/down and reset reason";
        presence "true";
        leaf disable {
          description
            "disable";
          type empty;
        }
      }
      container maximum-prefix {
        description
          "Maximum number of prefixes accepted from this peer";
        leaf max-prefix-no {
          type string;
        }
        leaf threshold {
          type string;
        }
        leaf restart {
          description
            "Restart bgp connection after limit is exceeded";
          type string;
        }
        leaf warning-only {
          description
            "Only give warning message when limit is exceeded";
          type empty;
        }
      }
      leaf next-hop-self {
        description
          "Disable the next hop calculation for this neighbor";
        type empty;
      }
      leaf next-hop-unchanged {
        description
          "Propagate the iBGP paths's next hop unchanged for this neighbor";
        type empty;
      }
      uses ncs_template_neighbor-password-grouping;
      list prefix-list {
        // NCS patched for predictable order
        ordered-by user;
        description
          "Filter updates to/from this neighbor";
        key "inout";
        leaf inout {
          type string;
        }
        leaf prefix-list-name {
          type string;
          // NCS drop mandatory statement
        }
      }
      container path-attribute {
        description
          "BGP optional attribute filtering";
        container discard {
          description
            "Discard matching path-attribute for this neighbor";
          uses ncs_template_bgp-path-range-grouping;
        }
        container treat-as-withdraw {
          description
            "Treat-as-withdraw matching path-attribute for this neighbor";
          uses ncs_template_bgp-path-range-grouping;
        }
      }
      leaf remove-private-as {
        description
          "Remove private AS number from outbound updates";
        type empty;
      }
      list route-map {
        // NCS patched for predictable order
        ordered-by user;
        description
          "Apply route map to neighbor";
        key "inout";
        leaf inout {
          type string;
        }
        leaf route-map-name {
          type string;
          // NCS drop mandatory statement
        }
      }
      leaf route-reflector-client {
        description
          "Configure a neighbor as Route Reflector client";
        type empty;
      }
      leaf route-reflector-cluster-id {
        type string;
      }
      container send-community {
        description
          "Send Community attribute to this neighbor";
        presence "true";
        leaf send-community-where {
          type string;
        }
      }
      container send-label {
        description
          "Send NLRI + MPLS Label to this peer";
        leaf send-label-explicit {
          type string;
        }
      }
      leaf soo {
        description
          "ASN:nn or IP-address:nn  VPN extended community";
        type string;
      }
      leaf shutdown {
        description
          "Administratively shut down this neighbor";
        type empty;
      }
      leaf soft-reconfiguration {
        description
          "Per neighbor soft reconfiguration";
        type string;
      }
      container slow-peer {
        description
          "Configure slow-peer";
        container detection {
          description
            "Slow-peer detection";
          presence "true";
          leaf threshold {
            description
              "Threshold value (seconds)";
            type string;
          }
        }
        container split-update-group {
          description
            "Configure slow-peer split-update-group";
          container dynamic {
            description
              "Dynamically split the slow peer to slow-update group";
            presence "true";
            leaf permanent {
              description
                "Keep the slow-peer permanently in slow-update group";
              type empty;
            }
          }
        }
      }
      container timers {
        description
          "BGP per neighbor timers";
        leaf keepalive-interval {
          type string;
        }
        leaf holdtime {
          type string;
        }
        leaf minimum-neighbor-hold {
          type string;
        }
      }
      container translate-update {
        description
          "Translate Update to MBGP format";
        container ipv4 {
          description
            "Address Family";
          container multicast {
            description
              "Address Family modifier";
            presence "Address Family modifier";
            leaf unicast {
              description
                "Address Family modifier";
              type empty;
            }
          }
        }
      }
      container transport {
        description
          "Transport options";
        leaf connection-mode {
          description
            "Specify passive or active connection";
          type string;
        }
        leaf multi-session {
          description
            "Use Multi-session for transport";
          type empty;
        }
        container path-mtu-discovery {
          description
            "Use transport path MTU discovery";
          presence "true";
          leaf disable {
            description
              "disable";
            type empty;
          }
        }
      }
      container ttl-security {
        description
          "BGP ttl security check";
        leaf hops {
          description
            "IP hops";
          type string;
        }
      }
      leaf unsuppress-map {
        description
          "Route-map to selectively unsuppress suppressed routes";
        type string;
      }
      uses ncs_template_neighbor-update-source-grouping;
      uses ncs_template_neighbor-version-grouping;
      leaf weight {
        description
          "Set default weight for routes from this neighbor";
        type string;
      }
      container ha-mode {
        description
          "high availability mode";
        container graceful-restart {
          description
            "graceful-restart for this peer";
          presence "true";
          leaf disable {
            description
              "disable graceful-restart";
            type empty;
          }
        }
        container sso {
          description
            "stateful-switchover support for this peer";
          presence "true";
          leaf disable {
            description
              "disable stateful-switchover";
            type empty;
          }
        }
      }
    }
    list network {
      // NCS patched for predictable order
      ordered-by user;
      description
        "Specify a network to announce via BGP";
      key "number";
      leaf number {
        type string;
      }
      leaf backdoor {
        description
          "Specify a BGP backdoor route";
        type empty;
      }
      leaf mask {
        description
          "Network mask";
        type string;
      }
      leaf route-map {
        description
          "Route-map to modify the attributes";
        type string;
      }
    }
    container redistribute {
      description
        "Redistribute information from another routing protocol";
      container application {
        description
          "Application";
        presence "true";
        list name {
          // NCS patched for predictable order
          ordered-by user;
          key "name";
          leaf name {
            description
              "WORD;;Route map name";
            type string;
          }
          uses ncs_template_metric-route-map-grouping;
        }
      }
      container bgp {
        description
          "Border Gateway Protocol (BGP)";
        leaf as-no {
          type string;
        }
        uses ncs_template_metric-route-map-grouping;
      }
      container connected {
        description
          "Connected";
        presence "Connected";
        uses ncs_template_metric-route-map-grouping;
      }
      container dvmrp {
        description
          "Redistribution of DVMRP into BGP IPv4 Multicast";
        presence "Redistribution of DVMRP into BGP IPv4 Multicast";
        uses ncs_template_route-map-metric-grouping;
      }
      container eigrp {
        description
          "Enhanced Interior Gateway Routing Protocol (EIGRP)";
        leaf as-no {
          type string;
        }
        uses ncs_template_metric-route-map-grouping;
      }
      container isis {
        description
          "ISO IS-IS";
        list isis-area {
          // NCS patched for predictable order
          ordered-by user;
          key "name";
          leaf name {
            type string;
          }
          uses ncs_template_redistribute-isis-grouping;
        }
        container default {
          uses ncs_template_redistribute-isis-grouping;
        }
      }
      container lisp {
        description
          "Locator/ID Separation Protocol";
        presence "lisp";
        leaf include-connected {
          type empty;
        }
        uses ncs_template_metric-route-map-grouping;
      }
      container iso-igrp {
        description
          "IGRP for OSI networks";
        list iso-igrp-area {
          // NCS patched for predictable order
          ordered-by user;
          key "name";
          leaf name {
            type string;
          }
          uses ncs_template_route-map-metric-grouping;
        }
        container default {
          uses ncs_template_route-map-metric-grouping;
        }
      }
      container mobile {
        presence "Mobile routes";
        description
          "Mobile routes";
        uses ncs_template_metric-route-map-grouping;
      }
      container odr {
        presence "On Demand stub Routes";
        description
          "On Demand stub Routes";
        uses ncs_template_metric-route-map-grouping;
      }
      list ospf {
        // NCS patched for predictable order
        ordered-by user;
        description
          "Open Shortest Path First (OSPF)";
        key "id";
        leaf id {
          type string;
        }
        list vrf {
          // NCS patched for predictable order
          ordered-by user;
          description
            "VPN Routing/Forwarding Instance";
          key "name";
          leaf name {
            type string;
          }
          container match;
          uses ncs_template_metric-route-map-grouping;
        }
        container non-vrf {
          container match {
            leaf internal {
              description
                "Redistribute OSPF internal routes";
              type empty;
            }
            leaf external {
              description
                "Redistribute OSPF external routes";
              type string;
            }
            leaf external2 {
              description
                "Redistribute OSPF external routes";
              type string;
            }
            leaf nssa-external {
              description
                "Redistribute OSPF NSSA external routes";
              type string;
            }
            uses ncs_template_metric-route-map-grouping;
          }
          uses ncs_template_metric-route-map-grouping;
        }
      }
      container rip {
        presence "Routing Information Protocol (RIP)";
        description
          "Routing Information Protocol (RIP)";
        uses ncs_template_metric-route-map-grouping;
        leaf name {
          description
            "User selected string identifying this process";
          type string;
        }
      }
      container static {
        presence "Static routes";
        description
          "Static routes";
        container clns {
          description
            "Redistribution of OSI dynamic routes";
          presence "true";
          uses ncs_template_route-map-metric-grouping;
        }
        container ip {
          presence "true";
          uses ncs_template_metric-route-map-grouping;
        }
        uses ncs_template_metric-route-map-grouping;
      }
    }
    leaf synchronization {
      description
        "Perform IGP synchronization";
      type empty;
    }
    leaf auto-summary {
      description
        "Enable automatic network number summarization";
      type string;
    }
    container table-map {
      presence "true";
      description
        "Map external entry attributes into routing table";
      leaf name {
        description
          "WORD;;route-map name";
        type string;
      }
      leaf filter {
        type empty;
      }
    }
    container snmp {
      description
        "Modify snmp parameters";
      presence "true";
      container context {
        description
          "Configure a SNMP context";
        list context_word {
          // NCS patched for predictable order
          ordered-by user;
          key "context_word";
          leaf context_word {
            description
              "Context Name";
            type string;
          }
        }
      }
    }
  }

  grouping ncs_template_bgp-path-range-grouping {
    container attibute_type {
      leaf type {
        description
          "path attribute type";
        type string;
      }
      leaf in {
        description
          "Perform inbound path-attribute filtering";
        type empty;
      }
    }
    container range {
      leaf start_value {
        description
          "path attribute range start value";
        type string;
      }
      leaf end_value {
        description
          "path attribute range end value";
        type string;
      }
      leaf in {
        description
          "Perform inbound path-attribute filtering";
        type empty;
      }
    }
  }

  grouping ncs_template_config-bgp-grouping {
    list bgp {
      // NCS patched for predictable order
      ordered-by user;
      description
        "Border Gateway Protocol (BGP)";
      key "id";
      // NCS drop max-elements statement
      leaf id {
        type string;
      }
      uses ncs_template_bgp-address-family-grouping;
      container address-family {
        description
          "Enter Address Family command mode";
        container with-vrf {
          list ipv4 {
            // NCS patched for predictable order
            ordered-by user;
            description
              "Address family";
            key "af-name";
            leaf af-name {
              type string;
            }
            list vrf {
              // NCS patched for predictable order
              ordered-by user;
              key "name";
              leaf name {
                type string;
              }
              uses ncs_template_bgp-ipv4-af-aggregate-address-grouping;
              uses ncs_template_bgp-address-family-grouping;
            }
          }
          list ipv6 {
            // NCS patched for predictable order
            ordered-by user;
            description
              "Address family";
            key "af-name";
            leaf af-name {
              type string;
            }
            list vrf {
              // NCS patched for predictable order
              ordered-by user;
              key "name";
              leaf name {
                type string;
              }
              uses ncs_template_bgp-ipv6-af-aggregate-address-grouping;
              uses ncs_template_bgp-address-family-grouping;
            }
          }
        }
        container no-vrf {
          list ipv4 {
            // NCS patched for predictable order
            ordered-by user;
            description
              "Address family";
            key "af-name";
            leaf af-name {
              type string;
            }
            uses ncs_template_bgp-ipv4-af-aggregate-address-grouping;
            uses ncs_template_bgp-address-family-grouping;
          }
          list ipv6 {
            // NCS patched for predictable order
            ordered-by user;
            description
              "Address family";
            key "af-name";
            leaf af-name {
              type string;
            }
            uses ncs_template_bgp-ipv6-af-aggregate-address-grouping;
            uses ncs_template_bgp-address-family-grouping;
          }
          list vpnv4 {
            // NCS patched for predictable order
            ordered-by user;
            description
              "Address family";
            key "af-name";
            leaf af-name {
              type string;
            }
            uses ncs_template_bgp-address-family-grouping;
          }
          list vpnv6 {
            // NCS patched for predictable order
            ordered-by user;
            description
              "Address family";
            key "af-name";
            leaf af-name {
              type string;
            }
            uses ncs_template_bgp-address-family-grouping;
          }
          list nsap {
            // NCS patched for predictable order
            ordered-by user;
            description
              "Address family";
            key "af-name";
            leaf af-name {
              type string;
            }
            uses ncs_template_bgp-address-family-grouping;
          }
          list l2vpn {
            // NCS patched for predictable order
            ordered-by user;
            // NCS drop if-feature statement
            description
              "Address family";
            key "af-name";
            leaf af-name {
              type string;
            }
            uses ncs_template_bgp-address-family-grouping;
          }
          list rtfilter {
            // NCS patched for predictable order
            ordered-by user;
            description
              "Address family";
            key "af-name";
            leaf af-name {
              type string;
            }
            uses ncs_template_bgp-address-family-grouping;
          }
        }
      }
      container template {
        description
          "Enter template command mode";
        list peer-policy {
          // NCS patched for predictable order
          ordered-by user;
          description
            "Template configuration for policy parameters";
          key "name";
          leaf name {
            type string;
          }
          list route-map {
            // NCS patched for predictable order
            ordered-by user;
            description
              "Apply route map to neighbor";
            key "name";
            leaf name {
              type string;
            }
            leaf in {
              description
                "Apply map to incoming routes";
              type empty;
            }
            leaf out {
              description
                "Apply map to outgong routes";
              type empty;
            }
          }
          list filter-list {
            // NCS patched for predictable order
            ordered-by user;
            description
              "Establish BGP filters";
            key "filter-range";
            leaf filter-range {
              description
                "AS path access list";
              type string;
            }
            leaf in {
              description
                "Filter incoming routes";
              type empty;
            }
            leaf out {
              description
                "Filter outgoing routes";
              type empty;
            }
          }
          container inherit {
            description
              "Inherit a template";
            container peer-policy {
              list template {
                // NCS patched for predictable order
                ordered-by user;
                key "name";
                leaf name {
                  description
                    "Template name";
                  type string;
                }
                leaf range {
                  description
                    "Sequence number";
                  type string;
                }
              }
            }
          }
        }
        list peer-session {
          // NCS patched for predictable order
          ordered-by user;
          description
            "Template configuration for session parameters";
          key "name";
          leaf name {
            type string;
          }
          container ha-mode {
            description
              "high availability mode";
            container graceful-restart {
              description
                "graceful-restart for this peer";
              presence "true";
              leaf disable {
                description
                  "disable graceful-restart";
                type empty;
              }
            }
          }
          container password {
            description
              "Set a password";
            list password-range {
              // NCS patched for predictable order
              ordered-by user;
              key "encruption-type-range";
              leaf encruption-type-range {
                description
                  "Encryption type (0 to disable encryption, 7 for proprietary)";
                type string;
              }
              leaf password {
                description
                  "The password";
                type string;
              }
            }
            leaf password {
              description
                "The password";
              type string;
            }
          }
          leaf remote-as {
            description
              "Specify a BGP neighbor";
            type string;
          }
          container update-source {
            description
              "Source of routing updates";
            uses ios-ifc:ncs_template_interface-grouping;
          }
          leaf version {
            description
              "Set the BGP version to match a neighbor";
            type string;
          }
        }
      }
      container timers {
        description
          "Adjust routing timers";
        container bgp {
          description
            "BGP timers";
          leaf keepalive-interval {
            type string;
          }
          leaf holdtime {
            type string;
          }
          leaf minimum-neighbor-hold {
            type string;
          }
        }
      }
      container scope {
        container global {
          presence "true";
          list neighbor {
            // NCS patched for predictable order
            ordered-by user;
            description
              "Specify a neighbor router";
            // NCS drop must statement
            key "id";
            leaf id {
              type string;
            }
            uses ncs_template_neighbor-peer-group-grouping;
            uses ncs_template_neighbor-remote-as-grouping;
            uses ncs_template_neighbor-description-grouping;
            uses ncs_template_neighbor-password-grouping;
            uses ncs_template_neighbor-update-source-grouping;
            uses ncs_template_neighbor-version-grouping;
          }
          container address-family {
            description
              "Enter Address Family command mode";
            uses ncs_template_address-family-no-vrf-grouping;
          }
        }
        list vrf {
          // NCS patched for predictable order
          ordered-by user;
          key "id";
          leaf id {
            type string;
          }
          list neighbor {
            // NCS patched for predictable order
            ordered-by user;
            description
              "Specify a neighbor router";
            // NCS drop must statement
            key "id";
            leaf id {
              type string;
            }
            uses ncs_template_neighbor-peer-group-grouping;
            uses ncs_template_neighbor-remote-as-grouping;
          }
          container address-family {
            description
              "Enter Address Family command mode";
            uses ncs_template_address-family-no-vrf-grouping;
          }
        }
      }
    }
  }

  grouping ncs_rpc_notif_address-family-no-vrf-grouping {
    container no-vrf {
      list ipv4 {
        description
          "Address family";
        key "af-name";
        leaf af-name {
          type ios-types:bgp_ipv4_af_type;
        }
        uses ncs_rpc_notif_bgp-ipv4-af-aggregate-address-grouping;
        uses ncs_rpc_notif_bgp-address-family-grouping;
      }
      list ipv6 {
        description
          "Address family";
        key "af-name";
        leaf af-name {
          type ios-types:bgp_ipv6_af_type;
        }
        uses ncs_rpc_notif_bgp-ipv6-af-aggregate-address-grouping;
        uses ncs_rpc_notif_bgp-address-family-grouping;
      }
      list vpnv4 {
        description
          "Address family";
        key "af-name";
        leaf af-name {
          type enumeration {
            enum "unicast";
            enum "multicast";
            enum "flowspec";
          }
        }
        uses ncs_rpc_notif_bgp-address-family-grouping;
      }
      list vpnv6 {
        description
          "Address family";
        key "af-name";
        leaf af-name {
          type enumeration {
            enum "unicast";
            enum "multicast";
            enum "flowspec";
          }
        }
        uses ncs_rpc_notif_bgp-address-family-grouping;
      }
      list nsap {
        description
          "Address family";
        key "af-name";
        leaf af-name {
          type enumeration {
            enum "unicast";
          }
        }
        uses ncs_rpc_notif_bgp-address-family-grouping;
      }
      list l2vpn {
        tailf:display-when "not(../ncs:module) or boolean(/ncs:devices/ncs:device[ncs:name=current()/../ncs:name]/capability/feature='ios-features:l2vpn')";
        description
          "Address family";
        key "af-name";
        leaf af-name {
          type enumeration {
            enum "evpn";
            enum "vpls";
          }
        }
        uses ncs_rpc_notif_bgp-address-family-grouping;
      }
      list rtfilter {
        description
          "Address family";
        key "af-name";
        leaf af-name {
          type enumeration {
            enum "unicast";
          }
        }
        uses ncs_rpc_notif_bgp-address-family-grouping;
      }
    }
  }

  grouping ncs_rpc_notif_neighbor-description-grouping {
    leaf description {
      description
        "Neighbor specific description";
      type string;
    }
  }

  grouping ncs_rpc_notif_neighbor-password-grouping {
    container password {
      description
        "Set a password";
      leaf enctype {
        type uint8 {
          range "0..7";
        }
      }
      leaf text {
        type string;
      }
    }
  }

  grouping ncs_rpc_notif_neighbor-peer-group-grouping {
    container peer-group {
      description
        "Member of the peer-group";
      presence "true";
      leaf peer-group-name {
        description
          "WORD;;peer-group name";
        type string;
      }
    }
  }

  grouping ncs_rpc_notif_neighbor-remote-as-grouping {
    leaf remote-as {
      description
        "Specify a BGP neighbor";
      type union {
        type uint32 {
          range "1..4294967295";
        }
        type string;
      }
    }
  }

  grouping ncs_rpc_notif_neighbor-update-source-grouping {
    container update-source {
      description
        "Source of routing updates";
      uses ios-ifc:ncs_rpc_notif_interface-grouping;
    }
  }

  grouping ncs_rpc_notif_neighbor-version-grouping {
    leaf version {
      description
        "Set the BGP version to match a neighbor";
      type uint16 {
        range "4";
      }
    }
  }

  grouping ncs_rpc_notif_ip-community-list-standard-grouping {
    container deny {
      description
        "Specify community to reject";
      leaf-list deny-list {
        type union {
          type ios-types:community-number-type;
          type ios-types:community-well-known-type;
        }
      }
    }
    container permit {
      description
        "Specify community to accept";
      leaf-list permit-list {
        type union {
          type ios-types:community-number-type;
          type ios-types:community-well-known-type;
        }
      }
    }
  }

  grouping ncs_rpc_notif_ip-community-list-expanded-grouping {
    container deny {
      description
        "Specify community to reject";
      leaf-list deny-list {
        ordered-by user;
        type string;
      }
    }
    container permit {
      description
        "Specify community to accept";
      leaf-list permit-list {
        ordered-by user;
        type string;
      }
    }
  }

  grouping ncs_rpc_notif_ip-extcommunity-list-standard-grouping {
    container deny {
      description
        "Specify community to reject";
      list rt {
        description
          "Route Target extended community";
        key "name";
        leaf name {
          type string;
        }
      }
      list soo {
        description
          "Site-of-Origin extended community";
        key "name";
        leaf name {
          type string;
        }
      }
      list vpn-distinguisher {
        description
          "VPN Distinguisher extcomm";
        key "name";
        leaf name {
          type string;
        }
      }
    }
    container permit {
      description
        "Specify community to accept";
      list rt {
        description
          "Route Target extended community";
        key "name";
        leaf name {
          type string;
        }
      }
      list soo {
        description
          "Site-of-Origin extended community";
        key "name";
        leaf name {
          type string;
        }
      }
      list vpn-distinguisher {
        description
          "VPN Distinguisher extcomm";
        key "name";
        leaf name {
          type string;
        }
      }
    }
  }

  grouping ncs_rpc_notif_config-ip-community-list-grouping {
    container community-list {
      description
        "Add a community list entry";
      list number-standard {
        key "no";
        leaf no {
          type uint16 {
            range "1..99";
          }
        }
        uses ncs_rpc_notif_ip-community-list-standard-grouping;
      }
      list number-expanded {
        key "no";
        leaf no {
          type uint16 {
            range "100..500";
          }
        }
        uses ncs_rpc_notif_ip-community-list-expanded-grouping;
      }
      list expanded {
        description
          "Add an expanded community-list entry";
        key "name";
        leaf name {
          type string;
        }
        uses ncs_rpc_notif_ip-community-list-expanded-grouping;
      }
      list standard {
        description
          "Add a standard community-list entry";
        key "name";
        leaf name {
          type string;
        }
        uses ncs_rpc_notif_ip-community-list-standard-grouping;
      }
    }
  }

  grouping ncs_rpc_notif_config-ip-extcommunity-list-grouping {
    container extcommunity-list {
      description
        "Extended a community list entry";
      list number-standard {
        key "no";
        leaf no {
          type uint16 {
            range "1..99";
          }
        }
        uses ncs_rpc_notif_ip-extcommunity-list-standard-grouping;
      }
      list number-expanded {
        key "no";
        leaf no {
          type uint16 {
            range "100..500";
          }
        }
        uses ncs_rpc_notif_ip-community-list-expanded-grouping;
      }
      list expanded {
        description
          "Extended an expanded community-list entry";
        key "name";
        leaf name {
          type string;
        }
        uses ncs_rpc_notif_ip-community-list-expanded-grouping;
      }
      list standard {
        description
          "Extended a standard community-list entry";
        key "name";
        leaf name {
          type string;
        }
        uses ncs_rpc_notif_ip-extcommunity-list-standard-grouping;
      }
    }
  }

  grouping ncs_rpc_notif_config-ip-as-path-grouping {
    list access-list {
      description
        "Specify an access list number";
      key "name";
      leaf name {
        type uint16 {
          range "1..500";
        }
      }
      uses ncs_rpc_notif_ip-community-list-expanded-grouping;
    }
  }

  grouping ncs_rpc_notif_max-path-grouping {
    container max-path {
      leaf max {
        type uint16 {
          range "1..32";
        }
      }
    }
    container external-rtfilter {
      description
        "VPN prefix multipath on external RTFilter peers";
      leaf max {
        type uint16 {
          range "1..32";
        }
      }
    }
  }

  grouping ncs_rpc_notif_metric-route-map-grouping {
    leaf metric {
      description
        "Metric for redistributed routes";
      type uint32 {
        range "0..4294967295";
      }
    }
    leaf route-map {
      description
        "Route map reference";
      type string;
    }
  }

  grouping ncs_rpc_notif_route-map-metric-grouping {
    leaf route-map {
      description
        "Route map reference";
      type string;
    }
    leaf metric {
      description
        "Metric for redistributed routes";
      type uint32 {
        range "0..4294967295";
      }
    }
  }

  grouping ncs_rpc_notif_redistribute-isis-grouping {
    choice osi-ip-choice {
      leaf ip {
        description
          "Redistribution of IP dynamic routes";
        type empty;
      }
      leaf clns {
        description
          "Redistribution of OSI dynamic routes";
        type empty;
      }
    }
    leaf routes {
      type enumeration {
        enum "level-1";
        enum "level-2";
        enum "level-1-2";
      }
    }
    uses ncs_rpc_notif_metric-route-map-grouping;
  }

  grouping ncs_rpc_notif_bgp-ipv4-af-aggregate-address-grouping {
    container aggregate-address {
      description
        "Configure BGP aggregate entries";
      leaf ipv4-address {
        type inet:ipv4-address;
      }
      leaf ipv4-mask {
        type inet:ipv4-address;
      }
      leaf advertise-map {
        description
          "Set condition to advertise attribute";
        type string;
      }
      leaf as-set {
        description
          "Generate AS set path information";
        type empty;
      }
      leaf attribute-map {
        type string;
      }
      leaf as-override {
        description
          "Override matching AS-number while sending update";
        type empty;
      }
      leaf route-map {
        type string;
      }
      leaf summary-only {
        description
          "Filter more specific routes from updates";
        type empty;
      }
      leaf suppress-map {
        description
          "Conditionally filter more specific routes from updates";
        type string;
      }
    }
  }

  grouping ncs_rpc_notif_bgp-ipv6-af-aggregate-address-grouping {
    container aggregate-address {
      description
        "Configure BGP aggregate entries";
      leaf ipv6-address {
        type ios-types:ipv6-prefix;
      }
      leaf advertise-map {
        description
          "Set condition to advertise attribute";
        type string;
      }
      leaf as-set {
        description
          "Generate AS set path information";
        type empty;
      }
      leaf attribute-map {
        type string;
      }
      leaf as-override {
        description
          "Override matching AS-number while sending update";
        type empty;
      }
      leaf route-map {
        type string;
      }
      leaf summary-only {
        description
          "Filter more specific routes from updates";
        type empty;
      }
      leaf suppress-map {
        description
          "Conditionally filter more specific routes from updates";
        type string;
      }
    }
  }

  grouping ncs_rpc_notif_bgp-address-family-grouping {
    container import {
      description
        "Configure path import";
      container path {
        description
          "Path selection and path limit";
        leaf limit {
          description
            "Per net imported path limit";
          type uint8 {
            range "2..255";
          }
        }
      }
    }
    container bgp {
      description
        "BGP specific commands";
      leaf router-id {
        description
          "Override configured router identifier (peers will reset)";
        type inet:ipv4-address;
      }
      leaf always-compare-med {
        description
          "Allow comparing MED from different neighbors";
        type empty;
      }
      leaf aggregate-timer {
        description
          "Timer interval";
        type uint8 {
          range "6..60";
        }
      }
      container asnotation {
        description
          "Change the default asplain notation";
        leaf dot {
          description
            "asdot notation";
          type empty;
        }
      }
      container nopeerup-delay {
        description
          "Set how long BGP will wait for the first peer to come up before beginning the update delay or graceful restart timers (in seconds)";
        leaf cold-boot {
          description
            "Delay in seconds";
          type uint16 {
            range "1..3600";
          }
        }
        leaf nsf-switchover {
          description
            "Delay in seconds";
          type uint16 {
            range "1..3600";
          }
        }
        leaf post-boot {
          description
            "Delay in seconds";
          type uint16 {
            range "1..3600";
          }
        }
        leaf user-initiated {
          description
            "Delay in seconds";
          type uint16 {
            range "1..3600";
          }
        }
      }
      container recursion {
        description
          "recursion rule for the nexthops";
        leaf host {
          description
            "recursion via host for the nexthops";
          type empty;
        }
      }
      leaf advertise-best-external {
        description
          "Advertise best external path to internal peers";
        type empty;
      }
      container additional-paths {
        description
          "Additional paths in the BGP table";
        leaf install {
          description
            "Additional paths to install into RIB";
          type empty;
        }
        leaf receive {
          description
            "Receive additional paths from neighbors";
          type empty;
        }
        container select {
          description
            "Selection criteria to pick the paths";
          container all {
            description
              "Select all available paths";
            presence "true";
            container best {
              description
                "Select best N paths";
              list range {
                key "range";
                leaf range {
                  description
                    "Number of best paths in additional paths to be selected";
                  type uint8 {
                    range "2..3";
                  }
                }
                leaf group-best {
                  description
                    "Select group-best path";
                  type empty;
                }
              }
            }
            container group-best {
              description
                "Select group-best path";
              presence "true";
              leaf best {
                description
                  "Number of best paths in additional paths to be selected";
                type uint8 {
                  range "2..3";
                }
              }
            }
          }
          container backup {
            description
              "Select backup path";
            presence "true";
            leaf best-external {
              description
                "Select best-external path";
              type empty;
            }
          }
          container best {
            description
              "Select best N paths";
            list range {
              key "range";
              leaf range {
                description
                  "Number of best paths in additional paths to be selected";
                type uint8 {
                  range "2..3";
                }
              }
              leaf all {
                description
                  "Select all available paths";
                type empty;
              }
              container group-best {
                description
                  "Select group-best path";
                presence "true";
                leaf all {
                  description
                    "Select all available paths";
                  type empty;
                }
              }
            }
          }
          container best-external {
            description
              "Select best-external path";
            presence "true";
            leaf backup {
              description
                "Select backup path";
              type empty;
            }
          }
          container group-best {
            description
              "Select group-best path";
            presence "true";
            leaf all {
              description
                "Select all available paths";
              type empty;
            }
            leaf best {
              description
                "Number of best paths in additional paths to be selected";
              type uint8 {
                range "2..3";
              }
            }
          }
        }
        container send {
          description
            "Send additional paths to neighbors";
          presence "true";
          leaf receive {
            description
              "Receive additional paths from neighbors";
            type empty;
          }
        }
      }
      container bestpath {
        description
          "Change the default bestpath selection";
        leaf compare-routerid {
          type empty;
        }
        container cost-community {
          description
            "cost community";
          leaf ignore {
            description
              "Ignore cost communities in bestpath selection";
            type empty;
          }
        }
        container igp-metric {
          description
            "igp metric";
          leaf ignore {
            description
              "Ignore igp metric in bestpath selection";
            type empty;
          }
        }
        container med {
          description
            "MED attribute";
          choice med-choice {
            container confed {
              description
                "Compare MED among confederation paths";
              presence "Compare MED among confederation paths";
              leaf missing-at-worst {
                description
                  "Treat missing MED as the least preferred one";
                type empty;
              }
            }
            leaf missing-at-worst {
              description
                "Treat missing MED as the least preferred one";
              type empty;
            }
          }
        }
      }
      container client-to-client {
        description
          "Configure client to client route reflection";
        leaf reflection {
          description
            "reflection of routes allowed";
          type empty;
        }
      }
      leaf cluster-id {
        type union {
          type uint32 {
            range "1..4294967295";
          }
          type inet:ipv4-address;
        }
      }
      container confederation {
        description
          "AS confederation parameters";
        leaf identifier {
          type inet:as-number;
        }
        container peers {
          description
            "Peer ASs in BGP confederation";
          leaf-list peers-as {
            type inet:as-number;
          }
        }
      }
      container consistency-checker {
        description
          "Consistency-checker";
        container auto-repair {
          description
            "Auto-Repair";
          presence "true";
          leaf interval {
            description
              "Interval (minutes)";
            type uint16 {
              range "5..1440";
            }
          }
        }
        container error-message {
          description
            "Log Error-Msg";
          presence "true";
          leaf interval {
            description
              "Interval (minutes)";
            type uint16 {
              range "5..1440";
            }
          }
        }
      }
      container dampening {
        description
          "Enable route-flap dampening";
        presence "enable bgp route-flap dampening";
        choice dampening-choice {
          leaf route-map {
            description
              "Route-map to specify criteria for dampening";
            type string;
          }
          container dampen {
            leaf half-life-time {
              type uint8 {
                range "1 .. 45";
              }
            }
            leaf reuse-time {
              type uint16 {
                range "1 .. 20000";
              }
            }
            leaf suppress-time {
              type uint16 {
                range "1 .. 20000";
              }
            }
            leaf max-suppress-time {
              type uint8 {
                range "1 .. 255";
              }
            }
          }
        }
      }
      container default {
        description
          "Configure BGP defaults";
        choice default-choice {
          leaf ipv4-unicast {
            description
              "Activate ipv4-unicast for a peer by default";
            type boolean;
          }
          leaf ipv6-nexthop {
            description
              "Default IPv6 nexthop format";
            type empty;
          }
          leaf local-preference {
            description
              "local preference (higher=more preferred)";
            type uint32 {
              range "1..4294967295";
            }
          }
          leaf route-target {
            description
              "Control behavior based on Route-Target attributes";
            type enumeration {
              enum "filter";
            }
          }
        }
      }
      leaf deterministic-med {
        description
          "Pick the best-MED path among paths advertised from the neighboring AS";
        type empty;
      }
      leaf dmzlink-bw {
        description
          "Use DMZ Link Bandwidth as weight for BGP multipaths";
        type empty;
      }
      leaf enforce-first-as {
        description
          "Enforce the first AS for EBGP routes(default)";
        type empty;
      }
      leaf enhanced-error {
        description
          "Enabled BGP Enhanced error handling";
        type empty;
      }
      leaf fast-external-fallover {
        description
          "Immediately reset session if a link to a directly connected external peer goes down";
        type boolean;
      }
      container graceful-restart {
        description
          "Graceful restart capability parameters";
        presence "Graceful restart capability parameters";
        leaf extended {
          type empty;
        }
        leaf restart-time {
          description
            "Set the max time needed to restart and come back up";
          type uint16 {
            range "1..3600";
          }
        }
        leaf stalepath-time {
          description
            "Set the max time to hold onto restarting peer's stale paths";
          type uint16 {
            range "1..3600";
          }
        }
      }
      container ha-mode {
        description
          "Select BGP High Availability mode";
        container sso {
          description
            "BGP High Availability NSR sso mode";
          presence "true";
          leaf prefer {
            description
              "Perfer BGP High Availability NSR sso mode";
            type empty;
          }
        }
      }
      list inject-map {
        description
          "Routemap which specifies prefixes to inject";
        key "name";
        leaf name {
          type string;
        }
        leaf exist-map {
          description
            "Routemap which specifies exist condition";
          type string;
        }
        leaf copy-attributes {
          description
            "Copy attributes from aggregate";
          type empty;
        }
      }
      leaf log-neighbor-changes {
        description
          "Log neighbor up/down and reset reason";
        type empty;
      }
      leaf maxas-limit {
        description
          "Allow AS-PATH attribute from any neighbor imposing a limit on number of ASes";
        type uint16 {
          range "1..2000";
        }
      }
      leaf maxcommunity-limit {
        description
          "Number of communities in the COMMUNITY attribute";
        type uint16 {
          range "1..1018";
        }
      }
      container route-map {
        description
          "bgp route-map commands";
        leaf priority {
          description
            "Have route-map set commands take priority over BGP commands such ";
          type empty;
        }
      }
      container slow-peer {
        description
          "Configure slow-peer";
        container detection {
          description
            "Slow-peer detection";
          presence "true";
          leaf disable {
            description
              "Disable slow-peer detection";
            type empty;
          }
          leaf threshold {
            description
              "Threshold value (seconds)";
            type uint16 {
              range "120..3600";
            }
          }
        }
        container split-update-group {
          description
            "Configure slow-peer split-update-group";
          container dynamic {
            description
              "Dynamically split the slow peer to slow-update group";
            presence "true";
            leaf permanent {
              description
                "Keep the slow-peer permanently in slow-update group";
              type empty;
            }
          }
        }
      }
      container update-group {
        description
          "Manage peers in bgp update groups";
        container split {
          description
            "Split update groups based on Policy";
          leaf as-override {
            description
              "Keep peers with as-override in different update groups";
            type empty;
          }
        }
      }
      container nexthop {
        description
          "Nexthop tracking commands";
        container trigger {
          description
            "Nexthop triggering";
          leaf delay {
            description
              "Set the delay to tigger nexthop tracking";
            type uint8 {
              range "0..100";
            }
          }
          leaf enable {
            description
              "Enable nexthop tracking";
            type boolean;
          }
        }
        leaf route-map {
          description
            "Route map for valid nexthops";
          type string;
        }
      }
      leaf redistribute-internal {
        description
          "Allow redistribution of iBGP into IGPs (dangerous)";
        type empty;
      }
      container regexp {
        description
          "Select regular expression engine";
        leaf deterministic {
          description
            "Enable bounded-execution-time regular expression engine";
          type empty;
        }
      }
      leaf scan-time {
        description
          "Configure background scanner interval";
        type uint8 {
          range "5..60";
        }
      }
      leaf soft-reconfig-backup {
        description
          "Use soft-reconfiguration inbound only when route-refresh is not negotiated";
        type empty;
      }
      leaf suppress-inactive {
        description
          "Suppress routes that are not in the routing table";
        type empty;
      }
      container transport {
        description
          "Transport options";
        leaf path-mtu-discovery {
          description
            "Use transport path MTU discovery";
          type boolean;
        }
      }
      leaf update-delay {
        description
          "Set the max initial delay for sending update";
        type uint16 {
          range "1..3600";
        }
      }
    }
    container default-information {
      description
        "Control distribution of default information";
      leaf originate {
        description
          "Distribute a default route";
        type empty;
      }
    }
    leaf default-metric {
      description
        "Set metric of redistributed routes";
      type uint32 {
        range "1..4294967295";
      }
    }
    container distance {
      description
        "Define an administrative distance";
      container bgp {
        description
          "BGP distance";
        leaf extern-as {
          type uint16 {
            range "1..255";
          }
        }
        leaf internal-as {
          type uint16 {
            range "1..255";
          }
        }
        leaf local {
          type uint16 {
            range "1..255";
          }
        }
      }
      list adm-distance {
        key "distance srcip wildbits";
        leaf distance {
          type uint16 {
            range "1..255";
          }
        }
        leaf srcip {
          type inet:ipv4-address;
        }
        leaf wildbits {
          type inet:ipv4-address;
        }
        leaf acl {
          type union {
            type uint16 {
              range "1..99";
            }
            type uint16 {
              range "1300..1999";
            }
            type string {
              pattern '[a-zA-Z].*';
            }
          }
        }
      }
    }
    list distribute-list {
      description
        "Filter networks in routing updates";
      key "id";
      leaf id {
        type ios-types:bgp-distribute-list-type;
      }
      choice in-out-choice {
        container in {
          presence "enable incoming routing updates";
          description
            "Filter incoming routing updates";
          leaf interface {
            type string;
          }
        }
        container out {
          presence "enable outgoing routing updates";
          description
            "Filter outgoing routing updates";
          leaf interface {
            type string;
          }
        }
      }
    }
    container maximum-paths {
      description
        "Forward packets over multiple paths";
      uses ncs_rpc_notif_max-path-grouping;
      choice max-path-choice {
        leaf eibgp {
          description
            "Both eBGP and iBGP paths as multipath";
          type uint16 {
            range "1..32";
          }
        }
        container ibgp {
          description
            "iBGP-multipath";
          choice ibgp-choice {
            leaf unequal-cost {
              description
                "Perform Un-Equal cost multipath selection";
              type uint16 {
                range "1..32";
              }
            }
            leaf max {
              type uint16 {
                range "1..32";
              }
            }
          }
        }
      }
    }
    list neighbor {
      description
        "Specify a neighbor router";
      ordered-by user;
      must "count(*) > 1" {
        tailf:xpath-root 3;
      }
      key "id";
      leaf id {
        type union {
          type string;
          type inet:ipv4-address;
          type inet:ipv6-address;
        }
      }
      uses ncs_rpc_notif_neighbor-peer-group-grouping;
      uses ncs_rpc_notif_neighbor-remote-as-grouping;
      container local-as {
        description
          "Specify a local-as number";
        presence "Specify a local-as number";
        leaf as-no {
          type ios-types:bgp-as-number-type;
        }
        leaf no-prepend {
          description
            "Do not prepend local-as to updates from ebgp peers";
          type empty;
        }
        leaf replace-as {
          description
            "Replace real AS with local AS in the EBGP updates";
          type empty;
        }
        leaf dual-as {
          description
            "Accept either real AS or local AS from the ebgp peer";
          type empty;
        }
      }
      leaf activate {
        description
          "Enable the Address Family for this Neighbor";
        type empty;
      }
      container additional-paths {
        leaf disable {
          description
            "Disable additional paths for this neighbor";
          type empty;
        }
        leaf receive {
          description
            "Receive additional paths from neighbors";
          type empty;
        }
        container send {
          description
            "Send additional paths to this neighbor";
          presence "true";
          leaf receive {
            description
              "Receive additional paths from this neighbor";
            type empty;
          }
        }
      }
      container advertise {
        description
          "Advertise to this neighbor";
        container additional-paths {
          description
            "Advertise additional paths";
          container all {
            description
              "Select all available paths";
            presence "true";
            container best {
              description
                "Select best N paths";
              list best-range {
                key "range";
                leaf range {
                  description
                    "Number of best paths in additional paths to be selected";
                  type uint8 {
                    range "2..3";
                  }
                }
                leaf group-best {
                  description
                    "Select group-best paths";
                  type empty;
                }
              }
            }
            container group-best {
              description
                "Select group-best paths";
              presence "true";
              leaf best {
                description
                  "Number of best paths in additional paths to be selected";
                type uint8 {
                  range "2..3";
                }
              }
            }
          }
          container best {
            description
              "Select best N paths";
            list best-range {
              key "range";
              leaf range {
                description
                  "Number of best paths in additional paths to be selected";
                type uint8 {
                  range "2..3";
                }
              }
              leaf all {
                description
                  "Select all available paths";
                type empty;
              }
              container group-best {
                description
                  "Select group-best paths";
                presence "true";
                leaf all {
                  description
                    "Select all available paths";
                  type empty;
                }
              }
            }
          }
          container group-best {
            description
              "Select group-best paths";
            presence "true";
            leaf all {
              description
                "Select all available paths";
              type empty;
            }
            leaf best {
              description
                "Number of best paths in additional paths to be selected";
              type uint8 {
                range "2..3";
              }
            }
          }
        }
        leaf best-external {
          description
            "Advertise best-external (at RRs best-internal) path";
          type empty;
        }
        container diverse-path {
          description
            "Advertise diverse path";
          container backup {
            description
              "Diverse path can be backup path";
            presence "true";
            leaf mpath {
              description
                "Diverse path can be multipath";
              type empty;
            }
          }
          leaf mpath {
            description
              "Diverse path can be multipath";
            type empty;
          }
        }
      }
      container advertise-map {
        description
          "specify route-map for conditional advertisement";
        list name {
          key "word";
          leaf word {
            description
              "advertise route-map name";
            type string;
          }
          leaf exist-map {
            description
              "condition route-map name";
            type string;
          }
          leaf non-exist-map {
            description
              "condition route-map name";
            type string;
          }
        }
      }
      container aigp {
        description
          "Enable a AIGP on neighbor";
        presence "true";
        container send {
          description
            "Cost community or MED carrying AIGP VALUE";
          container cost-community {
            description
              "Cost extended community carrying AIGP Value";
            list cc-range {
              key "range";
              leaf range {
                description
                  "Community ID";
                type uint8 {
                  range "0..255";
                }
              }
              container poi {
                description
                  "Point of Insertion";
                container igp-cost {
                  description
                    "Point of Insertion After IGP";
                  presence "true";
                  leaf transitive {
                    description
                      "Cost community is Transitive";
                    type empty;
                  }
                }
                container pre-bestpath {
                  description
                    "Point of Insertion At Beginning";
                  presence "true";
                  leaf transitive {
                    description
                      "Cost community is Transitive";
                    type empty;
                  }
                }
              }
            }
          }
          leaf med {
            description
              "Med carrying AIGP Value";
            type empty;
          }
        }
      }
      leaf allow-policy {
        description
          "Enable the policy support for this IBGP Neighbor";
        type empty;
      }
      container announce {
        description
          "Announce RPKI State using an Extended Community";
        container rpki {
          description
            "Announce RPKI information using an Extended Community";
          leaf state {
            description
              "Announce RPKI State information using an Extended Community";
            type empty;
          }
        }
      }
      leaf advertisement-interval {
        description
          "Minimum interval between sending BGP routing updates";
        type uint16 {
          range "0..600";
        }
      }
      container allowas-in {
        description
          "Accept as-path with my AS present in it";
        presence "accept as-paths";
        leaf as-number {
          type uint8 {
            range "1..10";
          }
        }
      }
      container as-override {
        description
          "Override matching AS-number while sending update";
        presence "true";
        leaf disable {
          type empty;
        }
      }
      container capability {
        description
          "Advertise capability to the peer";
        container orf {
          description
            "Advertise ORF capability to the peer";
          leaf-list prefix-list {
            description
              "Advertise prefixlist ORF capability to this neighbor";
            max-elements 1;
            type enumeration {
              enum "both";
              enum "receive";
              enum "send";
            }
          }
        }
      }
      leaf cluster-id {
        type union {
          type uint32 {
            range "1..4294967295";
          }
          type inet:ipv4-address;
        }
      }
      container default-originate {
        description
          "Originate default route to this neighbour";
        presence "enable originate default route to this neighbour";
        leaf route-map {
          description
            "Route-map to specify criteria to originate default";
          type string;
        }
      }
      uses ncs_rpc_notif_neighbor-description-grouping;
      leaf disable-connected-check {
        description
          "One-hop away EBGP peer using loopback address";
        type empty;
      }
      list distribute-list {
        description
          "Filter updates to/from this neighbor";
        key "inout";
        leaf inout {
          type enumeration {
            enum "in";
            enum "out";
          }
        }
        leaf accesslist {
          type ios-types:bgp-distribute-list-type2;
          mandatory true;
        }
      }
      leaf dmzlink-bw {
        description
          "Propagate the DMZ link bandwidth";
        type empty;
      }
      container ebgp-multihop {
        description
          "Allow EBGP neighbors not on directly connected networks";
        presence "Allow EBGP neighbors not on directly connected networks";
        leaf max-hop {
          type uint8 {
            range "1..255";
          }
        }
      }
      container fall-over {
        description
          "session fall on peer route lost";
        container bfd {
          description
            "Use BFD to detect failure";
          presence "true";
        }
      }
      list filter-list {
        description
          "Establish BGP filters";
        key "inout";
        leaf inout {
          type enumeration {
            enum "in";
            enum "out";
          }
        }
        leaf as-path-list {
          type uint16 {
            range "1..500";
          }
          mandatory true;
        }
      }
      container inherit {
        description
          "Inherit a template";
        leaf peer-policy {
          description
            "Inherit a peer-policy template";
          type string;
        }
        leaf peer-session {
          description
            "Inherit a peer-session template";
          type string;
        }
      }
      container log-neighbor-changes {
        description
          "Log neighbor up/down and reset reason";
        presence "true";
        leaf disable {
          description
            "disable";
          type empty;
        }
      }
      container maximum-prefix {
        description
          "Maximum number of prefixes accepted from this peer";
        leaf max-prefix-no {
          type uint32 {
            range "1..2147483647";
          }
        }
        leaf threshold {
          type uint8 {
            range "1..100";
          }
        }
        leaf restart {
          description
            "Restart bgp connection after limit is exceeded";
          type uint16 {
            range "1..65535";
          }
        }
        leaf warning-only {
          description
            "Only give warning message when limit is exceeded";
          type empty;
        }
      }
      leaf next-hop-self {
        description
          "Disable the next hop calculation for this neighbor";
        type empty;
      }
      leaf next-hop-unchanged {
        description
          "Propagate the iBGP paths's next hop unchanged for this neighbor";
        type empty;
      }
      uses ncs_rpc_notif_neighbor-password-grouping;
      list prefix-list {
        description
          "Filter updates to/from this neighbor";
        key "inout";
        leaf inout {
          type enumeration {
            enum "in";
            enum "out";
          }
        }
        leaf prefix-list-name {
          type string;
          mandatory true;
        }
      }
      container path-attribute {
        description
          "BGP optional attribute filtering";
        container discard {
          description
            "Discard matching path-attribute for this neighbor";
          uses ncs_rpc_notif_bgp-path-range-grouping;
        }
        container treat-as-withdraw {
          description
            "Treat-as-withdraw matching path-attribute for this neighbor";
          uses ncs_rpc_notif_bgp-path-range-grouping;
        }
      }
      leaf remove-private-as {
        description
          "Remove private AS number from outbound updates";
        type empty;
      }
      list route-map {
        description
          "Apply route map to neighbor";
        key "inout";
        leaf inout {
          type enumeration {
            enum "in";
            enum "out";
          }
        }
        leaf route-map-name {
          type string;
          mandatory true;
        }
      }
      leaf route-reflector-client {
        description
          "Configure a neighbor as Route Reflector client";
        type empty;
      }
      leaf route-reflector-cluster-id {
        type union {
          type uint32 {
            range "1..4294967295";
          }
          type inet:ipv4-address;
        }
      }
      container send-community {
        description
          "Send Community attribute to this neighbor";
        presence "true";
        leaf send-community-where {
          type enumeration {
            enum "both";
            enum "extended";
            enum "standard";
          }
        }
      }
      container send-label {
        description
          "Send NLRI + MPLS Label to this peer";
        leaf send-label-explicit {
          type enumeration {
            enum "explicit-null";
          }
        }
      }
      leaf soo {
        description
          "ASN:nn or IP-address:nn  VPN extended community";
        type string;
      }
      leaf shutdown {
        description
          "Administratively shut down this neighbor";
        type empty;
      }
      leaf soft-reconfiguration {
        description
          "Per neighbor soft reconfiguration";
        type enumeration {
          enum "inbound";
        }
      }
      container slow-peer {
        description
          "Configure slow-peer";
        container detection {
          description
            "Slow-peer detection";
          presence "true";
          leaf threshold {
            description
              "Threshold value (seconds)";
            type uint16 {
              range "120..3600";
            }
          }
        }
        container split-update-group {
          description
            "Configure slow-peer split-update-group";
          container dynamic {
            description
              "Dynamically split the slow peer to slow-update group";
            presence "true";
            leaf permanent {
              description
                "Keep the slow-peer permanently in slow-update group";
              type empty;
            }
          }
        }
      }
      container timers {
        description
          "BGP per neighbor timers";
        leaf keepalive-interval {
          type uint16 {
            range "0..65535";
          }
        }
        leaf holdtime {
          type uint16 {
            range "0..65535";
          }
        }
        leaf minimum-neighbor-hold {
          type uint16 {
            range "0..65535";
          }
        }
      }
      container translate-update {
        description
          "Translate Update to MBGP format";
        container ipv4 {
          description
            "Address Family";
          container multicast {
            description
              "Address Family modifier";
            presence "Address Family modifier";
            leaf unicast {
              description
                "Address Family modifier";
              type empty;
            }
          }
        }
      }
      container transport {
        description
          "Transport options";
        leaf connection-mode {
          description
            "Specify passive or active connection";
          type enumeration {
            enum "active";
            enum "passive";
          }
        }
        leaf multi-session {
          description
            "Use Multi-session for transport";
          type empty;
        }
        container path-mtu-discovery {
          description
            "Use transport path MTU discovery";
          presence "true";
          leaf disable {
            description
              "disable";
            type empty;
          }
        }
      }
      container ttl-security {
        description
          "BGP ttl security check";
        leaf hops {
          description
            "IP hops";
          type uint8 {
            range "1..254";
          }
        }
      }
      leaf unsuppress-map {
        description
          "Route-map to selectively unsuppress suppressed routes";
        type string;
      }
      uses ncs_rpc_notif_neighbor-update-source-grouping;
      uses ncs_rpc_notif_neighbor-version-grouping;
      leaf weight {
        description
          "Set default weight for routes from this neighbor";
        type uint16 {
          range "0..65535";
        }
      }
      container ha-mode {
        description
          "high availability mode";
        container graceful-restart {
          description
            "graceful-restart for this peer";
          presence "true";
          leaf disable {
            description
              "disable graceful-restart";
            type empty;
          }
        }
        container sso {
          description
            "stateful-switchover support for this peer";
          presence "true";
          leaf disable {
            description
              "disable stateful-switchover";
            type empty;
          }
        }
      }
    }
    list network {
      description
        "Specify a network to announce via BGP";
      key "number";
      leaf number {
        type union {
          type inet:ipv4-address;
          type ios-types:ipv6-prefix;
        }
      }
      leaf backdoor {
        description
          "Specify a BGP backdoor route";
        type empty;
      }
      leaf mask {
        description
          "Network mask";
        type inet:ipv4-address;
      }
      leaf route-map {
        description
          "Route-map to modify the attributes";
        type string;
      }
    }
    container redistribute {
      description
        "Redistribute information from another routing protocol";
      container application {
        description
          "Application";
        presence "true";
        list name {
          key "name";
          leaf name {
            description
              "WORD;;Route map name";
            type string;
          }
          uses ncs_rpc_notif_metric-route-map-grouping;
        }
      }
      container bgp {
        description
          "Border Gateway Protocol (BGP)";
        leaf as-no {
          type ios-types:bgp-as-number-type;
        }
        uses ncs_rpc_notif_metric-route-map-grouping;
      }
      container connected {
        description
          "Connected";
        presence "Connected";
        uses ncs_rpc_notif_metric-route-map-grouping;
      }
      container dvmrp {
        description
          "Redistribution of DVMRP into BGP IPv4 Multicast";
        presence "Redistribution of DVMRP into BGP IPv4 Multicast";
        uses ncs_rpc_notif_route-map-metric-grouping;
      }
      container eigrp {
        description
          "Enhanced Interior Gateway Routing Protocol (EIGRP)";
        leaf as-no {
          type uint16 {
            range "1..65535";
          }
        }
        uses ncs_rpc_notif_metric-route-map-grouping;
      }
      container isis {
        description
          "ISO IS-IS";
        list isis-area {
          key "name";
          leaf name {
            type string;
          }
          uses ncs_rpc_notif_redistribute-isis-grouping;
        }
        container default {
          uses ncs_rpc_notif_redistribute-isis-grouping;
        }
      }
      container lisp {
        description
          "Locator/ID Separation Protocol";
        presence "lisp";
        leaf include-connected {
          type empty;
        }
        uses ncs_rpc_notif_metric-route-map-grouping;
      }
      container iso-igrp {
        description
          "IGRP for OSI networks";
        list iso-igrp-area {
          key "name";
          leaf name {
            type string;
          }
          uses ncs_rpc_notif_route-map-metric-grouping;
        }
        container default {
          uses ncs_rpc_notif_route-map-metric-grouping;
        }
      }
      container mobile {
        presence "Mobile routes";
        description
          "Mobile routes";
        uses ncs_rpc_notif_metric-route-map-grouping;
      }
      container odr {
        presence "On Demand stub Routes";
        description
          "On Demand stub Routes";
        uses ncs_rpc_notif_metric-route-map-grouping;
      }
      list ospf {
        description
          "Open Shortest Path First (OSPF)";
        key "id";
        leaf id {
          type uint16 {
            range "1..65535";
          }
        }
        list vrf {
          description
            "VPN Routing/Forwarding Instance";
          key "name";
          leaf name {
            type string;
          }
          container match;
          uses ncs_rpc_notif_metric-route-map-grouping;
        }
        container non-vrf {
          container match {
            leaf internal {
              description
                "Redistribute OSPF internal routes";
              type empty;
            }
            leaf external {
              description
                "Redistribute OSPF external routes";
              type ios-types:redist-ospf-external-type;
            }
            leaf external2 {
              description
                "Redistribute OSPF external routes";
              type ios-types:redist-ospf-external-type;
            }
            leaf nssa-external {
              description
                "Redistribute OSPF NSSA external routes";
              type ios-types:redist-ospf-external-type;
            }
            uses ncs_rpc_notif_metric-route-map-grouping;
          }
          uses ncs_rpc_notif_metric-route-map-grouping;
        }
      }
      container rip {
        presence "Routing Information Protocol (RIP)";
        description
          "Routing Information Protocol (RIP)";
        uses ncs_rpc_notif_metric-route-map-grouping;
        leaf name {
          description
            "User selected string identifying this process";
          type string;
        }
      }
      container static {
        presence "Static routes";
        description
          "Static routes";
        container clns {
          description
            "Redistribution of OSI dynamic routes";
          presence "true";
          uses ncs_rpc_notif_route-map-metric-grouping;
        }
        container ip {
          presence "true";
          uses ncs_rpc_notif_metric-route-map-grouping;
        }
        uses ncs_rpc_notif_metric-route-map-grouping;
      }
    }
    leaf synchronization {
      description
        "Perform IGP synchronization";
      type empty;
    }
    leaf auto-summary {
      description
        "Enable automatic network number summarization";
      type boolean;
    }
    container table-map {
      presence "true";
      description
        "Map external entry attributes into routing table";
      leaf name {
        description
          "WORD;;route-map name";
        type string;
      }
      leaf filter {
        type empty;
      }
    }
    container snmp {
      description
        "Modify snmp parameters";
      presence "true";
      container context {
        description
          "Configure a SNMP context";
        list context_word {
          key "context_word";
          leaf context_word {
            description
              "Context Name";
            type string;
          }
        }
      }
    }
  }

  grouping ncs_rpc_notif_bgp-path-range-grouping {
    container attibute_type {
      leaf type {
        description
          "path attribute type";
        type uint8 {
          range "1..255";
        }
      }
      leaf in {
        description
          "Perform inbound path-attribute filtering";
        type empty;
      }
    }
    container range {
      leaf start_value {
        description
          "path attribute range start value";
        type uint8 {
          range "1..255";
        }
      }
      leaf end_value {
        description
          "path attribute range end value";
        type uint8 {
          range "1..255";
        }
      }
      leaf in {
        description
          "Perform inbound path-attribute filtering";
        type empty;
      }
    }
  }

  grouping ncs_rpc_notif_config-bgp-grouping {
    list bgp {
      description
        "Border Gateway Protocol (BGP)";
      key "id";
      max-elements 1;
      leaf id {
        type ios-types:bgp-as-number-type;
      }
      uses ncs_rpc_notif_bgp-address-family-grouping;
      container address-family {
        description
          "Enter Address Family command mode";
        container with-vrf {
          list ipv4 {
            description
              "Address family";
            key "af-name";
            leaf af-name {
              type ios-types:bgp_ipv4_af_type;
            }
            list vrf {
              key "name";
              leaf name {
                type string;
              }
              uses ncs_rpc_notif_bgp-ipv4-af-aggregate-address-grouping;
              uses ncs_rpc_notif_bgp-address-family-grouping;
            }
          }
          list ipv6 {
            description
              "Address family";
            key "af-name";
            leaf af-name {
              type ios-types:bgp_ipv6_af_type;
            }
            list vrf {
              key "name";
              leaf name {
                type string;
              }
              uses ncs_rpc_notif_bgp-ipv6-af-aggregate-address-grouping;
              uses ncs_rpc_notif_bgp-address-family-grouping;
            }
          }
        }
        container no-vrf {
          list ipv4 {
            description
              "Address family";
            key "af-name";
            leaf af-name {
              type ios-types:bgp_ipv4_af_type;
            }
            uses ncs_rpc_notif_bgp-ipv4-af-aggregate-address-grouping;
            uses ncs_rpc_notif_bgp-address-family-grouping;
          }
          list ipv6 {
            description
              "Address family";
            key "af-name";
            leaf af-name {
              type ios-types:bgp_ipv6_af_type;
            }
            uses ncs_rpc_notif_bgp-ipv6-af-aggregate-address-grouping;
            uses ncs_rpc_notif_bgp-address-family-grouping;
          }
          list vpnv4 {
            description
              "Address family";
            key "af-name";
            leaf af-name {
              type enumeration {
                enum "unicast";
                enum "multicast";
                enum "flowspec";
              }
            }
            uses ncs_rpc_notif_bgp-address-family-grouping;
          }
          list vpnv6 {
            description
              "Address family";
            key "af-name";
            leaf af-name {
              type enumeration {
                enum "unicast";
                enum "multicast";
                enum "flowspec";
              }
            }
            uses ncs_rpc_notif_bgp-address-family-grouping;
          }
          list nsap {
            description
              "Address family";
            key "af-name";
            leaf af-name {
              type enumeration {
                enum "unicast";
              }
            }
            uses ncs_rpc_notif_bgp-address-family-grouping;
          }
          list l2vpn {
            tailf:display-when "not(../../../ncs:module) or boolean(/ncs:devices/ncs:device[ncs:name=current()/../../../ncs:name]/capability/feature='ios-features:l2vpn')";
            description
              "Address family";
            key "af-name";
            leaf af-name {
              type enumeration {
                enum "evpn";
                enum "vpls";
              }
            }
            uses ncs_rpc_notif_bgp-address-family-grouping;
          }
          list rtfilter {
            description
              "Address family";
            key "af-name";
            leaf af-name {
              type enumeration {
                enum "unicast";
              }
            }
            uses ncs_rpc_notif_bgp-address-family-grouping;
          }
        }
      }
      container template {
        description
          "Enter template command mode";
        list peer-policy {
          description
            "Template configuration for policy parameters";
          key "name";
          leaf name {
            type string;
          }
          list route-map {
            description
              "Apply route map to neighbor";
            key "name";
            leaf name {
              type string;
            }
            leaf in {
              description
                "Apply map to incoming routes";
              type empty;
            }
            leaf out {
              description
                "Apply map to outgong routes";
              type empty;
            }
          }
          list filter-list {
            description
              "Establish BGP filters";
            key "filter-range";
            leaf filter-range {
              description
                "AS path access list";
              type uint16 {
                range "1..500";
              }
            }
            leaf in {
              description
                "Filter incoming routes";
              type empty;
            }
            leaf out {
              description
                "Filter outgoing routes";
              type empty;
            }
          }
          container inherit {
            description
              "Inherit a template";
            container peer-policy {
              list template {
                key "name";
                leaf name {
                  description
                    "Template name";
                  type string;
                }
                leaf range {
                  description
                    "Sequence number";
                  type uint16 {
                    range "1..65535";
                  }
                }
              }
            }
          }
        }
        list peer-session {
          description
            "Template configuration for session parameters";
          key "name";
          leaf name {
            type string;
          }
          container ha-mode {
            description
              "high availability mode";
            container graceful-restart {
              description
                "graceful-restart for this peer";
              presence "true";
              leaf disable {
                description
                  "disable graceful-restart";
                type empty;
              }
            }
          }
          container password {
            description
              "Set a password";
            list password-range {
              key "encruption-type-range";
              leaf encruption-type-range {
                description
                  "Encryption type (0 to disable encryption, 7 for proprietary)";
                type uint8 {
                  range "0..7";
                }
              }
              leaf password {
                description
                  "The password";
                type string;
              }
            }
            leaf password {
              description
                "The password";
              type string;
            }
          }
          leaf remote-as {
            description
              "Specify a BGP neighbor";
            type ios-types:bgp-as-number-type;
          }
          container update-source {
            description
              "Source of routing updates";
            uses ios-ifc:ncs_rpc_notif_interface-grouping;
          }
          leaf version {
            description
              "Set the BGP version to match a neighbor";
            type uint8 {
              range "4";
            }
          }
        }
      }
      container timers {
        description
          "Adjust routing timers";
        container bgp {
          description
            "BGP timers";
          leaf keepalive-interval {
            type uint16 {
              range "0..65535";
            }
          }
          leaf holdtime {
            type uint16 {
              range "0..65535";
            }
          }
          leaf minimum-neighbor-hold {
            type uint16 {
              range "0..65535";
            }
          }
        }
      }
      container scope {
        container global {
          presence "true";
          list neighbor {
            description
              "Specify a neighbor router";
            ordered-by user;
            must "count(*) > 1" {
              tailf:xpath-root 3;
            }
            key "id";
            leaf id {
              type union {
                type string;
                type inet:ipv4-address;
                type inet:ipv6-address;
              }
            }
            uses ncs_rpc_notif_neighbor-peer-group-grouping;
            uses ncs_rpc_notif_neighbor-remote-as-grouping;
            uses ncs_rpc_notif_neighbor-description-grouping;
            uses ncs_rpc_notif_neighbor-password-grouping;
            uses ncs_rpc_notif_neighbor-update-source-grouping;
            uses ncs_rpc_notif_neighbor-version-grouping;
          }
          container address-family {
            description
              "Enter Address Family command mode";
            uses ncs_rpc_notif_address-family-no-vrf-grouping;
          }
        }
        list vrf {
          key "id";
          leaf id {
            type union {
              type string;
              type inet:ipv4-address;
              type inet:ipv6-address;
            }
          }
          list neighbor {
            description
              "Specify a neighbor router";
            ordered-by user;
            must "count(*) > 1" {
              tailf:xpath-root 3;
            }
            key "id";
            leaf id {
              type union {
                type string;
                type inet:ipv4-address;
                type inet:ipv6-address;
              }
            }
            uses ncs_rpc_notif_neighbor-peer-group-grouping;
            uses ncs_rpc_notif_neighbor-remote-as-grouping;
          }
          container address-family {
            description
              "Enter Address Family command mode";
            uses ncs_rpc_notif_address-family-no-vrf-grouping;
          }
        }
      }
    }
  }

  grouping live_ncs_address-family-no-vrf-grouping {
    container no-vrf {
      list ipv4 {
        description
          "Address family";
        key "af-name";
        leaf af-name {
          type ios-types:bgp_ipv4_af_type;
        }
        uses live_ncs_bgp-ipv4-af-aggregate-address-grouping;
        uses live_ncs_bgp-address-family-grouping;
      }
      list ipv6 {
        description
          "Address family";
        key "af-name";
        leaf af-name {
          type ios-types:bgp_ipv6_af_type;
        }
        uses live_ncs_bgp-ipv6-af-aggregate-address-grouping;
        uses live_ncs_bgp-address-family-grouping;
      }
      list vpnv4 {
        description
          "Address family";
        key "af-name";
        leaf af-name {
          type enumeration {
            enum "unicast";
            enum "multicast";
            enum "flowspec";
          }
        }
        uses live_ncs_bgp-address-family-grouping;
      }
      list vpnv6 {
        description
          "Address family";
        key "af-name";
        leaf af-name {
          type enumeration {
            enum "unicast";
            enum "multicast";
            enum "flowspec";
          }
        }
        uses live_ncs_bgp-address-family-grouping;
      }
      list nsap {
        description
          "Address family";
        key "af-name";
        leaf af-name {
          type enumeration {
            enum "unicast";
          }
        }
        uses live_ncs_bgp-address-family-grouping;
      }
      list l2vpn {
        // NCS drop if-feature statement
        description
          "Address family";
        key "af-name";
        leaf af-name {
          type enumeration {
            enum "evpn";
            enum "vpls";
          }
        }
        uses live_ncs_bgp-address-family-grouping;
      }
      list rtfilter {
        description
          "Address family";
        key "af-name";
        leaf af-name {
          type enumeration {
            enum "unicast";
          }
        }
        uses live_ncs_bgp-address-family-grouping;
      }
    }
  }

  grouping live_ncs_neighbor-description-grouping {
    leaf description {
      description
        "Neighbor specific description";
      type string;
    }
  }

  grouping live_ncs_neighbor-password-grouping {
    container password {
      description
        "Set a password";
      leaf enctype {
        type uint8 {
          range "0..7";
        }
      }
      leaf text {
        type string;
      }
    }
  }

  grouping live_ncs_neighbor-peer-group-grouping {
    container peer-group {
      description
        "Member of the peer-group";
      presence "true";
      leaf peer-group-name {
        description
          "WORD;;peer-group name";
        type string;
      }
    }
  }

  grouping live_ncs_neighbor-remote-as-grouping {
    leaf remote-as {
      description
        "Specify a BGP neighbor";
      type union {
        type uint32 {
          range "1..4294967295";
        }
        type string;
      }
    }
  }

  grouping live_ncs_neighbor-update-source-grouping {
    container update-source {
      description
        "Source of routing updates";
      uses ios-ifc:live_ncs_interface-grouping;
    }
  }

  grouping live_ncs_neighbor-version-grouping {
    leaf version {
      description
        "Set the BGP version to match a neighbor";
      type uint16 {
        range "4";
      }
    }
  }

  grouping live_ncs_ip-community-list-standard-grouping {
    container deny {
      description
        "Specify community to reject";
      leaf-list deny-list {
        type union {
          type ios-types:community-number-type;
          type ios-types:community-well-known-type;
        }
      }
    }
    container permit {
      description
        "Specify community to accept";
      leaf-list permit-list {
        type union {
          type ios-types:community-number-type;
          type ios-types:community-well-known-type;
        }
      }
    }
  }

  grouping live_ncs_ip-community-list-expanded-grouping {
    container deny {
      description
        "Specify community to reject";
      leaf-list deny-list {
        ordered-by user;
        type string;
      }
    }
    container permit {
      description
        "Specify community to accept";
      leaf-list permit-list {
        ordered-by user;
        type string;
      }
    }
  }

  grouping live_ncs_ip-extcommunity-list-standard-grouping {
    container deny {
      description
        "Specify community to reject";
      list rt {
        description
          "Route Target extended community";
        key "name";
        leaf name {
          type string;
        }
      }
      list soo {
        description
          "Site-of-Origin extended community";
        key "name";
        leaf name {
          type string;
        }
      }
      list vpn-distinguisher {
        description
          "VPN Distinguisher extcomm";
        key "name";
        leaf name {
          type string;
        }
      }
    }
    container permit {
      description
        "Specify community to accept";
      list rt {
        description
          "Route Target extended community";
        key "name";
        leaf name {
          type string;
        }
      }
      list soo {
        description
          "Site-of-Origin extended community";
        key "name";
        leaf name {
          type string;
        }
      }
      list vpn-distinguisher {
        description
          "VPN Distinguisher extcomm";
        key "name";
        leaf name {
          type string;
        }
      }
    }
  }

  grouping live_ncs_config-ip-community-list-grouping {
    container community-list {
      description
        "Add a community list entry";
      list number-standard {
        key "no";
        leaf no {
          type uint16 {
            range "1..99";
          }
        }
        uses live_ncs_ip-community-list-standard-grouping;
      }
      list number-expanded {
        key "no";
        leaf no {
          type uint16 {
            range "100..500";
          }
        }
        uses live_ncs_ip-community-list-expanded-grouping;
      }
      list expanded {
        description
          "Add an expanded community-list entry";
        key "name";
        leaf name {
          type string;
        }
        uses live_ncs_ip-community-list-expanded-grouping;
      }
      list standard {
        description
          "Add a standard community-list entry";
        key "name";
        leaf name {
          type string;
        }
        uses live_ncs_ip-community-list-standard-grouping;
      }
    }
  }

  grouping live_ncs_config-ip-extcommunity-list-grouping {
    container extcommunity-list {
      description
        "Extended a community list entry";
      list number-standard {
        key "no";
        leaf no {
          type uint16 {
            range "1..99";
          }
        }
        uses live_ncs_ip-extcommunity-list-standard-grouping;
      }
      list number-expanded {
        key "no";
        leaf no {
          type uint16 {
            range "100..500";
          }
        }
        uses live_ncs_ip-community-list-expanded-grouping;
      }
      list expanded {
        description
          "Extended an expanded community-list entry";
        key "name";
        leaf name {
          type string;
        }
        uses live_ncs_ip-community-list-expanded-grouping;
      }
      list standard {
        description
          "Extended a standard community-list entry";
        key "name";
        leaf name {
          type string;
        }
        uses live_ncs_ip-extcommunity-list-standard-grouping;
      }
    }
  }

  grouping live_ncs_config-ip-as-path-grouping {
    list access-list {
      description
        "Specify an access list number";
      key "name";
      leaf name {
        type uint16 {
          range "1..500";
        }
      }
      uses live_ncs_ip-community-list-expanded-grouping;
    }
  }

  grouping live_ncs_max-path-grouping {
    container max-path {
      leaf max {
        type uint16 {
          range "1..32";
        }
      }
    }
    container external-rtfilter {
      description
        "VPN prefix multipath on external RTFilter peers";
      leaf max {
        type uint16 {
          range "1..32";
        }
      }
    }
  }

  grouping live_ncs_metric-route-map-grouping {
    leaf metric {
      description
        "Metric for redistributed routes";
      type uint32 {
        range "0..4294967295";
      }
    }
    leaf route-map {
      description
        "Route map reference";
      type string;
    }
  }

  grouping live_ncs_route-map-metric-grouping {
    leaf route-map {
      description
        "Route map reference";
      type string;
    }
    leaf metric {
      description
        "Metric for redistributed routes";
      type uint32 {
        range "0..4294967295";
      }
    }
  }

  grouping live_ncs_redistribute-isis-grouping {
    choice osi-ip-choice {
      leaf ip {
        description
          "Redistribution of IP dynamic routes";
        type empty;
      }
      leaf clns {
        description
          "Redistribution of OSI dynamic routes";
        type empty;
      }
    }
    leaf routes {
      type enumeration {
        enum "level-1";
        enum "level-2";
        enum "level-1-2";
      }
    }
    uses live_ncs_metric-route-map-grouping;
  }

  grouping live_ncs_bgp-ipv4-af-aggregate-address-grouping {
    container aggregate-address {
      description
        "Configure BGP aggregate entries";
      leaf ipv4-address {
        type inet:ipv4-address;
      }
      leaf ipv4-mask {
        type inet:ipv4-address;
      }
      leaf advertise-map {
        description
          "Set condition to advertise attribute";
        type string;
      }
      leaf as-set {
        description
          "Generate AS set path information";
        type empty;
      }
      leaf attribute-map {
        type string;
      }
      leaf as-override {
        description
          "Override matching AS-number while sending update";
        type empty;
      }
      leaf route-map {
        type string;
      }
      leaf summary-only {
        description
          "Filter more specific routes from updates";
        type empty;
      }
      leaf suppress-map {
        description
          "Conditionally filter more specific routes from updates";
        type string;
      }
    }
  }

  grouping live_ncs_bgp-ipv6-af-aggregate-address-grouping {
    container aggregate-address {
      description
        "Configure BGP aggregate entries";
      leaf ipv6-address {
        type ios-types:ipv6-prefix;
      }
      leaf advertise-map {
        description
          "Set condition to advertise attribute";
        type string;
      }
      leaf as-set {
        description
          "Generate AS set path information";
        type empty;
      }
      leaf attribute-map {
        type string;
      }
      leaf as-override {
        description
          "Override matching AS-number while sending update";
        type empty;
      }
      leaf route-map {
        type string;
      }
      leaf summary-only {
        description
          "Filter more specific routes from updates";
        type empty;
      }
      leaf suppress-map {
        description
          "Conditionally filter more specific routes from updates";
        type string;
      }
    }
  }

  grouping live_ncs_bgp-address-family-grouping {
    container import {
      description
        "Configure path import";
      container path {
        description
          "Path selection and path limit";
        leaf limit {
          description
            "Per net imported path limit";
          type uint8 {
            range "2..255";
          }
        }
      }
    }
    container bgp {
      description
        "BGP specific commands";
      leaf router-id {
        description
          "Override configured router identifier (peers will reset)";
        type inet:ipv4-address;
      }
      leaf always-compare-med {
        description
          "Allow comparing MED from different neighbors";
        type empty;
      }
      leaf aggregate-timer {
        description
          "Timer interval";
        type uint8 {
          range "6..60";
        }
      }
      container asnotation {
        description
          "Change the default asplain notation";
        leaf dot {
          description
            "asdot notation";
          type empty;
        }
      }
      container nopeerup-delay {
        description
          "Set how long BGP will wait for the first peer to come up before beginning the update delay or graceful restart timers (in seconds)";
        leaf cold-boot {
          description
            "Delay in seconds";
          type uint16 {
            range "1..3600";
          }
        }
        leaf nsf-switchover {
          description
            "Delay in seconds";
          type uint16 {
            range "1..3600";
          }
        }
        leaf post-boot {
          description
            "Delay in seconds";
          type uint16 {
            range "1..3600";
          }
        }
        leaf user-initiated {
          description
            "Delay in seconds";
          type uint16 {
            range "1..3600";
          }
        }
      }
      container recursion {
        description
          "recursion rule for the nexthops";
        leaf host {
          description
            "recursion via host for the nexthops";
          type empty;
        }
      }
      leaf advertise-best-external {
        description
          "Advertise best external path to internal peers";
        type empty;
      }
      container additional-paths {
        description
          "Additional paths in the BGP table";
        leaf install {
          description
            "Additional paths to install into RIB";
          type empty;
        }
        leaf receive {
          description
            "Receive additional paths from neighbors";
          type empty;
        }
        container select {
          description
            "Selection criteria to pick the paths";
          container all {
            description
              "Select all available paths";
            presence "true";
            container best {
              description
                "Select best N paths";
              list range {
                key "range";
                leaf range {
                  description
                    "Number of best paths in additional paths to be selected";
                  type uint8 {
                    range "2..3";
                  }
                }
                leaf group-best {
                  description
                    "Select group-best path";
                  type empty;
                }
              }
            }
            container group-best {
              description
                "Select group-best path";
              presence "true";
              leaf best {
                description
                  "Number of best paths in additional paths to be selected";
                type uint8 {
                  range "2..3";
                }
              }
            }
          }
          container backup {
            description
              "Select backup path";
            presence "true";
            leaf best-external {
              description
                "Select best-external path";
              type empty;
            }
          }
          container best {
            description
              "Select best N paths";
            list range {
              key "range";
              leaf range {
                description
                  "Number of best paths in additional paths to be selected";
                type uint8 {
                  range "2..3";
                }
              }
              leaf all {
                description
                  "Select all available paths";
                type empty;
              }
              container group-best {
                description
                  "Select group-best path";
                presence "true";
                leaf all {
                  description
                    "Select all available paths";
                  type empty;
                }
              }
            }
          }
          container best-external {
            description
              "Select best-external path";
            presence "true";
            leaf backup {
              description
                "Select backup path";
              type empty;
            }
          }
          container group-best {
            description
              "Select group-best path";
            presence "true";
            leaf all {
              description
                "Select all available paths";
              type empty;
            }
            leaf best {
              description
                "Number of best paths in additional paths to be selected";
              type uint8 {
                range "2..3";
              }
            }
          }
        }
        container send {
          description
            "Send additional paths to neighbors";
          presence "true";
          leaf receive {
            description
              "Receive additional paths from neighbors";
            type empty;
          }
        }
      }
      container bestpath {
        description
          "Change the default bestpath selection";
        leaf compare-routerid {
          type empty;
        }
        container cost-community {
          description
            "cost community";
          leaf ignore {
            description
              "Ignore cost communities in bestpath selection";
            type empty;
          }
        }
        container igp-metric {
          description
            "igp metric";
          leaf ignore {
            description
              "Ignore igp metric in bestpath selection";
            type empty;
          }
        }
        container med {
          description
            "MED attribute";
          choice med-choice {
            container confed {
              description
                "Compare MED among confederation paths";
              presence "Compare MED among confederation paths";
              leaf missing-at-worst {
                description
                  "Treat missing MED as the least preferred one";
                type empty;
              }
            }
            leaf missing-at-worst {
              description
                "Treat missing MED as the least preferred one";
              type empty;
            }
          }
        }
      }
      container client-to-client {
        description
          "Configure client to client route reflection";
        leaf reflection {
          description
            "reflection of routes allowed";
          type empty;
        }
      }
      leaf cluster-id {
        type union {
          type uint32 {
            range "1..4294967295";
          }
          type inet:ipv4-address;
        }
      }
      container confederation {
        description
          "AS confederation parameters";
        leaf identifier {
          type inet:as-number;
        }
        container peers {
          description
            "Peer ASs in BGP confederation";
          leaf-list peers-as {
            type inet:as-number;
          }
        }
      }
      container consistency-checker {
        description
          "Consistency-checker";
        container auto-repair {
          description
            "Auto-Repair";
          presence "true";
          leaf interval {
            description
              "Interval (minutes)";
            type uint16 {
              range "5..1440";
            }
          }
        }
        container error-message {
          description
            "Log Error-Msg";
          presence "true";
          leaf interval {
            description
              "Interval (minutes)";
            type uint16 {
              range "5..1440";
            }
          }
        }
      }
      container dampening {
        description
          "Enable route-flap dampening";
        presence "enable bgp route-flap dampening";
        choice dampening-choice {
          leaf route-map {
            description
              "Route-map to specify criteria for dampening";
            type string;
          }
          container dampen {
            leaf half-life-time {
              type uint8 {
                range "1 .. 45";
              }
            }
            leaf reuse-time {
              type uint16 {
                range "1 .. 20000";
              }
            }
            leaf suppress-time {
              type uint16 {
                range "1 .. 20000";
              }
            }
            leaf max-suppress-time {
              type uint8 {
                range "1 .. 255";
              }
            }
          }
        }
      }
      container default {
        description
          "Configure BGP defaults";
        choice default-choice {
          leaf ipv4-unicast {
            description
              "Activate ipv4-unicast for a peer by default";
            type boolean;
          }
          leaf ipv6-nexthop {
            description
              "Default IPv6 nexthop format";
            type empty;
          }
          leaf local-preference {
            description
              "local preference (higher=more preferred)";
            type uint32 {
              range "1..4294967295";
            }
          }
          leaf route-target {
            description
              "Control behavior based on Route-Target attributes";
            type enumeration {
              enum "filter";
            }
          }
        }
      }
      leaf deterministic-med {
        description
          "Pick the best-MED path among paths advertised from the neighboring AS";
        type empty;
      }
      leaf dmzlink-bw {
        description
          "Use DMZ Link Bandwidth as weight for BGP multipaths";
        type empty;
      }
      leaf enforce-first-as {
        description
          "Enforce the first AS for EBGP routes(default)";
        type empty;
      }
      leaf enhanced-error {
        description
          "Enabled BGP Enhanced error handling";
        type empty;
      }
      leaf fast-external-fallover {
        description
          "Immediately reset session if a link to a directly connected external peer goes down";
        type boolean;
      }
      container graceful-restart {
        description
          "Graceful restart capability parameters";
        presence "Graceful restart capability parameters";
        leaf extended {
          type empty;
        }
        leaf restart-time {
          description
            "Set the max time needed to restart and come back up";
          type uint16 {
            range "1..3600";
          }
        }
        leaf stalepath-time {
          description
            "Set the max time to hold onto restarting peer's stale paths";
          type uint16 {
            range "1..3600";
          }
        }
      }
      container ha-mode {
        description
          "Select BGP High Availability mode";
        container sso {
          description
            "BGP High Availability NSR sso mode";
          presence "true";
          leaf prefer {
            description
              "Perfer BGP High Availability NSR sso mode";
            type empty;
          }
        }
      }
      list inject-map {
        description
          "Routemap which specifies prefixes to inject";
        key "name";
        leaf name {
          type string;
        }
        leaf exist-map {
          description
            "Routemap which specifies exist condition";
          type string;
        }
        leaf copy-attributes {
          description
            "Copy attributes from aggregate";
          type empty;
        }
      }
      leaf log-neighbor-changes {
        description
          "Log neighbor up/down and reset reason";
        type empty;
      }
      leaf maxas-limit {
        description
          "Allow AS-PATH attribute from any neighbor imposing a limit on number of ASes";
        type uint16 {
          range "1..2000";
        }
      }
      leaf maxcommunity-limit {
        description
          "Number of communities in the COMMUNITY attribute";
        type uint16 {
          range "1..1018";
        }
      }
      container route-map {
        description
          "bgp route-map commands";
        leaf priority {
          description
            "Have route-map set commands take priority over BGP commands such ";
          type empty;
        }
      }
      container slow-peer {
        description
          "Configure slow-peer";
        container detection {
          description
            "Slow-peer detection";
          presence "true";
          leaf disable {
            description
              "Disable slow-peer detection";
            type empty;
          }
          leaf threshold {
            description
              "Threshold value (seconds)";
            type uint16 {
              range "120..3600";
            }
          }
        }
        container split-update-group {
          description
            "Configure slow-peer split-update-group";
          container dynamic {
            description
              "Dynamically split the slow peer to slow-update group";
            presence "true";
            leaf permanent {
              description
                "Keep the slow-peer permanently in slow-update group";
              type empty;
            }
          }
        }
      }
      container update-group {
        description
          "Manage peers in bgp update groups";
        container split {
          description
            "Split update groups based on Policy";
          leaf as-override {
            description
              "Keep peers with as-override in different update groups";
            type empty;
          }
        }
      }
      container nexthop {
        description
          "Nexthop tracking commands";
        container trigger {
          description
            "Nexthop triggering";
          leaf delay {
            description
              "Set the delay to tigger nexthop tracking";
            type uint8 {
              range "0..100";
            }
          }
          leaf enable {
            description
              "Enable nexthop tracking";
            type boolean;
          }
        }
        leaf route-map {
          description
            "Route map for valid nexthops";
          type string;
        }
      }
      leaf redistribute-internal {
        description
          "Allow redistribution of iBGP into IGPs (dangerous)";
        type empty;
      }
      container regexp {
        description
          "Select regular expression engine";
        leaf deterministic {
          description
            "Enable bounded-execution-time regular expression engine";
          type empty;
        }
      }
      leaf scan-time {
        description
          "Configure background scanner interval";
        type uint8 {
          range "5..60";
        }
      }
      leaf soft-reconfig-backup {
        description
          "Use soft-reconfiguration inbound only when route-refresh is not negotiated";
        type empty;
      }
      leaf suppress-inactive {
        description
          "Suppress routes that are not in the routing table";
        type empty;
      }
      container transport {
        description
          "Transport options";
        leaf path-mtu-discovery {
          description
            "Use transport path MTU discovery";
          type boolean;
        }
      }
      leaf update-delay {
        description
          "Set the max initial delay for sending update";
        type uint16 {
          range "1..3600";
        }
      }
    }
    container default-information {
      description
        "Control distribution of default information";
      leaf originate {
        description
          "Distribute a default route";
        type empty;
      }
    }
    leaf default-metric {
      description
        "Set metric of redistributed routes";
      type uint32 {
        range "1..4294967295";
      }
    }
    container distance {
      description
        "Define an administrative distance";
      container bgp {
        description
          "BGP distance";
        leaf extern-as {
          type uint16 {
            range "1..255";
          }
        }
        leaf internal-as {
          type uint16 {
            range "1..255";
          }
        }
        leaf local {
          type uint16 {
            range "1..255";
          }
        }
      }
      list adm-distance {
        key "distance srcip wildbits";
        leaf distance {
          type uint16 {
            range "1..255";
          }
        }
        leaf srcip {
          type inet:ipv4-address;
        }
        leaf wildbits {
          type inet:ipv4-address;
        }
        leaf acl {
          type union {
            type uint16 {
              range "1..99";
            }
            type uint16 {
              range "1300..1999";
            }
            type string {
              pattern '[a-zA-Z].*';
            }
          }
        }
      }
    }
    list distribute-list {
      description
        "Filter networks in routing updates";
      key "id";
      leaf id {
        type ios-types:bgp-distribute-list-type;
      }
      choice in-out-choice {
        container in {
          presence "enable incoming routing updates";
          description
            "Filter incoming routing updates";
          leaf interface {
            type string;
          }
        }
        container out {
          presence "enable outgoing routing updates";
          description
            "Filter outgoing routing updates";
          leaf interface {
            type string;
          }
        }
      }
    }
    container maximum-paths {
      description
        "Forward packets over multiple paths";
      uses live_ncs_max-path-grouping;
      choice max-path-choice {
        leaf eibgp {
          description
            "Both eBGP and iBGP paths as multipath";
          type uint16 {
            range "1..32";
          }
        }
        container ibgp {
          description
            "iBGP-multipath";
          choice ibgp-choice {
            leaf unequal-cost {
              description
                "Perform Un-Equal cost multipath selection";
              type uint16 {
                range "1..32";
              }
            }
            leaf max {
              type uint16 {
                range "1..32";
              }
            }
          }
        }
      }
    }
    list neighbor {
      description
        "Specify a neighbor router";
      ordered-by user;
      // NCS drop must statement
      key "id";
      leaf id {
        type union {
          type string;
          type inet:ipv4-address;
          type inet:ipv6-address;
        }
      }
      uses live_ncs_neighbor-peer-group-grouping;
      uses live_ncs_neighbor-remote-as-grouping;
      container local-as {
        description
          "Specify a local-as number";
        presence "Specify a local-as number";
        leaf as-no {
          type ios-types:bgp-as-number-type;
        }
        leaf no-prepend {
          description
            "Do not prepend local-as to updates from ebgp peers";
          type empty;
        }
        leaf replace-as {
          description
            "Replace real AS with local AS in the EBGP updates";
          type empty;
        }
        leaf dual-as {
          description
            "Accept either real AS or local AS from the ebgp peer";
          type empty;
        }
      }
      leaf activate {
        description
          "Enable the Address Family for this Neighbor";
        type empty;
      }
      container additional-paths {
        leaf disable {
          description
            "Disable additional paths for this neighbor";
          type empty;
        }
        leaf receive {
          description
            "Receive additional paths from neighbors";
          type empty;
        }
        container send {
          description
            "Send additional paths to this neighbor";
          presence "true";
          leaf receive {
            description
              "Receive additional paths from this neighbor";
            type empty;
          }
        }
      }
      container advertise {
        description
          "Advertise to this neighbor";
        container additional-paths {
          description
            "Advertise additional paths";
          container all {
            description
              "Select all available paths";
            presence "true";
            container best {
              description
                "Select best N paths";
              list best-range {
                key "range";
                leaf range {
                  description
                    "Number of best paths in additional paths to be selected";
                  type uint8 {
                    range "2..3";
                  }
                }
                leaf group-best {
                  description
                    "Select group-best paths";
                  type empty;
                }
              }
            }
            container group-best {
              description
                "Select group-best paths";
              presence "true";
              leaf best {
                description
                  "Number of best paths in additional paths to be selected";
                type uint8 {
                  range "2..3";
                }
              }
            }
          }
          container best {
            description
              "Select best N paths";
            list best-range {
              key "range";
              leaf range {
                description
                  "Number of best paths in additional paths to be selected";
                type uint8 {
                  range "2..3";
                }
              }
              leaf all {
                description
                  "Select all available paths";
                type empty;
              }
              container group-best {
                description
                  "Select group-best paths";
                presence "true";
                leaf all {
                  description
                    "Select all available paths";
                  type empty;
                }
              }
            }
          }
          container group-best {
            description
              "Select group-best paths";
            presence "true";
            leaf all {
              description
                "Select all available paths";
              type empty;
            }
            leaf best {
              description
                "Number of best paths in additional paths to be selected";
              type uint8 {
                range "2..3";
              }
            }
          }
        }
        leaf best-external {
          description
            "Advertise best-external (at RRs best-internal) path";
          type empty;
        }
        container diverse-path {
          description
            "Advertise diverse path";
          container backup {
            description
              "Diverse path can be backup path";
            presence "true";
            leaf mpath {
              description
                "Diverse path can be multipath";
              type empty;
            }
          }
          leaf mpath {
            description
              "Diverse path can be multipath";
            type empty;
          }
        }
      }
      container advertise-map {
        description
          "specify route-map for conditional advertisement";
        list name {
          key "word";
          leaf word {
            description
              "advertise route-map name";
            type string;
          }
          leaf exist-map {
            description
              "condition route-map name";
            type string;
          }
          leaf non-exist-map {
            description
              "condition route-map name";
            type string;
          }
        }
      }
      container aigp {
        description
          "Enable a AIGP on neighbor";
        presence "true";
        container send {
          description
            "Cost community or MED carrying AIGP VALUE";
          container cost-community {
            description
              "Cost extended community carrying AIGP Value";
            list cc-range {
              key "range";
              leaf range {
                description
                  "Community ID";
                type uint8 {
                  range "0..255";
                }
              }
              container poi {
                description
                  "Point of Insertion";
                container igp-cost {
                  description
                    "Point of Insertion After IGP";
                  presence "true";
                  leaf transitive {
                    description
                      "Cost community is Transitive";
                    type empty;
                  }
                }
                container pre-bestpath {
                  description
                    "Point of Insertion At Beginning";
                  presence "true";
                  leaf transitive {
                    description
                      "Cost community is Transitive";
                    type empty;
                  }
                }
              }
            }
          }
          leaf med {
            description
              "Med carrying AIGP Value";
            type empty;
          }
        }
      }
      leaf allow-policy {
        description
          "Enable the policy support for this IBGP Neighbor";
        type empty;
      }
      container announce {
        description
          "Announce RPKI State using an Extended Community";
        container rpki {
          description
            "Announce RPKI information using an Extended Community";
          leaf state {
            description
              "Announce RPKI State information using an Extended Community";
            type empty;
          }
        }
      }
      leaf advertisement-interval {
        description
          "Minimum interval between sending BGP routing updates";
        type uint16 {
          range "0..600";
        }
      }
      container allowas-in {
        description
          "Accept as-path with my AS present in it";
        presence "accept as-paths";
        leaf as-number {
          type uint8 {
            range "1..10";
          }
        }
      }
      container as-override {
        description
          "Override matching AS-number while sending update";
        presence "true";
        leaf disable {
          type empty;
        }
      }
      container capability {
        description
          "Advertise capability to the peer";
        container orf {
          description
            "Advertise ORF capability to the peer";
          leaf-list prefix-list {
            description
              "Advertise prefixlist ORF capability to this neighbor";
            // NCS drop max-elements statement
            type enumeration {
              enum "both";
              enum "receive";
              enum "send";
            }
          }
        }
      }
      leaf cluster-id {
        type union {
          type uint32 {
            range "1..4294967295";
          }
          type inet:ipv4-address;
        }
      }
      container default-originate {
        description
          "Originate default route to this neighbour";
        presence "enable originate default route to this neighbour";
        leaf route-map {
          description
            "Route-map to specify criteria to originate default";
          type string;
        }
      }
      uses live_ncs_neighbor-description-grouping;
      leaf disable-connected-check {
        description
          "One-hop away EBGP peer using loopback address";
        type empty;
      }
      list distribute-list {
        description
          "Filter updates to/from this neighbor";
        key "inout";
        leaf inout {
          type enumeration {
            enum "in";
            enum "out";
          }
        }
        leaf accesslist {
          type ios-types:bgp-distribute-list-type2;
          // NCS drop mandatory statement
        }
      }
      leaf dmzlink-bw {
        description
          "Propagate the DMZ link bandwidth";
        type empty;
      }
      container ebgp-multihop {
        description
          "Allow EBGP neighbors not on directly connected networks";
        presence "Allow EBGP neighbors not on directly connected networks";
        leaf max-hop {
          type uint8 {
            range "1..255";
          }
        }
      }
      container fall-over {
        description
          "session fall on peer route lost";
        container bfd {
          description
            "Use BFD to detect failure";
          presence "true";
        }
      }
      list filter-list {
        description
          "Establish BGP filters";
        key "inout";
        leaf inout {
          type enumeration {
            enum "in";
            enum "out";
          }
        }
        leaf as-path-list {
          type uint16 {
            range "1..500";
          }
          // NCS drop mandatory statement
        }
      }
      container inherit {
        description
          "Inherit a template";
        leaf peer-policy {
          description
            "Inherit a peer-policy template";
          type string;
        }
        leaf peer-session {
          description
            "Inherit a peer-session template";
          type string;
        }
      }
      container log-neighbor-changes {
        description
          "Log neighbor up/down and reset reason";
        presence "true";
        leaf disable {
          description
            "disable";
          type empty;
        }
      }
      container maximum-prefix {
        description
          "Maximum number of prefixes accepted from this peer";
        leaf max-prefix-no {
          type uint32 {
            range "1..2147483647";
          }
        }
        leaf threshold {
          type uint8 {
            range "1..100";
          }
        }
        leaf restart {
          description
            "Restart bgp connection after limit is exceeded";
          type uint16 {
            range "1..65535";
          }
        }
        leaf warning-only {
          description
            "Only give warning message when limit is exceeded";
          type empty;
        }
      }
      leaf next-hop-self {
        description
          "Disable the next hop calculation for this neighbor";
        type empty;
      }
      leaf next-hop-unchanged {
        description
          "Propagate the iBGP paths's next hop unchanged for this neighbor";
        type empty;
      }
      uses live_ncs_neighbor-password-grouping;
      list prefix-list {
        description
          "Filter updates to/from this neighbor";
        key "inout";
        leaf inout {
          type enumeration {
            enum "in";
            enum "out";
          }
        }
        leaf prefix-list-name {
          type string;
          // NCS drop mandatory statement
        }
      }
      container path-attribute {
        description
          "BGP optional attribute filtering";
        container discard {
          description
            "Discard matching path-attribute for this neighbor";
          uses live_ncs_bgp-path-range-grouping;
        }
        container treat-as-withdraw {
          description
            "Treat-as-withdraw matching path-attribute for this neighbor";
          uses live_ncs_bgp-path-range-grouping;
        }
      }
      leaf remove-private-as {
        description
          "Remove private AS number from outbound updates";
        type empty;
      }
      list route-map {
        description
          "Apply route map to neighbor";
        key "inout";
        leaf inout {
          type enumeration {
            enum "in";
            enum "out";
          }
        }
        leaf route-map-name {
          type string;
          // NCS drop mandatory statement
        }
      }
      leaf route-reflector-client {
        description
          "Configure a neighbor as Route Reflector client";
        type empty;
      }
      leaf route-reflector-cluster-id {
        type union {
          type uint32 {
            range "1..4294967295";
          }
          type inet:ipv4-address;
        }
      }
      container send-community {
        description
          "Send Community attribute to this neighbor";
        presence "true";
        leaf send-community-where {
          type enumeration {
            enum "both";
            enum "extended";
            enum "standard";
          }
        }
      }
      container send-label {
        description
          "Send NLRI + MPLS Label to this peer";
        leaf send-label-explicit {
          type enumeration {
            enum "explicit-null";
          }
        }
      }
      leaf soo {
        description
          "ASN:nn or IP-address:nn  VPN extended community";
        type string;
      }
      leaf shutdown {
        description
          "Administratively shut down this neighbor";
        type empty;
      }
      leaf soft-reconfiguration {
        description
          "Per neighbor soft reconfiguration";
        type enumeration {
          enum "inbound";
        }
      }
      container slow-peer {
        description
          "Configure slow-peer";
        container detection {
          description
            "Slow-peer detection";
          presence "true";
          leaf threshold {
            description
              "Threshold value (seconds)";
            type uint16 {
              range "120..3600";
            }
          }
        }
        container split-update-group {
          description
            "Configure slow-peer split-update-group";
          container dynamic {
            description
              "Dynamically split the slow peer to slow-update group";
            presence "true";
            leaf permanent {
              description
                "Keep the slow-peer permanently in slow-update group";
              type empty;
            }
          }
        }
      }
      container timers {
        description
          "BGP per neighbor timers";
        leaf keepalive-interval {
          type uint16 {
            range "0..65535";
          }
        }
        leaf holdtime {
          type uint16 {
            range "0..65535";
          }
        }
        leaf minimum-neighbor-hold {
          type uint16 {
            range "0..65535";
          }
        }
      }
      container translate-update {
        description
          "Translate Update to MBGP format";
        container ipv4 {
          description
            "Address Family";
          container multicast {
            description
              "Address Family modifier";
            presence "Address Family modifier";
            leaf unicast {
              description
                "Address Family modifier";
              type empty;
            }
          }
        }
      }
      container transport {
        description
          "Transport options";
        leaf connection-mode {
          description
            "Specify passive or active connection";
          type enumeration {
            enum "active";
            enum "passive";
          }
        }
        leaf multi-session {
          description
            "Use Multi-session for transport";
          type empty;
        }
        container path-mtu-discovery {
          description
            "Use transport path MTU discovery";
          presence "true";
          leaf disable {
            description
              "disable";
            type empty;
          }
        }
      }
      container ttl-security {
        description
          "BGP ttl security check";
        leaf hops {
          description
            "IP hops";
          type uint8 {
            range "1..254";
          }
        }
      }
      leaf unsuppress-map {
        description
          "Route-map to selectively unsuppress suppressed routes";
        type string;
      }
      uses live_ncs_neighbor-update-source-grouping;
      uses live_ncs_neighbor-version-grouping;
      leaf weight {
        description
          "Set default weight for routes from this neighbor";
        type uint16 {
          range "0..65535";
        }
      }
      container ha-mode {
        description
          "high availability mode";
        container graceful-restart {
          description
            "graceful-restart for this peer";
          presence "true";
          leaf disable {
            description
              "disable graceful-restart";
            type empty;
          }
        }
        container sso {
          description
            "stateful-switchover support for this peer";
          presence "true";
          leaf disable {
            description
              "disable stateful-switchover";
            type empty;
          }
        }
      }
    }
    list network {
      description
        "Specify a network to announce via BGP";
      key "number";
      leaf number {
        type union {
          type inet:ipv4-address;
          type ios-types:ipv6-prefix;
        }
      }
      leaf backdoor {
        description
          "Specify a BGP backdoor route";
        type empty;
      }
      leaf mask {
        description
          "Network mask";
        type inet:ipv4-address;
      }
      leaf route-map {
        description
          "Route-map to modify the attributes";
        type string;
      }
    }
    container redistribute {
      description
        "Redistribute information from another routing protocol";
      container application {
        description
          "Application";
        presence "true";
        list name {
          key "name";
          leaf name {
            description
              "WORD;;Route map name";
            type string;
          }
          uses live_ncs_metric-route-map-grouping;
        }
      }
      container bgp {
        description
          "Border Gateway Protocol (BGP)";
        leaf as-no {
          type ios-types:bgp-as-number-type;
        }
        uses live_ncs_metric-route-map-grouping;
      }
      container connected {
        description
          "Connected";
        presence "Connected";
        uses live_ncs_metric-route-map-grouping;
      }
      container dvmrp {
        description
          "Redistribution of DVMRP into BGP IPv4 Multicast";
        presence "Redistribution of DVMRP into BGP IPv4 Multicast";
        uses live_ncs_route-map-metric-grouping;
      }
      container eigrp {
        description
          "Enhanced Interior Gateway Routing Protocol (EIGRP)";
        leaf as-no {
          type uint16 {
            range "1..65535";
          }
        }
        uses live_ncs_metric-route-map-grouping;
      }
      container isis {
        description
          "ISO IS-IS";
        list isis-area {
          key "name";
          leaf name {
            type string;
          }
          uses live_ncs_redistribute-isis-grouping;
        }
        container default {
          uses live_ncs_redistribute-isis-grouping;
        }
      }
      container lisp {
        description
          "Locator/ID Separation Protocol";
        presence "lisp";
        leaf include-connected {
          type empty;
        }
        uses live_ncs_metric-route-map-grouping;
      }
      container iso-igrp {
        description
          "IGRP for OSI networks";
        list iso-igrp-area {
          key "name";
          leaf name {
            type string;
          }
          uses live_ncs_route-map-metric-grouping;
        }
        container default {
          uses live_ncs_route-map-metric-grouping;
        }
      }
      container mobile {
        presence "Mobile routes";
        description
          "Mobile routes";
        uses live_ncs_metric-route-map-grouping;
      }
      container odr {
        presence "On Demand stub Routes";
        description
          "On Demand stub Routes";
        uses live_ncs_metric-route-map-grouping;
      }
      list ospf {
        description
          "Open Shortest Path First (OSPF)";
        key "id";
        leaf id {
          type uint16 {
            range "1..65535";
          }
        }
        list vrf {
          description
            "VPN Routing/Forwarding Instance";
          key "name";
          leaf name {
            type string;
          }
          container match;
          uses live_ncs_metric-route-map-grouping;
        }
        container non-vrf {
          container match {
            leaf internal {
              description
                "Redistribute OSPF internal routes";
              type empty;
            }
            leaf external {
              description
                "Redistribute OSPF external routes";
              type ios-types:redist-ospf-external-type;
            }
            leaf external2 {
              description
                "Redistribute OSPF external routes";
              type ios-types:redist-ospf-external-type;
            }
            leaf nssa-external {
              description
                "Redistribute OSPF NSSA external routes";
              type ios-types:redist-ospf-external-type;
            }
            uses live_ncs_metric-route-map-grouping;
          }
          uses live_ncs_metric-route-map-grouping;
        }
      }
      container rip {
        presence "Routing Information Protocol (RIP)";
        description
          "Routing Information Protocol (RIP)";
        uses live_ncs_metric-route-map-grouping;
        leaf name {
          description
            "User selected string identifying this process";
          type string;
        }
      }
      container static {
        presence "Static routes";
        description
          "Static routes";
        container clns {
          description
            "Redistribution of OSI dynamic routes";
          presence "true";
          uses live_ncs_route-map-metric-grouping;
        }
        container ip {
          presence "true";
          uses live_ncs_metric-route-map-grouping;
        }
        uses live_ncs_metric-route-map-grouping;
      }
    }
    leaf synchronization {
      description
        "Perform IGP synchronization";
      type empty;
    }
    leaf auto-summary {
      description
        "Enable automatic network number summarization";
      type boolean;
    }
    container table-map {
      presence "true";
      description
        "Map external entry attributes into routing table";
      leaf name {
        description
          "WORD;;route-map name";
        type string;
      }
      leaf filter {
        type empty;
      }
    }
    container snmp {
      description
        "Modify snmp parameters";
      presence "true";
      container context {
        description
          "Configure a SNMP context";
        list context_word {
          key "context_word";
          leaf context_word {
            description
              "Context Name";
            type string;
          }
        }
      }
    }
  }

  grouping live_ncs_bgp-path-range-grouping {
    container attibute_type {
      leaf type {
        description
          "path attribute type";
        type uint8 {
          range "1..255";
        }
      }
      leaf in {
        description
          "Perform inbound path-attribute filtering";
        type empty;
      }
    }
    container range {
      leaf start_value {
        description
          "path attribute range start value";
        type uint8 {
          range "1..255";
        }
      }
      leaf end_value {
        description
          "path attribute range end value";
        type uint8 {
          range "1..255";
        }
      }
      leaf in {
        description
          "Perform inbound path-attribute filtering";
        type empty;
      }
    }
  }

  grouping live_ncs_config-bgp-grouping {
    list bgp {
      description
        "Border Gateway Protocol (BGP)";
      key "id";
      // NCS drop max-elements statement
      leaf id {
        type ios-types:bgp-as-number-type;
      }
      uses live_ncs_bgp-address-family-grouping;
      container address-family {
        description
          "Enter Address Family command mode";
        container with-vrf {
          list ipv4 {
            description
              "Address family";
            key "af-name";
            leaf af-name {
              type ios-types:bgp_ipv4_af_type;
            }
            list vrf {
              key "name";
              leaf name {
                type string;
              }
              uses live_ncs_bgp-ipv4-af-aggregate-address-grouping;
              uses live_ncs_bgp-address-family-grouping;
            }
          }
          list ipv6 {
            description
              "Address family";
            key "af-name";
            leaf af-name {
              type ios-types:bgp_ipv6_af_type;
            }
            list vrf {
              key "name";
              leaf name {
                type string;
              }
              uses live_ncs_bgp-ipv6-af-aggregate-address-grouping;
              uses live_ncs_bgp-address-family-grouping;
            }
          }
        }
        container no-vrf {
          list ipv4 {
            description
              "Address family";
            key "af-name";
            leaf af-name {
              type ios-types:bgp_ipv4_af_type;
            }
            uses live_ncs_bgp-ipv4-af-aggregate-address-grouping;
            uses live_ncs_bgp-address-family-grouping;
          }
          list ipv6 {
            description
              "Address family";
            key "af-name";
            leaf af-name {
              type ios-types:bgp_ipv6_af_type;
            }
            uses live_ncs_bgp-ipv6-af-aggregate-address-grouping;
            uses live_ncs_bgp-address-family-grouping;
          }
          list vpnv4 {
            description
              "Address family";
            key "af-name";
            leaf af-name {
              type enumeration {
                enum "unicast";
                enum "multicast";
                enum "flowspec";
              }
            }
            uses live_ncs_bgp-address-family-grouping;
          }
          list vpnv6 {
            description
              "Address family";
            key "af-name";
            leaf af-name {
              type enumeration {
                enum "unicast";
                enum "multicast";
                enum "flowspec";
              }
            }
            uses live_ncs_bgp-address-family-grouping;
          }
          list nsap {
            description
              "Address family";
            key "af-name";
            leaf af-name {
              type enumeration {
                enum "unicast";
              }
            }
            uses live_ncs_bgp-address-family-grouping;
          }
          list l2vpn {
            // NCS drop if-feature statement
            description
              "Address family";
            key "af-name";
            leaf af-name {
              type enumeration {
                enum "evpn";
                enum "vpls";
              }
            }
            uses live_ncs_bgp-address-family-grouping;
          }
          list rtfilter {
            description
              "Address family";
            key "af-name";
            leaf af-name {
              type enumeration {
                enum "unicast";
              }
            }
            uses live_ncs_bgp-address-family-grouping;
          }
        }
      }
      container template {
        description
          "Enter template command mode";
        list peer-policy {
          description
            "Template configuration for policy parameters";
          key "name";
          leaf name {
            type string;
          }
          list route-map {
            description
              "Apply route map to neighbor";
            key "name";
            leaf name {
              type string;
            }
            leaf in {
              description
                "Apply map to incoming routes";
              type empty;
            }
            leaf out {
              description
                "Apply map to outgong routes";
              type empty;
            }
          }
          list filter-list {
            description
              "Establish BGP filters";
            key "filter-range";
            leaf filter-range {
              description
                "AS path access list";
              type uint16 {
                range "1..500";
              }
            }
            leaf in {
              description
                "Filter incoming routes";
              type empty;
            }
            leaf out {
              description
                "Filter outgoing routes";
              type empty;
            }
          }
          container inherit {
            description
              "Inherit a template";
            container peer-policy {
              list template {
                key "name";
                leaf name {
                  description
                    "Template name";
                  type string;
                }
                leaf range {
                  description
                    "Sequence number";
                  type uint16 {
                    range "1..65535";
                  }
                }
              }
            }
          }
        }
        list peer-session {
          description
            "Template configuration for session parameters";
          key "name";
          leaf name {
            type string;
          }
          container ha-mode {
            description
              "high availability mode";
            container graceful-restart {
              description
                "graceful-restart for this peer";
              presence "true";
              leaf disable {
                description
                  "disable graceful-restart";
                type empty;
              }
            }
          }
          container password {
            description
              "Set a password";
            list password-range {
              key "encruption-type-range";
              leaf encruption-type-range {
                description
                  "Encryption type (0 to disable encryption, 7 for proprietary)";
                type uint8 {
                  range "0..7";
                }
              }
              leaf password {
                description
                  "The password";
                type string;
              }
            }
            leaf password {
              description
                "The password";
              type string;
            }
          }
          leaf remote-as {
            description
              "Specify a BGP neighbor";
            type ios-types:bgp-as-number-type;
          }
          container update-source {
            description
              "Source of routing updates";
            uses ios-ifc:live_ncs_interface-grouping;
          }
          leaf version {
            description
              "Set the BGP version to match a neighbor";
            type uint8 {
              range "4";
            }
          }
        }
      }
      container timers {
        description
          "Adjust routing timers";
        container bgp {
          description
            "BGP timers";
          leaf keepalive-interval {
            type uint16 {
              range "0..65535";
            }
          }
          leaf holdtime {
            type uint16 {
              range "0..65535";
            }
          }
          leaf minimum-neighbor-hold {
            type uint16 {
              range "0..65535";
            }
          }
        }
      }
      container scope {
        container global {
          presence "true";
          list neighbor {
            description
              "Specify a neighbor router";
            ordered-by user;
            // NCS drop must statement
            key "id";
            leaf id {
              type union {
                type string;
                type inet:ipv4-address;
                type inet:ipv6-address;
              }
            }
            uses live_ncs_neighbor-peer-group-grouping;
            uses live_ncs_neighbor-remote-as-grouping;
            uses live_ncs_neighbor-description-grouping;
            uses live_ncs_neighbor-password-grouping;
            uses live_ncs_neighbor-update-source-grouping;
            uses live_ncs_neighbor-version-grouping;
          }
          container address-family {
            description
              "Enter Address Family command mode";
            uses live_ncs_address-family-no-vrf-grouping;
          }
        }
        list vrf {
          key "id";
          leaf id {
            type union {
              type string;
              type inet:ipv4-address;
              type inet:ipv6-address;
            }
          }
          list neighbor {
            description
              "Specify a neighbor router";
            ordered-by user;
            // NCS drop must statement
            key "id";
            leaf id {
              type union {
                type string;
                type inet:ipv4-address;
                type inet:ipv6-address;
              }
            }
            uses live_ncs_neighbor-peer-group-grouping;
            uses live_ncs_neighbor-remote-as-grouping;
          }
          container address-family {
            description
              "Enter Address Family command mode";
            uses live_ncs_address-family-no-vrf-grouping;
          }
        }
      }
    }
  }

  grouping address-family-no-vrf-grouping {
    container no-vrf {
      list ipv4 {
        description
          "Address family";
        key "af-name";
        leaf af-name {
          type ios-types:bgp_ipv4_af_type;
        }
        uses bgp-ipv4-af-aggregate-address-grouping;
        uses bgp-address-family-grouping;
      }
      list ipv6 {
        description
          "Address family";
        key "af-name";
        leaf af-name {
          type ios-types:bgp_ipv6_af_type;
        }
        uses bgp-ipv6-af-aggregate-address-grouping;
        uses bgp-address-family-grouping;
      }
      list vpnv4 {
        description
          "Address family";
        key "af-name";
        leaf af-name {
          type enumeration {
            enum "unicast";
            enum "multicast";
            enum "flowspec";
          }
        }
        uses bgp-address-family-grouping;
      }
      list vpnv6 {
        description
          "Address family";
        key "af-name";
        leaf af-name {
          type enumeration {
            enum "unicast";
            enum "multicast";
            enum "flowspec";
          }
        }
        uses bgp-address-family-grouping;
      }
      list nsap {
        description
          "Address family";
        key "af-name";
        leaf af-name {
          type enumeration {
            enum "unicast";
          }
        }
        uses bgp-address-family-grouping;
      }
      list l2vpn {
        tailf:display-when "not(../ncs:module) or boolean(/ncs:devices/ncs:device[ncs:name=current()/../ncs:name]/capability/feature='ios-features:l2vpn')";
        description
          "Address family";
        key "af-name";
        leaf af-name {
          type enumeration {
            enum "evpn";
            enum "vpls";
          }
        }
        uses bgp-address-family-grouping;
      }
      list rtfilter {
        description
          "Address family";
        key "af-name";
        leaf af-name {
          type enumeration {
            enum "unicast";
          }
        }
        uses bgp-address-family-grouping;
      }
    }
  }

  grouping neighbor-description-grouping {
    leaf description {
      description
        "Neighbor specific description";
      type string;
    }
  }

  grouping neighbor-password-grouping {
    container password {
      description
        "Set a password";
      leaf enctype {
        type uint8 {
          range "0..7";
        }
      }
      leaf text {
        type string;
      }
    }
  }

  grouping neighbor-peer-group-grouping {
    container peer-group {
      description
        "Member of the peer-group";
      presence "true";
      leaf peer-group-name {
        description
          "WORD;;peer-group name";
        type string;
      }
    }
  }

  grouping neighbor-remote-as-grouping {
    leaf remote-as {
      description
        "Specify a BGP neighbor";
      type union {
        type uint32 {
          range "1..4294967295";
        }
        type string;
      }
    }
  }

  grouping neighbor-update-source-grouping {
    container update-source {
      description
        "Source of routing updates";
      uses ios-ifc:interface-grouping;
    }
  }

  grouping neighbor-version-grouping {
    leaf version {
      description
        "Set the BGP version to match a neighbor";
      type uint16 {
        range "4";
      }
    }
  }

  grouping ip-community-list-standard-grouping {
    container deny {
      description
        "Specify community to reject";
      leaf-list deny-list {
        type union {
          type ios-types:community-number-type;
          type ios-types:community-well-known-type;
        }
      }
    }
    container permit {
      description
        "Specify community to accept";
      leaf-list permit-list {
        type union {
          type ios-types:community-number-type;
          type ios-types:community-well-known-type;
        }
      }
    }
  }

  grouping ip-community-list-expanded-grouping {
    container deny {
      description
        "Specify community to reject";
      leaf-list deny-list {
        ordered-by user;
        type string;
      }
    }
    container permit {
      description
        "Specify community to accept";
      leaf-list permit-list {
        ordered-by user;
        type string;
      }
    }
  }

  grouping ip-extcommunity-list-standard-grouping {
    container deny {
      description
        "Specify community to reject";
      list rt {
        description
          "Route Target extended community";
        key "name";
        leaf name {
          type string;
        }
      }
      list soo {
        description
          "Site-of-Origin extended community";
        key "name";
        leaf name {
          type string;
        }
      }
      list vpn-distinguisher {
        description
          "VPN Distinguisher extcomm";
        key "name";
        leaf name {
          type string;
        }
      }
    }
    container permit {
      description
        "Specify community to accept";
      list rt {
        description
          "Route Target extended community";
        key "name";
        leaf name {
          type string;
        }
      }
      list soo {
        description
          "Site-of-Origin extended community";
        key "name";
        leaf name {
          type string;
        }
      }
      list vpn-distinguisher {
        description
          "VPN Distinguisher extcomm";
        key "name";
        leaf name {
          type string;
        }
      }
    }
  }

  grouping config-ip-community-list-grouping {
    container community-list {
      description
        "Add a community list entry";
      list number-standard {
        key "no";
        leaf no {
          type uint16 {
            range "1..99";
          }
        }
        uses ip-community-list-standard-grouping;
      }
      list number-expanded {
        key "no";
        leaf no {
          type uint16 {
            range "100..500";
          }
        }
        uses ip-community-list-expanded-grouping;
      }
      list expanded {
        description
          "Add an expanded community-list entry";
        key "name";
        leaf name {
          type string;
        }
        uses ip-community-list-expanded-grouping;
      }
      list standard {
        description
          "Add a standard community-list entry";
        key "name";
        leaf name {
          type string;
        }
        uses ip-community-list-standard-grouping;
      }
    }
  }

  grouping config-ip-extcommunity-list-grouping {
    container extcommunity-list {
      description
        "Extended a community list entry";
      list number-standard {
        key "no";
        leaf no {
          type uint16 {
            range "1..99";
          }
        }
        uses ip-extcommunity-list-standard-grouping;
      }
      list number-expanded {
        key "no";
        leaf no {
          type uint16 {
            range "100..500";
          }
        }
        uses ip-community-list-expanded-grouping;
      }
      list expanded {
        description
          "Extended an expanded community-list entry";
        key "name";
        leaf name {
          type string;
        }
        uses ip-community-list-expanded-grouping;
      }
      list standard {
        description
          "Extended a standard community-list entry";
        key "name";
        leaf name {
          type string;
        }
        uses ip-extcommunity-list-standard-grouping;
      }
    }
  }

  grouping config-ip-as-path-grouping {
    list access-list {
      description
        "Specify an access list number";
      key "name";
      leaf name {
        type uint16 {
          range "1..500";
        }
      }
      uses ip-community-list-expanded-grouping;
    }
  }

  grouping max-path-grouping {
    container max-path {
      leaf max {
        type uint16 {
          range "1..32";
        }
      }
    }
    container external-rtfilter {
      description
        "VPN prefix multipath on external RTFilter peers";
      leaf max {
        type uint16 {
          range "1..32";
        }
      }
    }
  }

  grouping metric-route-map-grouping {
    leaf metric {
      description
        "Metric for redistributed routes";
      type uint32 {
        range "0..4294967295";
      }
    }
    leaf route-map {
      description
        "Route map reference";
      type string;
    }
  }

  grouping route-map-metric-grouping {
    leaf route-map {
      description
        "Route map reference";
      type string;
    }
    leaf metric {
      description
        "Metric for redistributed routes";
      type uint32 {
        range "0..4294967295";
      }
    }
  }

  grouping redistribute-isis-grouping {
    choice osi-ip-choice {
      leaf ip {
        description
          "Redistribution of IP dynamic routes";
        type empty;
      }
      leaf clns {
        description
          "Redistribution of OSI dynamic routes";
        type empty;
      }
    }
    leaf routes {
      type enumeration {
        enum "level-1";
        enum "level-2";
        enum "level-1-2";
      }
    }
    uses metric-route-map-grouping;
  }

  grouping bgp-ipv4-af-aggregate-address-grouping {
    container aggregate-address {
      description
        "Configure BGP aggregate entries";
      leaf ipv4-address {
        type inet:ipv4-address;
      }
      leaf ipv4-mask {
        type inet:ipv4-address;
      }
      leaf advertise-map {
        description
          "Set condition to advertise attribute";
        type string;
      }
      leaf as-set {
        description
          "Generate AS set path information";
        type empty;
      }
      leaf attribute-map {
        type string;
      }
      leaf as-override {
        description
          "Override matching AS-number while sending update";
        type empty;
      }
      leaf route-map {
        type string;
      }
      leaf summary-only {
        description
          "Filter more specific routes from updates";
        type empty;
      }
      leaf suppress-map {
        description
          "Conditionally filter more specific routes from updates";
        type string;
      }
    }
  }

  grouping bgp-ipv6-af-aggregate-address-grouping {
    container aggregate-address {
      description
        "Configure BGP aggregate entries";
      leaf ipv6-address {
        type ios-types:ipv6-prefix;
      }
      leaf advertise-map {
        description
          "Set condition to advertise attribute";
        type string;
      }
      leaf as-set {
        description
          "Generate AS set path information";
        type empty;
      }
      leaf attribute-map {
        type string;
      }
      leaf as-override {
        description
          "Override matching AS-number while sending update";
        type empty;
      }
      leaf route-map {
        type string;
      }
      leaf summary-only {
        description
          "Filter more specific routes from updates";
        type empty;
      }
      leaf suppress-map {
        description
          "Conditionally filter more specific routes from updates";
        type string;
      }
    }
  }

  grouping bgp-address-family-grouping {
    container import {
      description
        "Configure path import";
      container path {
        description
          "Path selection and path limit";
        leaf limit {
          description
            "Per net imported path limit";
          type uint8 {
            range "2..255";
          }
        }
      }
    }
    container bgp {
      description
        "BGP specific commands";
      leaf router-id {
        description
          "Override configured router identifier (peers will reset)";
        type inet:ipv4-address;
      }
      leaf always-compare-med {
        description
          "Allow comparing MED from different neighbors";
        type empty;
      }
      leaf aggregate-timer {
        description
          "Timer interval";
        type uint8 {
          range "6..60";
        }
      }
      container asnotation {
        description
          "Change the default asplain notation";
        leaf dot {
          description
            "asdot notation";
          type empty;
        }
      }
      container nopeerup-delay {
        description
          "Set how long BGP will wait for the first peer to come up before beginning the update delay or graceful restart timers (in seconds)";
        leaf cold-boot {
          description
            "Delay in seconds";
          type uint16 {
            range "1..3600";
          }
        }
        leaf nsf-switchover {
          description
            "Delay in seconds";
          type uint16 {
            range "1..3600";
          }
        }
        leaf post-boot {
          description
            "Delay in seconds";
          type uint16 {
            range "1..3600";
          }
        }
        leaf user-initiated {
          description
            "Delay in seconds";
          type uint16 {
            range "1..3600";
          }
        }
      }
      container recursion {
        description
          "recursion rule for the nexthops";
        leaf host {
          description
            "recursion via host for the nexthops";
          type empty;
        }
      }
      leaf advertise-best-external {
        description
          "Advertise best external path to internal peers";
        type empty;
      }
      container additional-paths {
        description
          "Additional paths in the BGP table";
        leaf install {
          description
            "Additional paths to install into RIB";
          type empty;
        }
        leaf receive {
          description
            "Receive additional paths from neighbors";
          type empty;
        }
        container select {
          description
            "Selection criteria to pick the paths";
          container all {
            description
              "Select all available paths";
            presence "true";
            container best {
              description
                "Select best N paths";
              list range {
                key "range";
                leaf range {
                  description
                    "Number of best paths in additional paths to be selected";
                  type uint8 {
                    range "2..3";
                  }
                }
                leaf group-best {
                  description
                    "Select group-best path";
                  type empty;
                }
              }
            }
            container group-best {
              description
                "Select group-best path";
              presence "true";
              leaf best {
                description
                  "Number of best paths in additional paths to be selected";
                type uint8 {
                  range "2..3";
                }
              }
            }
          }
          container backup {
            description
              "Select backup path";
            presence "true";
            leaf best-external {
              description
                "Select best-external path";
              type empty;
            }
          }
          container best {
            description
              "Select best N paths";
            list range {
              key "range";
              leaf range {
                description
                  "Number of best paths in additional paths to be selected";
                type uint8 {
                  range "2..3";
                }
              }
              leaf all {
                description
                  "Select all available paths";
                type empty;
              }
              container group-best {
                description
                  "Select group-best path";
                presence "true";
                leaf all {
                  description
                    "Select all available paths";
                  type empty;
                }
              }
            }
          }
          container best-external {
            description
              "Select best-external path";
            presence "true";
            leaf backup {
              description
                "Select backup path";
              type empty;
            }
          }
          container group-best {
            description
              "Select group-best path";
            presence "true";
            leaf all {
              description
                "Select all available paths";
              type empty;
            }
            leaf best {
              description
                "Number of best paths in additional paths to be selected";
              type uint8 {
                range "2..3";
              }
            }
          }
        }
        container send {
          description
            "Send additional paths to neighbors";
          presence "true";
          leaf receive {
            description
              "Receive additional paths from neighbors";
            type empty;
          }
        }
      }
      container bestpath {
        description
          "Change the default bestpath selection";
        leaf compare-routerid {
          type empty;
        }
        container cost-community {
          description
            "cost community";
          leaf ignore {
            description
              "Ignore cost communities in bestpath selection";
            type empty;
          }
        }
        container igp-metric {
          description
            "igp metric";
          leaf ignore {
            description
              "Ignore igp metric in bestpath selection";
            type empty;
          }
        }
        container med {
          description
            "MED attribute";
          choice med-choice {
            container confed {
              description
                "Compare MED among confederation paths";
              presence "Compare MED among confederation paths";
              leaf missing-at-worst {
                description
                  "Treat missing MED as the least preferred one";
                type empty;
              }
            }
            leaf missing-at-worst {
              description
                "Treat missing MED as the least preferred one";
              type empty;
            }
          }
        }
      }
      container client-to-client {
        description
          "Configure client to client route reflection";
        leaf reflection {
          description
            "reflection of routes allowed";
          type empty;
        }
      }
      leaf cluster-id {
        type union {
          type uint32 {
            range "1..4294967295";
          }
          type inet:ipv4-address;
        }
      }
      container confederation {
        description
          "AS confederation parameters";
        leaf identifier {
          type inet:as-number;
        }
        container peers {
          description
            "Peer ASs in BGP confederation";
          leaf-list peers-as {
            type inet:as-number;
          }
        }
      }
      container consistency-checker {
        description
          "Consistency-checker";
        container auto-repair {
          description
            "Auto-Repair";
          presence "true";
          leaf interval {
            description
              "Interval (minutes)";
            type uint16 {
              range "5..1440";
            }
          }
        }
        container error-message {
          description
            "Log Error-Msg";
          presence "true";
          leaf interval {
            description
              "Interval (minutes)";
            type uint16 {
              range "5..1440";
            }
          }
        }
      }
      container dampening {
        description
          "Enable route-flap dampening";
        presence "enable bgp route-flap dampening";
        choice dampening-choice {
          leaf route-map {
            description
              "Route-map to specify criteria for dampening";
            type string;
          }
          container dampen {
            leaf half-life-time {
              type uint8 {
                range "1 .. 45";
              }
            }
            leaf reuse-time {
              type uint16 {
                range "1 .. 20000";
              }
            }
            leaf suppress-time {
              type uint16 {
                range "1 .. 20000";
              }
            }
            leaf max-suppress-time {
              type uint8 {
                range "1 .. 255";
              }
            }
          }
        }
      }
      container default {
        description
          "Configure BGP defaults";
        choice default-choice {
          leaf ipv4-unicast {
            description
              "Activate ipv4-unicast for a peer by default";
            type boolean;
          }
          leaf ipv6-nexthop {
            description
              "Default IPv6 nexthop format";
            type empty;
          }
          leaf local-preference {
            description
              "local preference (higher=more preferred)";
            type uint32 {
              range "1..4294967295";
            }
          }
          leaf route-target {
            description
              "Control behavior based on Route-Target attributes";
            type enumeration {
              enum "filter";
            }
          }
        }
      }
      leaf deterministic-med {
        description
          "Pick the best-MED path among paths advertised from the neighboring AS";
        type empty;
      }
      leaf dmzlink-bw {
        description
          "Use DMZ Link Bandwidth as weight for BGP multipaths";
        type empty;
      }
      leaf enforce-first-as {
        description
          "Enforce the first AS for EBGP routes(default)";
        type empty;
      }
      leaf enhanced-error {
        description
          "Enabled BGP Enhanced error handling";
        type empty;
      }
      leaf fast-external-fallover {
        description
          "Immediately reset session if a link to a directly connected external peer goes down";
        type boolean;
      }
      container graceful-restart {
        description
          "Graceful restart capability parameters";
        presence "Graceful restart capability parameters";
        leaf extended {
          type empty;
        }
        leaf restart-time {
          description
            "Set the max time needed to restart and come back up";
          type uint16 {
            range "1..3600";
          }
        }
        leaf stalepath-time {
          description
            "Set the max time to hold onto restarting peer's stale paths";
          type uint16 {
            range "1..3600";
          }
        }
      }
      container ha-mode {
        description
          "Select BGP High Availability mode";
        container sso {
          description
            "BGP High Availability NSR sso mode";
          presence "true";
          leaf prefer {
            description
              "Perfer BGP High Availability NSR sso mode";
            type empty;
          }
        }
      }
      list inject-map {
        description
          "Routemap which specifies prefixes to inject";
        key "name";
        leaf name {
          type string;
        }
        leaf exist-map {
          description
            "Routemap which specifies exist condition";
          type string;
        }
        leaf copy-attributes {
          description
            "Copy attributes from aggregate";
          type empty;
        }
      }
      leaf log-neighbor-changes {
        description
          "Log neighbor up/down and reset reason";
        type empty;
      }
      leaf maxas-limit {
        description
          "Allow AS-PATH attribute from any neighbor imposing a limit on number of ASes";
        type uint16 {
          range "1..2000";
        }
      }
      leaf maxcommunity-limit {
        description
          "Number of communities in the COMMUNITY attribute";
        type uint16 {
          range "1..1018";
        }
      }
      container route-map {
        description
          "bgp route-map commands";
        leaf priority {
          description
            "Have route-map set commands take priority over BGP commands such ";
          type empty;
        }
      }
      container slow-peer {
        description
          "Configure slow-peer";
        container detection {
          description
            "Slow-peer detection";
          presence "true";
          leaf disable {
            description
              "Disable slow-peer detection";
            type empty;
          }
          leaf threshold {
            description
              "Threshold value (seconds)";
            type uint16 {
              range "120..3600";
            }
          }
        }
        container split-update-group {
          description
            "Configure slow-peer split-update-group";
          container dynamic {
            description
              "Dynamically split the slow peer to slow-update group";
            presence "true";
            leaf permanent {
              description
                "Keep the slow-peer permanently in slow-update group";
              type empty;
            }
          }
        }
      }
      container update-group {
        description
          "Manage peers in bgp update groups";
        container split {
          description
            "Split update groups based on Policy";
          leaf as-override {
            description
              "Keep peers with as-override in different update groups";
            type empty;
          }
        }
      }
      container nexthop {
        description
          "Nexthop tracking commands";
        container trigger {
          description
            "Nexthop triggering";
          leaf delay {
            description
              "Set the delay to tigger nexthop tracking";
            type uint8 {
              range "0..100";
            }
          }
          leaf enable {
            description
              "Enable nexthop tracking";
            type boolean;
          }
        }
        leaf route-map {
          description
            "Route map for valid nexthops";
          type string;
        }
      }
      leaf redistribute-internal {
        description
          "Allow redistribution of iBGP into IGPs (dangerous)";
        type empty;
      }
      container regexp {
        description
          "Select regular expression engine";
        leaf deterministic {
          description
            "Enable bounded-execution-time regular expression engine";
          type empty;
        }
      }
      leaf scan-time {
        description
          "Configure background scanner interval";
        type uint8 {
          range "5..60";
        }
      }
      leaf soft-reconfig-backup {
        description
          "Use soft-reconfiguration inbound only when route-refresh is not negotiated";
        type empty;
      }
      leaf suppress-inactive {
        description
          "Suppress routes that are not in the routing table";
        type empty;
      }
      container transport {
        description
          "Transport options";
        leaf path-mtu-discovery {
          description
            "Use transport path MTU discovery";
          type boolean;
        }
      }
      leaf update-delay {
        description
          "Set the max initial delay for sending update";
        type uint16 {
          range "1..3600";
        }
      }
    }
    container default-information {
      description
        "Control distribution of default information";
      leaf originate {
        description
          "Distribute a default route";
        type empty;
      }
    }
    leaf default-metric {
      description
        "Set metric of redistributed routes";
      type uint32 {
        range "1..4294967295";
      }
    }
    container distance {
      description
        "Define an administrative distance";
      container bgp {
        description
          "BGP distance";
        leaf extern-as {
          type uint16 {
            range "1..255";
          }
        }
        leaf internal-as {
          type uint16 {
            range "1..255";
          }
        }
        leaf local {
          type uint16 {
            range "1..255";
          }
        }
      }
      list adm-distance {
        key "distance srcip wildbits";
        leaf distance {
          type uint16 {
            range "1..255";
          }
        }
        leaf srcip {
          type inet:ipv4-address;
        }
        leaf wildbits {
          type inet:ipv4-address;
        }
        leaf acl {
          type union {
            type uint16 {
              range "1..99";
            }
            type uint16 {
              range "1300..1999";
            }
            type string {
              pattern '[a-zA-Z].*';
            }
          }
        }
      }
    }
    list distribute-list {
      description
        "Filter networks in routing updates";
      key "id";
      leaf id {
        type ios-types:bgp-distribute-list-type;
      }
      choice in-out-choice {
        container in {
          presence "enable incoming routing updates";
          description
            "Filter incoming routing updates";
          leaf interface {
            type string;
          }
        }
        container out {
          presence "enable outgoing routing updates";
          description
            "Filter outgoing routing updates";
          leaf interface {
            type string;
          }
        }
      }
    }
    container maximum-paths {
      description
        "Forward packets over multiple paths";
      uses max-path-grouping;
      choice max-path-choice {
        leaf eibgp {
          description
            "Both eBGP and iBGP paths as multipath";
          type uint16 {
            range "1..32";
          }
        }
        container ibgp {
          description
            "iBGP-multipath";
          choice ibgp-choice {
            leaf unequal-cost {
              description
                "Perform Un-Equal cost multipath selection";
              type uint16 {
                range "1..32";
              }
            }
            leaf max {
              type uint16 {
                range "1..32";
              }
            }
          }
        }
      }
    }
    list neighbor {
      description
        "Specify a neighbor router";
      ordered-by user;
      must "count(*) > 1" {
        tailf:xpath-root 3;
      }
      key "id";
      leaf id {
        type union {
          type string;
          type inet:ipv4-address;
          type inet:ipv6-address;
        }
      }
      uses neighbor-peer-group-grouping;
      uses neighbor-remote-as-grouping;
      container local-as {
        description
          "Specify a local-as number";
        presence "Specify a local-as number";
        leaf as-no {
          type ios-types:bgp-as-number-type;
        }
        leaf no-prepend {
          description
            "Do not prepend local-as to updates from ebgp peers";
          type empty;
        }
        leaf replace-as {
          description
            "Replace real AS with local AS in the EBGP updates";
          type empty;
        }
        leaf dual-as {
          description
            "Accept either real AS or local AS from the ebgp peer";
          type empty;
        }
      }
      leaf activate {
        description
          "Enable the Address Family for this Neighbor";
        type empty;
      }
      container additional-paths {
        leaf disable {
          description
            "Disable additional paths for this neighbor";
          type empty;
        }
        leaf receive {
          description
            "Receive additional paths from neighbors";
          type empty;
        }
        container send {
          description
            "Send additional paths to this neighbor";
          presence "true";
          leaf receive {
            description
              "Receive additional paths from this neighbor";
            type empty;
          }
        }
      }
      container advertise {
        description
          "Advertise to this neighbor";
        container additional-paths {
          description
            "Advertise additional paths";
          container all {
            description
              "Select all available paths";
            presence "true";
            container best {
              description
                "Select best N paths";
              list best-range {
                key "range";
                leaf range {
                  description
                    "Number of best paths in additional paths to be selected";
                  type uint8 {
                    range "2..3";
                  }
                }
                leaf group-best {
                  description
                    "Select group-best paths";
                  type empty;
                }
              }
            }
            container group-best {
              description
                "Select group-best paths";
              presence "true";
              leaf best {
                description
                  "Number of best paths in additional paths to be selected";
                type uint8 {
                  range "2..3";
                }
              }
            }
          }
          container best {
            description
              "Select best N paths";
            list best-range {
              key "range";
              leaf range {
                description
                  "Number of best paths in additional paths to be selected";
                type uint8 {
                  range "2..3";
                }
              }
              leaf all {
                description
                  "Select all available paths";
                type empty;
              }
              container group-best {
                description
                  "Select group-best paths";
                presence "true";
                leaf all {
                  description
                    "Select all available paths";
                  type empty;
                }
              }
            }
          }
          container group-best {
            description
              "Select group-best paths";
            presence "true";
            leaf all {
              description
                "Select all available paths";
              type empty;
            }
            leaf best {
              description
                "Number of best paths in additional paths to be selected";
              type uint8 {
                range "2..3";
              }
            }
          }
        }
        leaf best-external {
          description
            "Advertise best-external (at RRs best-internal) path";
          type empty;
        }
        container diverse-path {
          description
            "Advertise diverse path";
          container backup {
            description
              "Diverse path can be backup path";
            presence "true";
            leaf mpath {
              description
                "Diverse path can be multipath";
              type empty;
            }
          }
          leaf mpath {
            description
              "Diverse path can be multipath";
            type empty;
          }
        }
      }
      container advertise-map {
        description
          "specify route-map for conditional advertisement";
        list name {
          key "word";
          leaf word {
            description
              "advertise route-map name";
            type string;
          }
          leaf exist-map {
            description
              "condition route-map name";
            type string;
          }
          leaf non-exist-map {
            description
              "condition route-map name";
            type string;
          }
        }
      }
      container aigp {
        description
          "Enable a AIGP on neighbor";
        presence "true";
        container send {
          description
            "Cost community or MED carrying AIGP VALUE";
          container cost-community {
            description
              "Cost extended community carrying AIGP Value";
            list cc-range {
              key "range";
              leaf range {
                description
                  "Community ID";
                type uint8 {
                  range "0..255";
                }
              }
              container poi {
                description
                  "Point of Insertion";
                container igp-cost {
                  description
                    "Point of Insertion After IGP";
                  presence "true";
                  leaf transitive {
                    description
                      "Cost community is Transitive";
                    type empty;
                  }
                }
                container pre-bestpath {
                  description
                    "Point of Insertion At Beginning";
                  presence "true";
                  leaf transitive {
                    description
                      "Cost community is Transitive";
                    type empty;
                  }
                }
              }
            }
          }
          leaf med {
            description
              "Med carrying AIGP Value";
            type empty;
          }
        }
      }
      leaf allow-policy {
        description
          "Enable the policy support for this IBGP Neighbor";
        type empty;
      }
      container announce {
        description
          "Announce RPKI State using an Extended Community";
        container rpki {
          description
            "Announce RPKI information using an Extended Community";
          leaf state {
            description
              "Announce RPKI State information using an Extended Community";
            type empty;
          }
        }
      }
      leaf advertisement-interval {
        description
          "Minimum interval between sending BGP routing updates";
        type uint16 {
          range "0..600";
        }
      }
      container allowas-in {
        description
          "Accept as-path with my AS present in it";
        presence "accept as-paths";
        leaf as-number {
          type uint8 {
            range "1..10";
          }
        }
      }
      container as-override {
        description
          "Override matching AS-number while sending update";
        presence "true";
        leaf disable {
          type empty;
        }
      }
      container capability {
        description
          "Advertise capability to the peer";
        container orf {
          description
            "Advertise ORF capability to the peer";
          leaf-list prefix-list {
            description
              "Advertise prefixlist ORF capability to this neighbor";
            max-elements 1;
            type enumeration {
              enum "both";
              enum "receive";
              enum "send";
            }
          }
        }
      }
      leaf cluster-id {
        type union {
          type uint32 {
            range "1..4294967295";
          }
          type inet:ipv4-address;
        }
      }
      container default-originate {
        description
          "Originate default route to this neighbour";
        presence "enable originate default route to this neighbour";
        leaf route-map {
          description
            "Route-map to specify criteria to originate default";
          type string;
        }
      }
      uses neighbor-description-grouping;
      leaf disable-connected-check {
        description
          "One-hop away EBGP peer using loopback address";
        type empty;
      }
      list distribute-list {
        description
          "Filter updates to/from this neighbor";
        key "inout";
        leaf inout {
          type enumeration {
            enum "in";
            enum "out";
          }
        }
        leaf accesslist {
          type ios-types:bgp-distribute-list-type2;
          mandatory true;
        }
      }
      leaf dmzlink-bw {
        description
          "Propagate the DMZ link bandwidth";
        type empty;
      }
      container ebgp-multihop {
        description
          "Allow EBGP neighbors not on directly connected networks";
        presence "Allow EBGP neighbors not on directly connected networks";
        leaf max-hop {
          type uint8 {
            range "1..255";
          }
        }
      }
      container fall-over {
        description
          "session fall on peer route lost";
        container bfd {
          description
            "Use BFD to detect failure";
          presence "true";
        }
      }
      list filter-list {
        description
          "Establish BGP filters";
        key "inout";
        leaf inout {
          type enumeration {
            enum "in";
            enum "out";
          }
        }
        leaf as-path-list {
          type uint16 {
            range "1..500";
          }
          mandatory true;
        }
      }
      container inherit {
        description
          "Inherit a template";
        leaf peer-policy {
          description
            "Inherit a peer-policy template";
          type string;
        }
        leaf peer-session {
          description
            "Inherit a peer-session template";
          type string;
        }
      }
      container log-neighbor-changes {
        description
          "Log neighbor up/down and reset reason";
        presence "true";
        leaf disable {
          description
            "disable";
          type empty;
        }
      }
      container maximum-prefix {
        description
          "Maximum number of prefixes accepted from this peer";
        leaf max-prefix-no {
          type uint32 {
            range "1..2147483647";
          }
        }
        leaf threshold {
          type uint8 {
            range "1..100";
          }
        }
        leaf restart {
          description
            "Restart bgp connection after limit is exceeded";
          type uint16 {
            range "1..65535";
          }
        }
        leaf warning-only {
          description
            "Only give warning message when limit is exceeded";
          type empty;
        }
      }
      leaf next-hop-self {
        description
          "Disable the next hop calculation for this neighbor";
        type empty;
      }
      leaf next-hop-unchanged {
        description
          "Propagate the iBGP paths's next hop unchanged for this neighbor";
        type empty;
      }
      uses neighbor-password-grouping;
      list prefix-list {
        description
          "Filter updates to/from this neighbor";
        key "inout";
        leaf inout {
          type enumeration {
            enum "in";
            enum "out";
          }
        }
        leaf prefix-list-name {
          type string;
          mandatory true;
        }
      }
      container path-attribute {
        description
          "BGP optional attribute filtering";
        container discard {
          description
            "Discard matching path-attribute for this neighbor";
          uses bgp-path-range-grouping;
        }
        container treat-as-withdraw {
          description
            "Treat-as-withdraw matching path-attribute for this neighbor";
          uses bgp-path-range-grouping;
        }
      }
      leaf remove-private-as {
        description
          "Remove private AS number from outbound updates";
        type empty;
      }
      list route-map {
        description
          "Apply route map to neighbor";
        key "inout";
        leaf inout {
          type enumeration {
            enum "in";
            enum "out";
          }
        }
        leaf route-map-name {
          type string;
          mandatory true;
        }
      }
      leaf route-reflector-client {
        description
          "Configure a neighbor as Route Reflector client";
        type empty;
      }
      leaf route-reflector-cluster-id {
        type union {
          type uint32 {
            range "1..4294967295";
          }
          type inet:ipv4-address;
        }
      }
      container send-community {
        description
          "Send Community attribute to this neighbor";
        presence "true";
        leaf send-community-where {
          type enumeration {
            enum "both";
            enum "extended";
            enum "standard";
          }
        }
      }
      container send-label {
        description
          "Send NLRI + MPLS Label to this peer";
        leaf send-label-explicit {
          type enumeration {
            enum "explicit-null";
          }
        }
      }
      leaf soo {
        description
          "ASN:nn or IP-address:nn  VPN extended community";
        type string;
      }
      leaf shutdown {
        description
          "Administratively shut down this neighbor";
        type empty;
      }
      leaf soft-reconfiguration {
        description
          "Per neighbor soft reconfiguration";
        type enumeration {
          enum "inbound";
        }
      }
      container slow-peer {
        description
          "Configure slow-peer";
        container detection {
          description
            "Slow-peer detection";
          presence "true";
          leaf threshold {
            description
              "Threshold value (seconds)";
            type uint16 {
              range "120..3600";
            }
          }
        }
        container split-update-group {
          description
            "Configure slow-peer split-update-group";
          container dynamic {
            description
              "Dynamically split the slow peer to slow-update group";
            presence "true";
            leaf permanent {
              description
                "Keep the slow-peer permanently in slow-update group";
              type empty;
            }
          }
        }
      }
      container timers {
        description
          "BGP per neighbor timers";
        leaf keepalive-interval {
          type uint16 {
            range "0..65535";
          }
        }
        leaf holdtime {
          type uint16 {
            range "0..65535";
          }
        }
        leaf minimum-neighbor-hold {
          type uint16 {
            range "0..65535";
          }
        }
      }
      container translate-update {
        description
          "Translate Update to MBGP format";
        container ipv4 {
          description
            "Address Family";
          container multicast {
            description
              "Address Family modifier";
            presence "Address Family modifier";
            leaf unicast {
              description
                "Address Family modifier";
              type empty;
            }
          }
        }
      }
      container transport {
        description
          "Transport options";
        leaf connection-mode {
          description
            "Specify passive or active connection";
          type enumeration {
            enum "active";
            enum "passive";
          }
        }
        leaf multi-session {
          description
            "Use Multi-session for transport";
          type empty;
        }
        container path-mtu-discovery {
          description
            "Use transport path MTU discovery";
          presence "true";
          leaf disable {
            description
              "disable";
            type empty;
          }
        }
      }
      container ttl-security {
        description
          "BGP ttl security check";
        leaf hops {
          description
            "IP hops";
          type uint8 {
            range "1..254";
          }
        }
      }
      leaf unsuppress-map {
        description
          "Route-map to selectively unsuppress suppressed routes";
        type string;
      }
      uses neighbor-update-source-grouping;
      uses neighbor-version-grouping;
      leaf weight {
        description
          "Set default weight for routes from this neighbor";
        type uint16 {
          range "0..65535";
        }
      }
      container ha-mode {
        description
          "high availability mode";
        container graceful-restart {
          description
            "graceful-restart for this peer";
          presence "true";
          leaf disable {
            description
              "disable graceful-restart";
            type empty;
          }
        }
        container sso {
          description
            "stateful-switchover support for this peer";
          presence "true";
          leaf disable {
            description
              "disable stateful-switchover";
            type empty;
          }
        }
      }
    }
    list network {
      description
        "Specify a network to announce via BGP";
      key "number";
      leaf number {
        type union {
          type inet:ipv4-address;
          type ios-types:ipv6-prefix;
        }
      }
      leaf backdoor {
        description
          "Specify a BGP backdoor route";
        type empty;
      }
      leaf mask {
        description
          "Network mask";
        type inet:ipv4-address;
      }
      leaf route-map {
        description
          "Route-map to modify the attributes";
        type string;
      }
    }
    container redistribute {
      description
        "Redistribute information from another routing protocol";
      container application {
        description
          "Application";
        presence "true";
        list name {
          key "name";
          leaf name {
            description
              "WORD;;Route map name";
            type string;
          }
          uses metric-route-map-grouping;
        }
      }
      container bgp {
        description
          "Border Gateway Protocol (BGP)";
        leaf as-no {
          type ios-types:bgp-as-number-type;
        }
        uses metric-route-map-grouping;
      }
      container connected {
        description
          "Connected";
        presence "Connected";
        uses metric-route-map-grouping;
      }
      container dvmrp {
        description
          "Redistribution of DVMRP into BGP IPv4 Multicast";
        presence "Redistribution of DVMRP into BGP IPv4 Multicast";
        uses route-map-metric-grouping;
      }
      container eigrp {
        description
          "Enhanced Interior Gateway Routing Protocol (EIGRP)";
        leaf as-no {
          type uint16 {
            range "1..65535";
          }
        }
        uses metric-route-map-grouping;
      }
      container isis {
        description
          "ISO IS-IS";
        list isis-area {
          key "name";
          leaf name {
            type string;
          }
          uses redistribute-isis-grouping;
        }
        container default {
          uses redistribute-isis-grouping;
        }
      }
      container lisp {
        description
          "Locator/ID Separation Protocol";
        presence "lisp";
        leaf include-connected {
          type empty;
        }
        uses metric-route-map-grouping;
      }
      container iso-igrp {
        description
          "IGRP for OSI networks";
        list iso-igrp-area {
          key "name";
          leaf name {
            type string;
          }
          uses route-map-metric-grouping;
        }
        container default {
          uses route-map-metric-grouping;
        }
      }
      container mobile {
        presence "Mobile routes";
        description
          "Mobile routes";
        uses metric-route-map-grouping;
      }
      container odr {
        presence "On Demand stub Routes";
        description
          "On Demand stub Routes";
        uses metric-route-map-grouping;
      }
      list ospf {
        description
          "Open Shortest Path First (OSPF)";
        key "id";
        leaf id {
          type uint16 {
            range "1..65535";
          }
        }
        list vrf {
          description
            "VPN Routing/Forwarding Instance";
          key "name";
          leaf name {
            type string;
          }
          container match;
          uses metric-route-map-grouping;
        }
        container non-vrf {
          container match {
            leaf internal {
              description
                "Redistribute OSPF internal routes";
              type empty;
            }
            leaf external {
              description
                "Redistribute OSPF external routes";
              type ios-types:redist-ospf-external-type;
            }
            leaf external2 {
              description
                "Redistribute OSPF external routes";
              type ios-types:redist-ospf-external-type;
            }
            leaf nssa-external {
              description
                "Redistribute OSPF NSSA external routes";
              type ios-types:redist-ospf-external-type;
            }
            uses metric-route-map-grouping;
          }
          uses metric-route-map-grouping;
        }
      }
      container rip {
        presence "Routing Information Protocol (RIP)";
        description
          "Routing Information Protocol (RIP)";
        uses metric-route-map-grouping;
        leaf name {
          description
            "User selected string identifying this process";
          type string;
        }
      }
      container static {
        presence "Static routes";
        description
          "Static routes";
        container clns {
          description
            "Redistribution of OSI dynamic routes";
          presence "true";
          uses route-map-metric-grouping;
        }
        container ip {
          presence "true";
          uses metric-route-map-grouping;
        }
        uses metric-route-map-grouping;
      }
    }
    leaf synchronization {
      description
        "Perform IGP synchronization";
      type empty;
    }
    leaf auto-summary {
      description
        "Enable automatic network number summarization";
      type boolean;
    }
    container table-map {
      presence "true";
      description
        "Map external entry attributes into routing table";
      leaf name {
        description
          "WORD;;route-map name";
        type string;
      }
      leaf filter {
        type empty;
      }
    }
    container snmp {
      description
        "Modify snmp parameters";
      presence "true";
      container context {
        description
          "Configure a SNMP context";
        list context_word {
          key "context_word";
          leaf context_word {
            description
              "Context Name";
            type string;
          }
        }
      }
    }
  }

  grouping bgp-path-range-grouping {
    container attibute_type {
      leaf type {
        description
          "path attribute type";
        type uint8 {
          range "1..255";
        }
      }
      leaf in {
        description
          "Perform inbound path-attribute filtering";
        type empty;
      }
    }
    container range {
      leaf start_value {
        description
          "path attribute range start value";
        type uint8 {
          range "1..255";
        }
      }
      leaf end_value {
        description
          "path attribute range end value";
        type uint8 {
          range "1..255";
        }
      }
      leaf in {
        description
          "Perform inbound path-attribute filtering";
        type empty;
      }
    }
  }

  grouping config-bgp-grouping {
    list bgp {
      description
        "Border Gateway Protocol (BGP)";
      key "id";
      max-elements 1;
      leaf id {
        type ios-types:bgp-as-number-type;
      }
      uses bgp-address-family-grouping;
      container address-family {
        description
          "Enter Address Family command mode";
        container with-vrf {
          list ipv4 {
            description
              "Address family";
            key "af-name";
            leaf af-name {
              type ios-types:bgp_ipv4_af_type;
            }
            list vrf {
              key "name";
              leaf name {
                type string;
              }
              uses bgp-ipv4-af-aggregate-address-grouping;
              uses bgp-address-family-grouping;
            }
          }
          list ipv6 {
            description
              "Address family";
            key "af-name";
            leaf af-name {
              type ios-types:bgp_ipv6_af_type;
            }
            list vrf {
              key "name";
              leaf name {
                type string;
              }
              uses bgp-ipv6-af-aggregate-address-grouping;
              uses bgp-address-family-grouping;
            }
          }
        }
        container no-vrf {
          list ipv4 {
            description
              "Address family";
            key "af-name";
            leaf af-name {
              type ios-types:bgp_ipv4_af_type;
            }
            uses bgp-ipv4-af-aggregate-address-grouping;
            uses bgp-address-family-grouping;
          }
          list ipv6 {
            description
              "Address family";
            key "af-name";
            leaf af-name {
              type ios-types:bgp_ipv6_af_type;
            }
            uses bgp-ipv6-af-aggregate-address-grouping;
            uses bgp-address-family-grouping;
          }
          list vpnv4 {
            description
              "Address family";
            key "af-name";
            leaf af-name {
              type enumeration {
                enum "unicast";
                enum "multicast";
                enum "flowspec";
              }
            }
            uses bgp-address-family-grouping;
          }
          list vpnv6 {
            description
              "Address family";
            key "af-name";
            leaf af-name {
              type enumeration {
                enum "unicast";
                enum "multicast";
                enum "flowspec";
              }
            }
            uses bgp-address-family-grouping;
          }
          list nsap {
            description
              "Address family";
            key "af-name";
            leaf af-name {
              type enumeration {
                enum "unicast";
              }
            }
            uses bgp-address-family-grouping;
          }
          list l2vpn {
            tailf:display-when "not(../../../ncs:module) or boolean(/ncs:devices/ncs:device[ncs:name=current()/../../../ncs:name]/capability/feature='ios-features:l2vpn')";
            description
              "Address family";
            key "af-name";
            leaf af-name {
              type enumeration {
                enum "evpn";
                enum "vpls";
              }
            }
            uses bgp-address-family-grouping;
          }
          list rtfilter {
            description
              "Address family";
            key "af-name";
            leaf af-name {
              type enumeration {
                enum "unicast";
              }
            }
            uses bgp-address-family-grouping;
          }
        }
      }
      container template {
        description
          "Enter template command mode";
        list peer-policy {
          description
            "Template configuration for policy parameters";
          key "name";
          leaf name {
            type string;
          }
          list route-map {
            description
              "Apply route map to neighbor";
            key "name";
            leaf name {
              type string;
            }
            leaf in {
              description
                "Apply map to incoming routes";
              type empty;
            }
            leaf out {
              description
                "Apply map to outgong routes";
              type empty;
            }
          }
          list filter-list {
            description
              "Establish BGP filters";
            key "filter-range";
            leaf filter-range {
              description
                "AS path access list";
              type uint16 {
                range "1..500";
              }
            }
            leaf in {
              description
                "Filter incoming routes";
              type empty;
            }
            leaf out {
              description
                "Filter outgoing routes";
              type empty;
            }
          }
          container inherit {
            description
              "Inherit a template";
            container peer-policy {
              list template {
                key "name";
                leaf name {
                  description
                    "Template name";
                  type string;
                }
                leaf range {
                  description
                    "Sequence number";
                  type uint16 {
                    range "1..65535";
                  }
                }
              }
            }
          }
        }
        list peer-session {
          description
            "Template configuration for session parameters";
          key "name";
          leaf name {
            type string;
          }
          container ha-mode {
            description
              "high availability mode";
            container graceful-restart {
              description
                "graceful-restart for this peer";
              presence "true";
              leaf disable {
                description
                  "disable graceful-restart";
                type empty;
              }
            }
          }
          container password {
            description
              "Set a password";
            list password-range {
              key "encruption-type-range";
              leaf encruption-type-range {
                description
                  "Encryption type (0 to disable encryption, 7 for proprietary)";
                type uint8 {
                  range "0..7";
                }
              }
              leaf password {
                description
                  "The password";
                type string;
              }
            }
            leaf password {
              description
                "The password";
              type string;
            }
          }
          leaf remote-as {
            description
              "Specify a BGP neighbor";
            type ios-types:bgp-as-number-type;
          }
          container update-source {
            description
              "Source of routing updates";
            uses ios-ifc:interface-grouping;
          }
          leaf version {
            description
              "Set the BGP version to match a neighbor";
            type uint8 {
              range "4";
            }
          }
        }
      }
      container timers {
        description
          "Adjust routing timers";
        container bgp {
          description
            "BGP timers";
          leaf keepalive-interval {
            type uint16 {
              range "0..65535";
            }
          }
          leaf holdtime {
            type uint16 {
              range "0..65535";
            }
          }
          leaf minimum-neighbor-hold {
            type uint16 {
              range "0..65535";
            }
          }
        }
      }
      container scope {
        container global {
          presence "true";
          list neighbor {
            description
              "Specify a neighbor router";
            ordered-by user;
            must "count(*) > 1" {
              tailf:xpath-root 3;
            }
            key "id";
            leaf id {
              type union {
                type string;
                type inet:ipv4-address;
                type inet:ipv6-address;
              }
            }
            uses neighbor-peer-group-grouping;
            uses neighbor-remote-as-grouping;
            uses neighbor-description-grouping;
            uses neighbor-password-grouping;
            uses neighbor-update-source-grouping;
            uses neighbor-version-grouping;
          }
          container address-family {
            description
              "Enter Address Family command mode";
            uses address-family-no-vrf-grouping;
          }
        }
        list vrf {
          key "id";
          leaf id {
            type union {
              type string;
              type inet:ipv4-address;
              type inet:ipv6-address;
            }
          }
          list neighbor {
            description
              "Specify a neighbor router";
            ordered-by user;
            must "count(*) > 1" {
              tailf:xpath-root 3;
            }
            key "id";
            leaf id {
              type union {
                type string;
                type inet:ipv4-address;
                type inet:ipv6-address;
              }
            }
            uses neighbor-peer-group-grouping;
            uses neighbor-remote-as-grouping;
          }
          container address-family {
            description
              "Enter Address Family command mode";
            uses address-family-no-vrf-grouping;
          }
        }
      }
    }
  }

  augment "/ncs:devices/ncs:template/ncs:config/ios:native/ios:router" {
    uses ncs_template_config-bgp-grouping;
  }
  augment "/ncs:devices/ncs:device/ncs:live-status/ios:native/ios:router" {
    uses live_ncs_config-bgp-grouping {
      refine bgp {
        tailf:ncs-device-type "netconf";
        tailf:display-when "not(../../../ncs:module) or ../../../ncs:module[ncs:name='Cisco-IOS-XE-bgp'] or (../../../ncs:live-status-protocol[not(ncs:capability)]) or (../../../ncs:live-status-protocol/ncs:capability/ncs:module[.='Cisco-IOS-XE-bgp'])";
      }
    }
  }
  augment "/ncs:devices/ncs:device/ncs:config/ios:native/ios:router" {
    uses config-bgp-grouping {
      refine bgp {
        tailf:ncs-device-type "netconf";
        tailf:display-when "not(../../../ncs:module) or ../../../ncs:module[ncs:name='Cisco-IOS-XE-bgp']";
      }
    }
  }
  augment "/ncs:devices/ncs:template/ncs:config/ios:native/ios:ip" {
    uses ncs_template_config-ip-community-list-grouping;
  }
  augment "/ncs:devices/ncs:device/ncs:live-status/ios:native/ios:ip" {
    uses live_ncs_config-ip-community-list-grouping {
      refine community-list {
        tailf:ncs-device-type "netconf";
        tailf:display-when "not(../../../../ncs:module) or ../../../../ncs:module[ncs:name='Cisco-IOS-XE-bgp'] or (../../../../ncs:live-status-protocol[not(ncs:capability)]) or (../../../../ncs:live-status-protocol/ncs:capability/ncs:module[.='Cisco-IOS-XE-bgp'])";
      }
    }
  }
  augment "/ncs:devices/ncs:device/ncs:config/ios:native/ios:ip" {
    uses config-ip-community-list-grouping {
      refine community-list {
        tailf:ncs-device-type "netconf";
        tailf:display-when "not(../../../../ncs:module) or ../../../../ncs:module[ncs:name='Cisco-IOS-XE-bgp']";
      }
    }
  }
  augment "/ncs:devices/ncs:template/ncs:config/ios:native/ios:ip" {
    uses ncs_template_config-ip-extcommunity-list-grouping;
  }
  augment "/ncs:devices/ncs:device/ncs:live-status/ios:native/ios:ip" {
    uses live_ncs_config-ip-extcommunity-list-grouping {
      refine extcommunity-list {
        tailf:ncs-device-type "netconf";
        tailf:display-when "not(../../../../ncs:module) or ../../../../ncs:module[ncs:name='Cisco-IOS-XE-bgp'] or (../../../../ncs:live-status-protocol[not(ncs:capability)]) or (../../../../ncs:live-status-protocol/ncs:capability/ncs:module[.='Cisco-IOS-XE-bgp'])";
      }
    }
  }
  augment "/ncs:devices/ncs:device/ncs:config/ios:native/ios:ip" {
    uses config-ip-extcommunity-list-grouping {
      refine extcommunity-list {
        tailf:ncs-device-type "netconf";
        tailf:display-when "not(../../../../ncs:module) or ../../../../ncs:module[ncs:name='Cisco-IOS-XE-bgp']";
      }
    }
  }
  augment "/ncs:devices/ncs:template/ncs:config/ios:native/ios:ip/ios:as-path" {
    uses ncs_template_config-ip-as-path-grouping;
  }
  augment "/ncs:devices/ncs:device/ncs:live-status/ios:native/ios:ip/ios:as-path" {
    uses live_ncs_config-ip-as-path-grouping {
      refine access-list {
        tailf:ncs-device-type "netconf";
        tailf:display-when "not(../../../../ncs:module) or ../../../../ncs:module[ncs:name='Cisco-IOS-XE-bgp'] or (../../../../ncs:live-status-protocol[not(ncs:capability)]) or (../../../../ncs:live-status-protocol/ncs:capability/ncs:module[.='Cisco-IOS-XE-bgp'])";
      }
    }
  }
  augment "/ncs:devices/ncs:device/ncs:config/ios:native/ios:ip/ios:as-path" {
    uses config-ip-as-path-grouping {
      refine access-list {
        tailf:ncs-device-type "netconf";
        tailf:display-when "not(../../../../ncs:module) or ../../../../ncs:module[ncs:name='Cisco-IOS-XE-bgp']";
      }
    }
  }
}
