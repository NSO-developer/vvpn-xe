module Cisco-IOS-XE-card {
  // Generated by yanger -t ncs
  tailf:ncs-device-type "netconf";

  namespace "http://cisco.com/ns/yang/Cisco-IOS-XE-card";
  prefix ios-card;

  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Card Yang model.
     Copyright (c) 2016 by Cisco Systems, Inc.
     All rights reserved.";

  revision 2017-02-07 {
    description
      "Initial revision";
  }

  grouping ncs_template_config-card-grouping {
    container card {
      description
        "Configure T1/E1 SPA";
      leaf type {
        type string;
      }
      leaf slot {
        type string;
      }
      leaf bay {
        type string;
      }
    }
  }

  grouping ncs_rpc_notif_config-card-grouping {
    container card {
      description
        "Configure T1/E1 SPA";
      leaf type {
        type enumeration {
          enum "t1";
          enum "e1";
        }
      }
      leaf slot {
        type uint32;
      }
      leaf bay {
        type uint32;
      }
    }
  }

  grouping live_ncs_config-card-grouping {
    container card {
      description
        "Configure T1/E1 SPA";
      leaf type {
        type enumeration {
          enum "t1";
          enum "e1";
        }
      }
      leaf slot {
        type uint32;
      }
      leaf bay {
        type uint32;
      }
    }
  }

  grouping config-card-grouping {
    container card {
      description
        "Configure T1/E1 SPA";
      leaf type {
        type enumeration {
          enum "t1";
          enum "e1";
        }
      }
      leaf slot {
        type uint32;
      }
      leaf bay {
        type uint32;
      }
    }
  }

  augment "/ncs:devices/ncs:template/ncs:config/ios:native" {
    uses ncs_template_config-card-grouping;
  }
  augment "/ncs:devices/ncs:device/ncs:live-status/ios:native" {
    uses live_ncs_config-card-grouping {
      refine card {
        tailf:ncs-device-type "netconf";
        tailf:display-when "not(../../../ncs:module) or ../../../ncs:module[ncs:name='Cisco-IOS-XE-card'] or (../../../ncs:live-status-protocol[not(ncs:capability)]) or (../../../ncs:live-status-protocol/ncs:capability/ncs:module[.='Cisco-IOS-XE-card'])";
      }
    }
  }
  augment "/ncs:devices/ncs:device/ncs:config/ios:native" {
    uses config-card-grouping {
      refine card {
        tailf:ncs-device-type "netconf";
        tailf:display-when "not(../../../ncs:module) or ../../../ncs:module[ncs:name='Cisco-IOS-XE-card']";
      }
    }
  }
}
