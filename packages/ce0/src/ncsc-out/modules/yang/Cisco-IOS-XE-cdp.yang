module Cisco-IOS-XE-cdp {
  // Generated by yanger -t ncs
  tailf:ncs-device-type "netconf";

  namespace "http://cisco.com/ns/yang/Cisco-IOS-XE-cdp";
  prefix ios-cdp;

  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Cisco Discovery Protocol (CDP) Yang Model.
     Copyright (c) 2016 by Cisco Systems, Inc.
     All rights reserved.";

  revision 2017-02-07 {
    description
      "Initial revision";
  }

  grouping ncs_template_config-interface-cdp-grouping {
    container cdp {
      description
        "CDP interface subcommands";
      leaf enable {
        description
          "Enable CDP on interface";
        type string;
      }
      container tlv {
        description
          "Enable exchange of specific tlv information";
        container app {
          description
            "Enable/Configure Application TLV";
          presence "true";
          leaf tlvtype {
            description
              "Configure APP TLV";
            type string;
          }
          leaf value {
            description
              "Configure App TLV Value information";
            type string;
          }
        }
        leaf server-location {
          description
            "Enable CDP location server on interface";
          type empty;
        }
        leaf location {
          description
            "Exchange location information";
          type empty;
        }
      }
    }
  }

  grouping ncs_template_config-cdp-grouping {
    leaf run {
      description
        "Enable CDP";
      type empty;
    }
  }

  grouping ncs_rpc_notif_config-interface-cdp-grouping {
    container cdp {
      description
        "CDP interface subcommands";
      leaf enable {
        description
          "Enable CDP on interface";
        type boolean;
      }
      container tlv {
        description
          "Enable exchange of specific tlv information";
        container app {
          description
            "Enable/Configure Application TLV";
          presence "true";
          leaf tlvtype {
            description
              "Configure APP TLV";
            type uint16 {
              range "1001..65535";
            }
          }
          leaf value {
            description
              "Configure App TLV Value information";
            type string;
          }
        }
        leaf server-location {
          description
            "Enable CDP location server on interface";
          type empty;
        }
        leaf location {
          description
            "Exchange location information";
          type empty;
        }
      }
    }
  }

  grouping ncs_rpc_notif_config-cdp-grouping {
    leaf run {
      description
        "Enable CDP";
      type empty;
    }
  }

  grouping live_ncs_config-interface-cdp-grouping {
    container cdp {
      description
        "CDP interface subcommands";
      leaf enable {
        description
          "Enable CDP on interface";
        type boolean;
      }
      container tlv {
        description
          "Enable exchange of specific tlv information";
        container app {
          description
            "Enable/Configure Application TLV";
          presence "true";
          leaf tlvtype {
            description
              "Configure APP TLV";
            type uint16 {
              range "1001..65535";
            }
          }
          leaf value {
            description
              "Configure App TLV Value information";
            type string;
          }
        }
        leaf server-location {
          description
            "Enable CDP location server on interface";
          type empty;
        }
        leaf location {
          description
            "Exchange location information";
          type empty;
        }
      }
    }
  }

  grouping live_ncs_config-cdp-grouping {
    leaf run {
      description
        "Enable CDP";
      type empty;
    }
  }

  grouping config-interface-cdp-grouping {
    container cdp {
      description
        "CDP interface subcommands";
      leaf enable {
        description
          "Enable CDP on interface";
        type boolean;
      }
      container tlv {
        description
          "Enable exchange of specific tlv information";
        container app {
          description
            "Enable/Configure Application TLV";
          presence "true";
          leaf tlvtype {
            description
              "Configure APP TLV";
            type uint16 {
              range "1001..65535";
            }
          }
          leaf value {
            description
              "Configure App TLV Value information";
            type string;
          }
        }
        leaf server-location {
          description
            "Enable CDP location server on interface";
          type empty;
        }
        leaf location {
          description
            "Exchange location information";
          type empty;
        }
      }
    }
  }

  grouping config-cdp-grouping {
    leaf run {
      description
        "Enable CDP";
      type empty;
    }
  }

  augment "/ncs:devices/ncs:template/ncs:config/ios:native/ios:cdp" {
    uses ncs_template_config-cdp-grouping;
  }
  augment "/ncs:devices/ncs:device/ncs:live-status/ios:native/ios:cdp" {
    uses live_ncs_config-cdp-grouping {
      refine run {
        tailf:ncs-device-type "netconf";
        tailf:display-when "not(../../../../ncs:module) or ../../../../ncs:module[ncs:name='Cisco-IOS-XE-cdp'] or (../../../../ncs:live-status-protocol[not(ncs:capability)]) or (../../../../ncs:live-status-protocol/ncs:capability/ncs:module[.='Cisco-IOS-XE-cdp'])";
      }
    }
  }
  augment "/ncs:devices/ncs:device/ncs:config/ios:native/ios:cdp" {
    uses config-cdp-grouping {
      refine run {
        tailf:ncs-device-type "netconf";
        tailf:display-when "not(../../../../ncs:module) or ../../../../ncs:module[ncs:name='Cisco-IOS-XE-cdp']";
      }
    }
  }
  augment "/ncs:devices/ncs:template/ncs:config/ios:native/ios:interface/ios:FastEthernet" {
    uses ncs_template_config-interface-cdp-grouping;
  }
  augment "/ncs:devices/ncs:device/ncs:live-status/ios:native/ios:interface/ios:FastEthernet" {
    uses live_ncs_config-interface-cdp-grouping {
      refine cdp {
        tailf:ncs-device-type "netconf";
        tailf:display-when "not(../../../../../ncs:module) or ../../../../../ncs:module[ncs:name='Cisco-IOS-XE-cdp'] or (../../../../../ncs:live-status-protocol[not(ncs:capability)]) or (../../../../../ncs:live-status-protocol/ncs:capability/ncs:module[.='Cisco-IOS-XE-cdp'])";
      }
    }
  }
  augment "/ncs:devices/ncs:device/ncs:config/ios:native/ios:interface/ios:FastEthernet" {
    uses config-interface-cdp-grouping {
      refine cdp {
        tailf:ncs-device-type "netconf";
        tailf:display-when "not(../../../../../ncs:module) or ../../../../../ncs:module[ncs:name='Cisco-IOS-XE-cdp']";
      }
    }
  }
  augment "/ncs:devices/ncs:template/ncs:config/ios:native/ios:interface/ios:GigabitEthernet" {
    uses ncs_template_config-interface-cdp-grouping;
  }
  augment "/ncs:devices/ncs:device/ncs:live-status/ios:native/ios:interface/ios:GigabitEthernet" {
    uses live_ncs_config-interface-cdp-grouping {
      refine cdp {
        tailf:ncs-device-type "netconf";
        tailf:display-when "not(../../../../../ncs:module) or ../../../../../ncs:module[ncs:name='Cisco-IOS-XE-cdp'] or (../../../../../ncs:live-status-protocol[not(ncs:capability)]) or (../../../../../ncs:live-status-protocol/ncs:capability/ncs:module[.='Cisco-IOS-XE-cdp'])";
      }
    }
  }
  augment "/ncs:devices/ncs:device/ncs:config/ios:native/ios:interface/ios:GigabitEthernet" {
    uses config-interface-cdp-grouping {
      refine cdp {
        tailf:ncs-device-type "netconf";
        tailf:display-when "not(../../../../../ncs:module) or ../../../../../ncs:module[ncs:name='Cisco-IOS-XE-cdp']";
      }
    }
  }
  augment "/ncs:devices/ncs:template/ncs:config/ios:native/ios:interface/ios:TenGigabitEthernet" {
    uses ncs_template_config-interface-cdp-grouping;
  }
  augment "/ncs:devices/ncs:device/ncs:live-status/ios:native/ios:interface/ios:TenGigabitEthernet" {
    uses live_ncs_config-interface-cdp-grouping {
      refine cdp {
        tailf:ncs-device-type "netconf";
        tailf:display-when "not(../../../../../ncs:module) or ../../../../../ncs:module[ncs:name='Cisco-IOS-XE-cdp'] or (../../../../../ncs:live-status-protocol[not(ncs:capability)]) or (../../../../../ncs:live-status-protocol/ncs:capability/ncs:module[.='Cisco-IOS-XE-cdp'])";
      }
    }
  }
  augment "/ncs:devices/ncs:device/ncs:config/ios:native/ios:interface/ios:TenGigabitEthernet" {
    uses config-interface-cdp-grouping {
      refine cdp {
        tailf:ncs-device-type "netconf";
        tailf:display-when "not(../../../../../ncs:module) or ../../../../../ncs:module[ncs:name='Cisco-IOS-XE-cdp']";
      }
    }
  }
  augment "/ncs:devices/ncs:template/ncs:config/ios:native/ios:interface/ios:Tunnel" {
    uses ncs_template_config-interface-cdp-grouping;
  }
  augment "/ncs:devices/ncs:device/ncs:live-status/ios:native/ios:interface/ios:Tunnel" {
    uses live_ncs_config-interface-cdp-grouping {
      refine cdp {
        tailf:ncs-device-type "netconf";
        tailf:display-when "not(../../../../../ncs:module) or ../../../../../ncs:module[ncs:name='Cisco-IOS-XE-cdp'] or (../../../../../ncs:live-status-protocol[not(ncs:capability)]) or (../../../../../ncs:live-status-protocol/ncs:capability/ncs:module[.='Cisco-IOS-XE-cdp'])";
      }
    }
  }
  augment "/ncs:devices/ncs:device/ncs:config/ios:native/ios:interface/ios:Tunnel" {
    uses config-interface-cdp-grouping {
      refine cdp {
        tailf:ncs-device-type "netconf";
        tailf:display-when "not(../../../../../ncs:module) or ../../../../../ncs:module[ncs:name='Cisco-IOS-XE-cdp']";
      }
    }
  }
  augment "/ncs:devices/ncs:template/ncs:config/ios:native/ios:interface/ios:Virtual-Template" {
    uses ncs_template_config-interface-cdp-grouping;
  }
  augment "/ncs:devices/ncs:device/ncs:live-status/ios:native/ios:interface/ios:Virtual-Template" {
    uses live_ncs_config-interface-cdp-grouping {
      refine cdp {
        tailf:ncs-device-type "netconf";
        tailf:display-when "not(../../../../../ncs:module) or ../../../../../ncs:module[ncs:name='Cisco-IOS-XE-cdp'] or (../../../../../ncs:live-status-protocol[not(ncs:capability)]) or (../../../../../ncs:live-status-protocol/ncs:capability/ncs:module[.='Cisco-IOS-XE-cdp'])";
      }
    }
  }
  augment "/ncs:devices/ncs:device/ncs:config/ios:native/ios:interface/ios:Virtual-Template" {
    uses config-interface-cdp-grouping {
      refine cdp {
        tailf:ncs-device-type "netconf";
        tailf:display-when "not(../../../../../ncs:module) or ../../../../../ncs:module[ncs:name='Cisco-IOS-XE-cdp']";
      }
    }
  }
}
