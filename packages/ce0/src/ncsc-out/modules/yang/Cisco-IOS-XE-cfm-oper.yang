module Cisco-IOS-XE-cfm-oper {
  // Generated by yanger -t ncs
  tailf:ncs-device-type "netconf";

  yang-version "1";
  namespace "http://cisco.com/ns/yang/Cisco-IOS-XE-cfm-oper";
  prefix cfm-stats-ios-xe-oper;

  import ietf-yang-types {
    prefix yang;
  }
  import tailf-ncs {
    prefix ncs;
  }
  import tailf-common {
    prefix tailf;
  }

  organization "Cisco Systems, Inc.";
  contact
    "Cisco Systems, Inc. Customer Service Postal: 170 W Tasman Drive
     San Jose, CA 95134 Tel: +1 1800 553-NETS E-mail: cs-yang@cisco.com";
  description
    "This module contains a collection of YANG definitions for
     monitoring memory usage of processes in a Network Element.Copyright (c) 2016-2017 by Cisco Systems, Inc.All rights reserved.";

  revision 2017-02-07 {
    description
      "Initial revision";
  }

  typedef cfm-last-cleared-type {
    type enumeration {
      enum "never-cleared";
      enum "cleared-before";
    }
  }

  grouping ncs_template_mep-key {
    leaf domain-name {
      type string;
      description
        "The name of the Domain corresponding the the MEP.";
    }
    leaf ma-name {
      type string;
      description
        "The name of the MA corresponding the the MEP.";
    }
    leaf mpid {
      type string;
      description
        "ID of the MEP";
    }
  }

  grouping ncs_template_cfm-cleared-type {
    choice cleared-choice {
      description
        "The last time when the counters were cleared.";
      case never-cleared {
        leaf never {
          type empty;
        }
      }
      case cleared-before {
        leaf time {
          type string;
        }
      }
    }
  }

  grouping ncs_template_mep-params {
    container last-cleared {
      uses cfm-stats-ios-xe-oper:ncs_template_cfm-cleared-type;
    }
    leaf ccm-transmitted {
      type string;
      description
        "The number of CCMs transmitted from the local MEP.";
    }
    leaf ccm-seq-errors {
      type string;
      description
        "The number of CCM sequence number errors detected.";
    }
    leaf ltr-unexpected {
      type string;
      description
        "The number of unexpected linktrace reply packets
         received at this MEP.";
    }
    leaf lbr-transmitted {
      type string;
      description
        "The number of loopback reply packets transmitted
         from the local MEP.";
    }
    leaf lbr-seq-errors {
      type string;
      description
        "The number of loopback reply packets received
         with sequence number errors.";
    }
    leaf lbr-received-ok {
      type string;
      description
        "The number of valid loopback reply packets received.";
    }
    leaf lbr-received-bad {
      type string;
      description
        "The number of loopback reply packets received
         with corrupted data pattern";
    }
  }

  grouping ncs_rpc_notif_mep-key {
    leaf domain-name {
      type string;
      description
        "The name of the Domain corresponding the the MEP.";
    }
    leaf ma-name {
      type string;
      description
        "The name of the MA corresponding the the MEP.";
    }
    leaf mpid {
      type uint32;
      description
        "ID of the MEP";
    }
  }

  grouping ncs_rpc_notif_cfm-cleared-type {
    choice cleared-choice {
      description
        "The last time when the counters were cleared.";
      case never-cleared {
        leaf never {
          type empty;
        }
      }
      case cleared-before {
        leaf time {
          type string;
        }
      }
    }
  }

  grouping ncs_rpc_notif_mep-params {
    container last-cleared {
      uses cfm-stats-ios-xe-oper:ncs_rpc_notif_cfm-cleared-type;
    }
    leaf ccm-transmitted {
      type yang:counter64;
      description
        "The number of CCMs transmitted from the local MEP.";
    }
    leaf ccm-seq-errors {
      type yang:counter64;
      description
        "The number of CCM sequence number errors detected.";
    }
    leaf ltr-unexpected {
      type yang:counter64;
      description
        "The number of unexpected linktrace reply packets
         received at this MEP.";
    }
    leaf lbr-transmitted {
      type yang:counter64;
      description
        "The number of loopback reply packets transmitted
         from the local MEP.";
    }
    leaf lbr-seq-errors {
      type yang:counter64;
      description
        "The number of loopback reply packets received
         with sequence number errors.";
    }
    leaf lbr-received-ok {
      type yang:counter64;
      description
        "The number of valid loopback reply packets received.";
    }
    leaf lbr-received-bad {
      type yang:counter64;
      description
        "The number of loopback reply packets received
         with corrupted data pattern";
    }
  }

  grouping live_ncs_mep-key {
    leaf domain-name {
      type string;
      description
        "The name of the Domain corresponding the the MEP.";
    }
    leaf ma-name {
      type string;
      description
        "The name of the MA corresponding the the MEP.";
    }
    leaf mpid {
      type uint32;
      description
        "ID of the MEP";
    }
  }

  grouping live_ncs_cfm-cleared-type {
    choice cleared-choice {
      description
        "The last time when the counters were cleared.";
      case never-cleared {
        leaf never {
          type empty;
        }
      }
      case cleared-before {
        leaf time {
          type string;
        }
      }
    }
  }

  grouping live_ncs_mep-params {
    container last-cleared {
      uses cfm-stats-ios-xe-oper:live_ncs_cfm-cleared-type;
    }
    leaf ccm-transmitted {
      type yang:counter64;
      description
        "The number of CCMs transmitted from the local MEP.";
    }
    leaf ccm-seq-errors {
      type yang:counter64;
      description
        "The number of CCM sequence number errors detected.";
    }
    leaf ltr-unexpected {
      type yang:counter64;
      description
        "The number of unexpected linktrace reply packets
         received at this MEP.";
    }
    leaf lbr-transmitted {
      type yang:counter64;
      description
        "The number of loopback reply packets transmitted
         from the local MEP.";
    }
    leaf lbr-seq-errors {
      type yang:counter64;
      description
        "The number of loopback reply packets received
         with sequence number errors.";
    }
    leaf lbr-received-ok {
      type yang:counter64;
      description
        "The number of valid loopback reply packets received.";
    }
    leaf lbr-received-bad {
      type yang:counter64;
      description
        "The number of loopback reply packets received
         with corrupted data pattern";
    }
  }

  grouping mep-key {
    leaf domain-name {
      type string;
      description
        "The name of the Domain corresponding the the MEP.";
    }
    leaf ma-name {
      type string;
      description
        "The name of the MA corresponding the the MEP.";
    }
    leaf mpid {
      type uint32;
      description
        "ID of the MEP";
    }
  }

  grouping cfm-cleared-type {
    choice cleared-choice {
      description
        "The last time when the counters were cleared.";
      case never-cleared {
        leaf never {
          type empty;
        }
      }
      case cleared-before {
        leaf time {
          type string;
        }
      }
    }
  }

  grouping mep-params {
    container last-cleared {
      uses cfm-stats-ios-xe-oper:cfm-cleared-type;
    }
    leaf ccm-transmitted {
      type yang:counter64;
      description
        "The number of CCMs transmitted from the local MEP.";
    }
    leaf ccm-seq-errors {
      type yang:counter64;
      description
        "The number of CCM sequence number errors detected.";
    }
    leaf ltr-unexpected {
      type yang:counter64;
      description
        "The number of unexpected linktrace reply packets
         received at this MEP.";
    }
    leaf lbr-transmitted {
      type yang:counter64;
      description
        "The number of loopback reply packets transmitted
         from the local MEP.";
    }
    leaf lbr-seq-errors {
      type yang:counter64;
      description
        "The number of loopback reply packets received
         with sequence number errors.";
    }
    leaf lbr-received-ok {
      type yang:counter64;
      description
        "The number of valid loopback reply packets received.";
    }
    leaf lbr-received-bad {
      type yang:counter64;
      description
        "The number of loopback reply packets received
         with corrupted data pattern";
    }
  }

  augment "/ncs:devices/ncs:device/ncs:config" {
    // NCS drop config false container 'cfm-statistics'
  }
  augment "/ncs:devices/ncs:device/ncs:live-status" {
    container cfm-statistics {
      tailf:ncs-device-type "netconf";
      tailf:display-when "not(../../ncs:module) or ../../ncs:module[ncs:name='Cisco-IOS-XE-cfm-oper'] or (../../ncs:live-status-protocol[not(ncs:capability)]) or (../../ncs:live-status-protocol/ncs:capability/ncs:module[.='Cisco-IOS-XE-cfm-oper'])";
      description
        "Data nodes for CFM Statistics.";
      container cfm-meps {
        list cfm-mep {
          key "domain-name ma-name mpid";
          description
            "The list of MEP entries in the system.";
          uses cfm-stats-ios-xe-oper:live_ncs_mep-key;
          uses cfm-stats-ios-xe-oper:live_ncs_mep-params;
        }
      }
    }
  }
  augment "/ncs:devices/ncs:template/ncs:config" {
    // NCS drop config false container 'cfm-statistics'
  }
}
