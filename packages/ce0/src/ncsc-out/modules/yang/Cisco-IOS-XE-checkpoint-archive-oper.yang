module Cisco-IOS-XE-checkpoint-archive-oper {
  // Generated by yanger -t ncs
  tailf:ncs-device-type "netconf";

  yang-version "1";
  namespace "http://cisco.com/ns/yang/Cisco-IOS-XE-checkpoint-archive-oper";
  prefix checkpoint-archive-ios-xe-oper;

  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring the checkpoint archives in a Network Element.
     Copyright (c) 2016-2017 by Cisco Systems, Inc.
     All rights reserved.";

  revision 2017-04-01 {
    description
      "Top level container name change";
    reference "2.0.0";
  }
  revision 2017-02-07 {
    description
      "Initial revision";
    reference "1.0.0";
  }

  grouping ncs_template_archive {
    description
      "Archive information";
    leaf number {
      type string;
      description
        "The archive number";
    }
    leaf name {
      type string;
      description
        "The name of the archive";
    }
  }

  grouping ncs_template_checkpoint-archive {
    description
      "Checkpoint archive information";
    leaf max {
      type string;
      description
        "The maxium number of archives";
    }
    leaf current {
      type string;
      description
        "The current number of archives";
    }
    leaf recent {
      type string;
      description
        "The most recent archive";
    }
    container archives {
      description
        "Archive information";
      list archive {
        // NCS patched for predictable order
        ordered-by user;
        key "number";
        description
          "List of archives";
        uses checkpoint-archive-ios-xe-oper:ncs_template_archive;
      }
    }
  }

  grouping ncs_rpc_notif_archive {
    description
      "Archive information";
    leaf number {
      type uint16;
      description
        "The archive number";
    }
    leaf name {
      type string;
      description
        "The name of the archive";
    }
  }

  grouping ncs_rpc_notif_checkpoint-archive {
    description
      "Checkpoint archive information";
    leaf max {
      type uint8;
      description
        "The maxium number of archives";
    }
    leaf current {
      type uint8;
      description
        "The current number of archives";
    }
    leaf recent {
      type string;
      description
        "The most recent archive";
    }
    container archives {
      description
        "Archive information";
      list archive {
        key "number";
        description
          "List of archives";
        uses checkpoint-archive-ios-xe-oper:ncs_rpc_notif_archive;
      }
    }
  }

  grouping live_ncs_archive {
    description
      "Archive information";
    leaf number {
      type uint16;
      description
        "The archive number";
    }
    leaf name {
      type string;
      description
        "The name of the archive";
    }
  }

  grouping live_ncs_checkpoint-archive {
    description
      "Checkpoint archive information";
    leaf max {
      type uint8;
      description
        "The maxium number of archives";
    }
    leaf current {
      type uint8;
      description
        "The current number of archives";
    }
    leaf recent {
      type string;
      description
        "The most recent archive";
    }
    container archives {
      description
        "Archive information";
      list archive {
        key "number";
        description
          "List of archives";
        uses checkpoint-archive-ios-xe-oper:live_ncs_archive;
      }
    }
  }

  grouping archive {
    description
      "Archive information";
    leaf number {
      type uint16;
      description
        "The archive number";
    }
    leaf name {
      type string;
      description
        "The name of the archive";
    }
  }

  grouping checkpoint-archive {
    description
      "Checkpoint archive information";
    leaf max {
      type uint8;
      description
        "The maxium number of archives";
    }
    leaf current {
      type uint8;
      description
        "The current number of archives";
    }
    leaf recent {
      type string;
      description
        "The most recent archive";
    }
    container archives {
      description
        "Archive information";
      list archive {
        key "number";
        description
          "List of archives";
        uses checkpoint-archive-ios-xe-oper:archive;
      }
    }
  }

  augment "/ncs:devices/ncs:device/ncs:config" {
    // NCS drop config false container 'checkpoint-archives'
  }
  augment "/ncs:devices/ncs:device/ncs:live-status" {
    container checkpoint-archives {
      tailf:ncs-device-type "netconf";
      tailf:display-when "not(../../ncs:module) or ../../ncs:module[ncs:name='Cisco-IOS-XE-checkpoint-archive-oper'] or (../../ncs:live-status-protocol[not(ncs:capability)]) or (../../ncs:live-status-protocol/ncs:capability/ncs:module[.='Cisco-IOS-XE-checkpoint-archive-oper'])";
      description
        "Contents of the checkpoint archive information base";
      uses checkpoint-archive-ios-xe-oper:live_ncs_checkpoint-archive;
    }
  }
  augment "/ncs:devices/ncs:template/ncs:config" {
    // NCS drop config false container 'checkpoint-archives'
  }
}
