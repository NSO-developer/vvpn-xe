module Cisco-IOS-XE-eem {
  // Generated by yanger -t ncs
  tailf:ncs-device-type "netconf";

  namespace "http://cisco.com/ns/yang/Cisco-IOS-XE-eem";
  prefix ios-eem;

  import ietf-inet-types {
    prefix inet;
  }
  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Embedded Event Manager (EEM) Yang model.
     Copyright (c) 2016 by Cisco Systems, Inc.
     All rights reserved.";

  revision 2017-04-13 {
    description
      "Add event track";
  }
  revision 2017-04-10 {
    description
      "Add cli command and exit for action";
  }
  revision 2017-02-07 {
    description
      "Initial revision";
  }

  typedef operator-type {
    type enumeration {
      enum "eq";
      enum "ge";
      enum "gt";
      enum "le";
      enum "lt";
      enum "ne";
    }
  }

  grouping ncs_template_config-eem-grouping {
    container manager {
      description
        "Event Manager configuration commands";
      list environment {
        // NCS patched for predictable order
        ordered-by user;
        description
          "Set an Embedded Event Manager global environment variable";
        key "name";
        leaf name {
          type string;
        }
        leaf value {
          type string;
        }
      }
      container directory {
        description
          "Set Embedded Event Manager directory information";
        container user {
          description
            "Set Embedded Event Manager user directory information";
          leaf policy {
            description
              "Set Embedded Event Manager user policy directory";
            type string;
          }
        }
      }
      container session {
        description
          "Set Embedded Event Manager session attributes";
        container cli {
          description
            "Set Embedded Event Manager session cli attributes";
          container username {
            description
              "Set username used in Embedded Event Manager cli sessions";
            list username_in_word {
              // NCS patched for predictable order
              ordered-by user;
              key "username_in_word";
              leaf username_in_word {
                type string;
              }
              leaf privilege {
                description
                  "Set user privilege level";
                type string;
              }
            }
          }
        }
      }
      list applet {
        // NCS patched for predictable order
        ordered-by user;
        description
          "Register an Event Manager applet";
        key "name";
        leaf name {
          type string;
        }
        leaf authorization {
          description
            "Specify an authorization type for the applet";
          type string;
        }
        leaf class {
          description
            "Specify a class for the applet";
          type string;
        }
        leaf trap {
          description
            "Generate an SNMP trap when applet is triggered.";
          type empty;
        }
        container event {
          description
            "Add or modify event information";
          container timer {
            description
              "Timer event";
            container watchdog {
              description
                "Watchdog timer event";
              container name {
                description
                  "Name of the timer";
                list timer-name {
                  // NCS patched for predictable order
                  ordered-by user;
                  key "timer-name";
                  leaf timer-name {
                    type string;
                  }
                  container time {
                    description
                      "Time period for watchdog / countdown / absolute timer";
                    list time-in-seconds {
                      // NCS patched for predictable order
                      ordered-by user;
                      key "time-in-seconds";
                      leaf time-in-seconds {
                        description
                          "Enter seconds[.milliseconds] value";
                        type string;
                      }
                      container maxrun {
                        description
                          "Maximum runtime of applet";
                        list timer-in-seconds {
                          // NCS patched for predictable order
                          ordered-by user;
                          key "timer-in-seconds";
                          leaf timer-in-seconds {
                            description
                              "Enter seconds[.milliseconds] value";
                            type string;
                          }
                          leaf ratelimit {
                            description
                              "Limit trigger to once per given time period.
                               Enter seconds[.milliseconds] value";
                            type string;
                          }
                        }
                      }
                    }
                  }
                }
              }
            }
          }
          container snmp-notification {
            description
              "SNMP Notification Event";
            leaf oid {
              description
                "Object ID of data element";
              type string;
            }
            leaf oid-val {
              description
                "Comparison value";
              type string;
            }
            leaf op {
              description
                "Operator";
              type string;
            }
            leaf src-ip-address {
              description
                "Source ip address";
              type string;
            }
            leaf dest-ip-address {
              description
                "Destination ip address";
              type string;
            }
          }
          container syslog {
            description
              "Syslog event";
            leaf pattern {
              description
                "Pattern match string for the entire message";
              type string;
            }
          }
          container track {
            description
              "Tracking object event";
            leaf track-object-number {
              description
                "Tracking object number";
              type string;
            }
            leaf state {
              description
                "State of tracking object";
              type string;
            }
          }
        }
        list action {
          // NCS patched for predictable order
          ordered-by user;
          description
            "Add or modify an action statement";
          key "name";
          leaf name {
            type string;
          }
          container cli {
            description
              "Execute a CLI command";
            leaf command {
              description
                "CLI command";
              type string;
            }
          }
          container if {
            description
              "if conditional";
            leaf string-op-1 {
              type string;
            }
            leaf keyword {
              type string;
            }
            leaf string-op-2 {
              type string;
            }
            leaf goto {
              description
                "goto label";
              type string;
            }
          }
          container info {
            description
              "Obtain system specific information";
            container type {
              description
                "Type of information to obtain";
              container snmp {
                description
                  "SNMP information";
                container var {
                  description
                    "Trap variable";
                  leaf variable-name {
                    type string;
                  }
                  leaf oid {
                    description
                      "SNMP object id";
                    type string;
                  }
                  leaf oid-type {
                    type string;
                  }
                  leaf oid-type-value {
                    type string;
                  }
                }
                container trap {
                  description
                    "SNMP trap";
                  leaf enterprise-oid {
                    description
                      "Enterprise oid";
                    type string;
                  }
                  leaf generic-trapnum {
                    description
                      "Generic trap number";
                    type string;
                  }
                  leaf specific-trapnum {
                    description
                      "Specific trap number";
                    type string;
                  }
                  leaf trap-oid {
                    description
                      "Trap oid";
                    type string;
                  }
                  leaf trap-var {
                    description
                      "Trap variable";
                    type string;
                  }
                }
              }
            }
          }
          leaf end {
            description
              "end conditional block";
            type empty;
          }
          container regexp {
            description
              "regular expression match";
            leaf string-pattern {
              type string;
            }
            leaf string-input {
              type string;
            }
            leaf string-match {
              type string;
            }
            leaf string-submatch1 {
              type string;
            }
            leaf string-submatch2 {
              type string;
            }
            leaf string-submatch3 {
              type string;
            }
          }
          container snmp-trap {
            description
              "Send an SNMP trap";
            presence "true";
            leaf intdata1 {
              description
                "SNMP integer data1";
              type string;
            }
            leaf intdata2 {
              description
                "SNMP integer data2";
              type string;
            }
            leaf strdata {
              description
                "SNMP trap string";
              type string;
            }
          }
          container string {
            description
              "string commands";
            leaf trim {
              description
                "trim characters from both ends of string";
              type string;
            }
          }
          container syslog {
            description
              "Log a syslog message";
            leaf facility {
              description
                "Facility string";
              type string;
            }
            leaf msg {
              description
                "Syslog message";
              type string;
            }
            leaf priority {
              description
                "Priority of syslog message";
              type string;
            }
          }
          leaf exit {
            description
              "Exit from applet run";
            type empty;
          }
        }
        leaf description {
          description
            "Add or modify an applet description";
          type string;
        }
        container trigger {
          description
            "Enter applet trigger configuration submode";
        }
      }
    }
  }

  grouping ncs_rpc_notif_config-eem-grouping {
    container manager {
      description
        "Event Manager configuration commands";
      list environment {
        description
          "Set an Embedded Event Manager global environment variable";
        key "name";
        leaf name {
          type string;
        }
        leaf value {
          type string;
        }
      }
      container directory {
        description
          "Set Embedded Event Manager directory information";
        container user {
          description
            "Set Embedded Event Manager user directory information";
          leaf policy {
            description
              "Set Embedded Event Manager user policy directory";
            type string;
          }
        }
      }
      container session {
        description
          "Set Embedded Event Manager session attributes";
        container cli {
          description
            "Set Embedded Event Manager session cli attributes";
          container username {
            description
              "Set username used in Embedded Event Manager cli sessions";
            list username_in_word {
              key "username_in_word";
              leaf username_in_word {
                type string;
              }
              leaf privilege {
                description
                  "Set user privilege level";
                type uint8 {
                  range "0..15";
                }
              }
            }
          }
        }
      }
      list applet {
        description
          "Register an Event Manager applet";
        key "name";
        leaf name {
          type string;
        }
        leaf authorization {
          description
            "Specify an authorization type for the applet";
          type enumeration {
            enum "bypass";
          }
        }
        leaf class {
          description
            "Specify a class for the applet";
          type string {
            pattern '[A-Z]|default';
          }
        }
        leaf trap {
          description
            "Generate an SNMP trap when applet is triggered.";
          type empty;
        }
        container event {
          description
            "Add or modify event information";
          container timer {
            description
              "Timer event";
            container watchdog {
              description
                "Watchdog timer event";
              container name {
                description
                  "Name of the timer";
                list timer-name {
                  key "timer-name";
                  leaf timer-name {
                    type string;
                  }
                  container time {
                    description
                      "Time period for watchdog / countdown / absolute timer";
                    list time-in-seconds {
                      key "time-in-seconds";
                      leaf time-in-seconds {
                        description
                          "Enter seconds[.milliseconds] value";
                        type uint32 {
                          range "1..2085978494";
                        }
                      }
                      container maxrun {
                        description
                          "Maximum runtime of applet";
                        list timer-in-seconds {
                          key "timer-in-seconds";
                          leaf timer-in-seconds {
                            description
                              "Enter seconds[.milliseconds] value";
                            type uint32 {
                              range "0..31536000";
                            }
                          }
                          leaf ratelimit {
                            description
                              "Limit trigger to once per given time period.
                               Enter seconds[.milliseconds] value";
                            type uint32 {
                              range "0..31536000";
                            }
                          }
                        }
                      }
                    }
                  }
                }
              }
            }
          }
          container snmp-notification {
            description
              "SNMP Notification Event";
            leaf oid {
              description
                "Object ID of data element";
              type string;
            }
            leaf oid-val {
              description
                "Comparison value";
              type string;
            }
            leaf op {
              description
                "Operator";
              type operator-type;
            }
            leaf src-ip-address {
              description
                "Source ip address";
              type union {
                type inet:ipv4-address;
                type inet:ipv6-address;
              }
            }
            leaf dest-ip-address {
              description
                "Destination ip address";
              type union {
                type inet:ipv4-address;
                type inet:ipv6-address;
              }
            }
          }
          container syslog {
            description
              "Syslog event";
            leaf pattern {
              description
                "Pattern match string for the entire message";
              type string;
            }
          }
          container track {
            description
              "Tracking object event";
            leaf track-object-number {
              description
                "Tracking object number";
              type uint16 {
                range "1..1000";
              }
            }
            leaf state {
              description
                "State of tracking object";
              type enumeration {
                enum "any";
                enum "down";
                enum "up";
              }
            }
          }
        }
        list action {
          description
            "Add or modify an action statement";
          ordered-by user;
          key "name";
          leaf name {
            type string;
          }
          container cli {
            description
              "Execute a CLI command";
            leaf command {
              description
                "CLI command";
              type string;
            }
          }
          container if {
            description
              "if conditional";
            leaf string-op-1 {
              type string;
            }
            leaf keyword {
              type operator-type;
            }
            leaf string-op-2 {
              type string;
            }
            leaf goto {
              description
                "goto label";
              type string;
            }
          }
          container info {
            description
              "Obtain system specific information";
            container type {
              description
                "Type of information to obtain";
              container snmp {
                description
                  "SNMP information";
                container var {
                  description
                    "Trap variable";
                  leaf variable-name {
                    type string;
                  }
                  leaf oid {
                    description
                      "SNMP object id";
                    type string;
                  }
                  leaf oid-type {
                    type enumeration {
                      enum "counter";
                      enum "gauge";
                      enum "int";
                      enum "ipv4";
                      enum "octet";
                      enum "string";
                      enum "uint";
                    }
                  }
                  leaf oid-type-value {
                    type string;
                  }
                }
                container trap {
                  description
                    "SNMP trap";
                  leaf enterprise-oid {
                    description
                      "Enterprise oid";
                    type string;
                  }
                  leaf generic-trapnum {
                    description
                      "Generic trap number";
                    type uint32;
                  }
                  leaf specific-trapnum {
                    description
                      "Specific trap number";
                    type uint32;
                  }
                  leaf trap-oid {
                    description
                      "Trap oid";
                    type string;
                  }
                  leaf trap-var {
                    description
                      "Trap variable";
                    type string;
                  }
                }
              }
            }
          }
          leaf end {
            description
              "end conditional block";
            type empty;
          }
          container regexp {
            description
              "regular expression match";
            leaf string-pattern {
              type string;
            }
            leaf string-input {
              type string;
            }
            leaf string-match {
              type string;
            }
            leaf string-submatch1 {
              type string;
            }
            leaf string-submatch2 {
              type string;
            }
            leaf string-submatch3 {
              type string;
            }
          }
          container snmp-trap {
            description
              "Send an SNMP trap";
            presence "true";
            leaf intdata1 {
              description
                "SNMP integer data1";
              type int32;
            }
            leaf intdata2 {
              description
                "SNMP integer data2";
              type int32;
            }
            leaf strdata {
              description
                "SNMP trap string";
              type string;
            }
          }
          container string {
            description
              "string commands";
            leaf trim {
              description
                "trim characters from both ends of string";
              type string;
            }
          }
          container syslog {
            description
              "Log a syslog message";
            leaf facility {
              description
                "Facility string";
              type string;
            }
            leaf msg {
              description
                "Syslog message";
              type string;
            }
            leaf priority {
              description
                "Priority of syslog message";
              type ios:logging-level-type;
            }
          }
          leaf exit {
            description
              "Exit from applet run";
            type empty;
          }
        }
        leaf description {
          description
            "Add or modify an applet description";
          type string;
        }
        container trigger {
          description
            "Enter applet trigger configuration submode";
        }
      }
    }
  }

  grouping live_ncs_config-eem-grouping {
    container manager {
      description
        "Event Manager configuration commands";
      list environment {
        description
          "Set an Embedded Event Manager global environment variable";
        key "name";
        leaf name {
          type string;
        }
        leaf value {
          type string;
        }
      }
      container directory {
        description
          "Set Embedded Event Manager directory information";
        container user {
          description
            "Set Embedded Event Manager user directory information";
          leaf policy {
            description
              "Set Embedded Event Manager user policy directory";
            type string;
          }
        }
      }
      container session {
        description
          "Set Embedded Event Manager session attributes";
        container cli {
          description
            "Set Embedded Event Manager session cli attributes";
          container username {
            description
              "Set username used in Embedded Event Manager cli sessions";
            list username_in_word {
              key "username_in_word";
              leaf username_in_word {
                type string;
              }
              leaf privilege {
                description
                  "Set user privilege level";
                type uint8 {
                  range "0..15";
                }
              }
            }
          }
        }
      }
      list applet {
        description
          "Register an Event Manager applet";
        key "name";
        leaf name {
          type string;
        }
        leaf authorization {
          description
            "Specify an authorization type for the applet";
          type enumeration {
            enum "bypass";
          }
        }
        leaf class {
          description
            "Specify a class for the applet";
          type string {
            pattern '[A-Z]|default';
          }
        }
        leaf trap {
          description
            "Generate an SNMP trap when applet is triggered.";
          type empty;
        }
        container event {
          description
            "Add or modify event information";
          container timer {
            description
              "Timer event";
            container watchdog {
              description
                "Watchdog timer event";
              container name {
                description
                  "Name of the timer";
                list timer-name {
                  key "timer-name";
                  leaf timer-name {
                    type string;
                  }
                  container time {
                    description
                      "Time period for watchdog / countdown / absolute timer";
                    list time-in-seconds {
                      key "time-in-seconds";
                      leaf time-in-seconds {
                        description
                          "Enter seconds[.milliseconds] value";
                        type uint32 {
                          range "1..2085978494";
                        }
                      }
                      container maxrun {
                        description
                          "Maximum runtime of applet";
                        list timer-in-seconds {
                          key "timer-in-seconds";
                          leaf timer-in-seconds {
                            description
                              "Enter seconds[.milliseconds] value";
                            type uint32 {
                              range "0..31536000";
                            }
                          }
                          leaf ratelimit {
                            description
                              "Limit trigger to once per given time period.
                               Enter seconds[.milliseconds] value";
                            type uint32 {
                              range "0..31536000";
                            }
                          }
                        }
                      }
                    }
                  }
                }
              }
            }
          }
          container snmp-notification {
            description
              "SNMP Notification Event";
            leaf oid {
              description
                "Object ID of data element";
              type string;
            }
            leaf oid-val {
              description
                "Comparison value";
              type string;
            }
            leaf op {
              description
                "Operator";
              type operator-type;
            }
            leaf src-ip-address {
              description
                "Source ip address";
              type union {
                type inet:ipv4-address;
                type inet:ipv6-address;
              }
            }
            leaf dest-ip-address {
              description
                "Destination ip address";
              type union {
                type inet:ipv4-address;
                type inet:ipv6-address;
              }
            }
          }
          container syslog {
            description
              "Syslog event";
            leaf pattern {
              description
                "Pattern match string for the entire message";
              type string;
            }
          }
          container track {
            description
              "Tracking object event";
            leaf track-object-number {
              description
                "Tracking object number";
              type uint16 {
                range "1..1000";
              }
            }
            leaf state {
              description
                "State of tracking object";
              type enumeration {
                enum "any";
                enum "down";
                enum "up";
              }
            }
          }
        }
        list action {
          description
            "Add or modify an action statement";
          ordered-by user;
          key "name";
          leaf name {
            type string;
          }
          container cli {
            description
              "Execute a CLI command";
            leaf command {
              description
                "CLI command";
              type string;
            }
          }
          container if {
            description
              "if conditional";
            leaf string-op-1 {
              type string;
            }
            leaf keyword {
              type operator-type;
            }
            leaf string-op-2 {
              type string;
            }
            leaf goto {
              description
                "goto label";
              type string;
            }
          }
          container info {
            description
              "Obtain system specific information";
            container type {
              description
                "Type of information to obtain";
              container snmp {
                description
                  "SNMP information";
                container var {
                  description
                    "Trap variable";
                  leaf variable-name {
                    type string;
                  }
                  leaf oid {
                    description
                      "SNMP object id";
                    type string;
                  }
                  leaf oid-type {
                    type enumeration {
                      enum "counter";
                      enum "gauge";
                      enum "int";
                      enum "ipv4";
                      enum "octet";
                      enum "string";
                      enum "uint";
                    }
                  }
                  leaf oid-type-value {
                    type string;
                  }
                }
                container trap {
                  description
                    "SNMP trap";
                  leaf enterprise-oid {
                    description
                      "Enterprise oid";
                    type string;
                  }
                  leaf generic-trapnum {
                    description
                      "Generic trap number";
                    type uint32;
                  }
                  leaf specific-trapnum {
                    description
                      "Specific trap number";
                    type uint32;
                  }
                  leaf trap-oid {
                    description
                      "Trap oid";
                    type string;
                  }
                  leaf trap-var {
                    description
                      "Trap variable";
                    type string;
                  }
                }
              }
            }
          }
          leaf end {
            description
              "end conditional block";
            type empty;
          }
          container regexp {
            description
              "regular expression match";
            leaf string-pattern {
              type string;
            }
            leaf string-input {
              type string;
            }
            leaf string-match {
              type string;
            }
            leaf string-submatch1 {
              type string;
            }
            leaf string-submatch2 {
              type string;
            }
            leaf string-submatch3 {
              type string;
            }
          }
          container snmp-trap {
            description
              "Send an SNMP trap";
            presence "true";
            leaf intdata1 {
              description
                "SNMP integer data1";
              type int32;
            }
            leaf intdata2 {
              description
                "SNMP integer data2";
              type int32;
            }
            leaf strdata {
              description
                "SNMP trap string";
              type string;
            }
          }
          container string {
            description
              "string commands";
            leaf trim {
              description
                "trim characters from both ends of string";
              type string;
            }
          }
          container syslog {
            description
              "Log a syslog message";
            leaf facility {
              description
                "Facility string";
              type string;
            }
            leaf msg {
              description
                "Syslog message";
              type string;
            }
            leaf priority {
              description
                "Priority of syslog message";
              type ios:logging-level-type;
            }
          }
          leaf exit {
            description
              "Exit from applet run";
            type empty;
          }
        }
        leaf description {
          description
            "Add or modify an applet description";
          type string;
        }
        container trigger {
          description
            "Enter applet trigger configuration submode";
        }
      }
    }
  }

  grouping config-eem-grouping {
    container manager {
      description
        "Event Manager configuration commands";
      list environment {
        description
          "Set an Embedded Event Manager global environment variable";
        key "name";
        leaf name {
          type string;
        }
        leaf value {
          type string;
        }
      }
      container directory {
        description
          "Set Embedded Event Manager directory information";
        container user {
          description
            "Set Embedded Event Manager user directory information";
          leaf policy {
            description
              "Set Embedded Event Manager user policy directory";
            type string;
          }
        }
      }
      container session {
        description
          "Set Embedded Event Manager session attributes";
        container cli {
          description
            "Set Embedded Event Manager session cli attributes";
          container username {
            description
              "Set username used in Embedded Event Manager cli sessions";
            list username_in_word {
              key "username_in_word";
              leaf username_in_word {
                type string;
              }
              leaf privilege {
                description
                  "Set user privilege level";
                type uint8 {
                  range "0..15";
                }
              }
            }
          }
        }
      }
      list applet {
        description
          "Register an Event Manager applet";
        key "name";
        leaf name {
          type string;
        }
        leaf authorization {
          description
            "Specify an authorization type for the applet";
          type enumeration {
            enum "bypass";
          }
        }
        leaf class {
          description
            "Specify a class for the applet";
          type string {
            pattern '[A-Z]|default';
          }
        }
        leaf trap {
          description
            "Generate an SNMP trap when applet is triggered.";
          type empty;
        }
        container event {
          description
            "Add or modify event information";
          container timer {
            description
              "Timer event";
            container watchdog {
              description
                "Watchdog timer event";
              container name {
                description
                  "Name of the timer";
                list timer-name {
                  key "timer-name";
                  leaf timer-name {
                    type string;
                  }
                  container time {
                    description
                      "Time period for watchdog / countdown / absolute timer";
                    list time-in-seconds {
                      key "time-in-seconds";
                      leaf time-in-seconds {
                        description
                          "Enter seconds[.milliseconds] value";
                        type uint32 {
                          range "1..2085978494";
                        }
                      }
                      container maxrun {
                        description
                          "Maximum runtime of applet";
                        list timer-in-seconds {
                          key "timer-in-seconds";
                          leaf timer-in-seconds {
                            description
                              "Enter seconds[.milliseconds] value";
                            type uint32 {
                              range "0..31536000";
                            }
                          }
                          leaf ratelimit {
                            description
                              "Limit trigger to once per given time period.
                               Enter seconds[.milliseconds] value";
                            type uint32 {
                              range "0..31536000";
                            }
                          }
                        }
                      }
                    }
                  }
                }
              }
            }
          }
          container snmp-notification {
            description
              "SNMP Notification Event";
            leaf oid {
              description
                "Object ID of data element";
              type string;
            }
            leaf oid-val {
              description
                "Comparison value";
              type string;
            }
            leaf op {
              description
                "Operator";
              type operator-type;
            }
            leaf src-ip-address {
              description
                "Source ip address";
              type union {
                type inet:ipv4-address;
                type inet:ipv6-address;
              }
            }
            leaf dest-ip-address {
              description
                "Destination ip address";
              type union {
                type inet:ipv4-address;
                type inet:ipv6-address;
              }
            }
          }
          container syslog {
            description
              "Syslog event";
            leaf pattern {
              description
                "Pattern match string for the entire message";
              type string;
            }
          }
          container track {
            description
              "Tracking object event";
            leaf track-object-number {
              description
                "Tracking object number";
              type uint16 {
                range "1..1000";
              }
            }
            leaf state {
              description
                "State of tracking object";
              type enumeration {
                enum "any";
                enum "down";
                enum "up";
              }
            }
          }
        }
        list action {
          description
            "Add or modify an action statement";
          ordered-by user;
          key "name";
          leaf name {
            type string;
          }
          container cli {
            description
              "Execute a CLI command";
            leaf command {
              description
                "CLI command";
              type string;
            }
          }
          container if {
            description
              "if conditional";
            leaf string-op-1 {
              type string;
            }
            leaf keyword {
              type operator-type;
            }
            leaf string-op-2 {
              type string;
            }
            leaf goto {
              description
                "goto label";
              type string;
            }
          }
          container info {
            description
              "Obtain system specific information";
            container type {
              description
                "Type of information to obtain";
              container snmp {
                description
                  "SNMP information";
                container var {
                  description
                    "Trap variable";
                  leaf variable-name {
                    type string;
                  }
                  leaf oid {
                    description
                      "SNMP object id";
                    type string;
                  }
                  leaf oid-type {
                    type enumeration {
                      enum "counter";
                      enum "gauge";
                      enum "int";
                      enum "ipv4";
                      enum "octet";
                      enum "string";
                      enum "uint";
                    }
                  }
                  leaf oid-type-value {
                    type string;
                  }
                }
                container trap {
                  description
                    "SNMP trap";
                  leaf enterprise-oid {
                    description
                      "Enterprise oid";
                    type string;
                  }
                  leaf generic-trapnum {
                    description
                      "Generic trap number";
                    type uint32;
                  }
                  leaf specific-trapnum {
                    description
                      "Specific trap number";
                    type uint32;
                  }
                  leaf trap-oid {
                    description
                      "Trap oid";
                    type string;
                  }
                  leaf trap-var {
                    description
                      "Trap variable";
                    type string;
                  }
                }
              }
            }
          }
          leaf end {
            description
              "end conditional block";
            type empty;
          }
          container regexp {
            description
              "regular expression match";
            leaf string-pattern {
              type string;
            }
            leaf string-input {
              type string;
            }
            leaf string-match {
              type string;
            }
            leaf string-submatch1 {
              type string;
            }
            leaf string-submatch2 {
              type string;
            }
            leaf string-submatch3 {
              type string;
            }
          }
          container snmp-trap {
            description
              "Send an SNMP trap";
            presence "true";
            leaf intdata1 {
              description
                "SNMP integer data1";
              type int32;
            }
            leaf intdata2 {
              description
                "SNMP integer data2";
              type int32;
            }
            leaf strdata {
              description
                "SNMP trap string";
              type string;
            }
          }
          container string {
            description
              "string commands";
            leaf trim {
              description
                "trim characters from both ends of string";
              type string;
            }
          }
          container syslog {
            description
              "Log a syslog message";
            leaf facility {
              description
                "Facility string";
              type string;
            }
            leaf msg {
              description
                "Syslog message";
              type string;
            }
            leaf priority {
              description
                "Priority of syslog message";
              type ios:logging-level-type;
            }
          }
          leaf exit {
            description
              "Exit from applet run";
            type empty;
          }
        }
        leaf description {
          description
            "Add or modify an applet description";
          type string;
        }
        container trigger {
          description
            "Enter applet trigger configuration submode";
        }
      }
    }
  }

  augment "/ncs:devices/ncs:template/ncs:config/ios:native/ios:event" {
    uses ncs_template_config-eem-grouping;
  }
  augment "/ncs:devices/ncs:device/ncs:live-status/ios:native/ios:event" {
    uses live_ncs_config-eem-grouping {
      refine manager {
        tailf:ncs-device-type "netconf";
        tailf:display-when "not(../../../../ncs:module) or ../../../../ncs:module[ncs:name='Cisco-IOS-XE-eem'] or (../../../../ncs:live-status-protocol[not(ncs:capability)]) or (../../../../ncs:live-status-protocol/ncs:capability/ncs:module[.='Cisco-IOS-XE-eem'])";
      }
    }
  }
  augment "/ncs:devices/ncs:device/ncs:config/ios:native/ios:event" {
    uses config-eem-grouping {
      refine manager {
        tailf:ncs-device-type "netconf";
        tailf:display-when "not(../../../../ncs:module) or ../../../../ncs:module[ncs:name='Cisco-IOS-XE-eem']";
      }
    }
  }
}
