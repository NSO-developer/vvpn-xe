module Cisco-IOS-XE-ip-sla-oper {
  // Generated by yanger -t ncs
  tailf:ncs-device-type "netconf";

  yang-version "1";
  namespace "http://cisco.com/ns/yang/Cisco-IOS-XE-ip-sla-oper";
  prefix ip-sla-ios-xe-oper;

  import ietf-yang-types {
    prefix yang;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring of IP SLA statistics of a Network Element.
     Copyright (c) 2016-2017 by Cisco Systems, Inc.
     All rights reserved.";

  revision 2017-04-01 {
    description
      "Enum name changes. Remove when clauses";
    reference "2.0.0";
  }
  revision 2017-02-07 {
    description
      "Initial revision";
    reference "1.0.0";
  }

  typedef ttl-type {
    type enumeration {
      enum "ttl-finite" {
        value 0;
      }
      enum "ttl-forever" {
        value 1;
      }
    }
    description
      "IP SLA time-to-live type";
  }

  typedef rtt-type {
    type enumeration {
      enum "rtt-known" {
        value 0;
      }
      enum "rtt-unknown" {
        value 1;
      }
      enum "rtt-could-not-find" {
        value 2;
      }
    }
    description
      "IP SLA RTT type";
  }

  typedef accuracy-type {
    type enumeration {
      enum "accuracy-milliseconds" {
        value 0;
      }
      enum "accuracy-microseconds" {
        value 1;
      }
    }
    description
      "IP SLA accuracy type";
  }

  typedef sla-return-code {
    type enumeration {
      enum "ret-code-unknown" {
        value 0;
      }
      enum "ret-code-ok" {
        value 1;
      }
      enum "ret-code-disconnected" {
        value 2;
      }
      enum "ret-code-busy" {
        value 3;
      }
      enum "ret-code-timeout" {
        value 4;
      }
      enum "ret-code-no-connection" {
        value 5;
      }
      enum "ret-code-internal-error" {
        value 6;
      }
      enum "ret-code-operation-failure" {
        value 7;
      }
      enum "ret-code-could-not-find" {
        value 8;
      }
    }
    description
      "IP SLA return code";
  }

  typedef sla-oper-type {
    type enumeration {
      enum "oper-type-unknown" {
        value 0;
      }
      enum "oper-type-udp-echo" {
        value 1;
      }
      enum "oper-type-udp-jitter" {
        value 2;
      }
      enum "oper-type-icmp-jitter" {
        value 3;
      }
      enum "oper-type-ethernet-jitter" {
        value 4;
      }
      enum "oper-type-ethernet-echo" {
        value 5;
      }
      enum "oper-type-y1731-delay" {
        value 6;
      }
      enum "oper-type-y1731-loss" {
        value 7;
      }
      enum "oper-type-video" {
        value 8;
      }
      enum "oper-type-mcast" {
        value 9;
      }
      enum "oper-type-pong" {
        value 10;
      }
      enum "oper-type-path-jitter" {
        value 11;
      }
    }
    description
      "IP SLA operational type";
  }

  grouping ncs_template_sla-time-values {
    description
      "SLA time values";
    leaf min {
      type string;
      description
        "Minimum value reading";
    }
    leaf avg {
      type string;
      description
        "Average value reading";
    }
    leaf max {
      type string;
      description
        "Maximum value reading";
    }
    leaf accuracy {
      type string;
      description
        "Reading accuracy";
    }
  }

  grouping ncs_template_sla-packet-loss-info {
    description
      "SLA packet loss information";
    leaf loss-period-count {
      type string;
      description
        "Loss period count";
    }
    leaf loss-period-len-min {
      type string;
      description
        "Shortest loss period length";
    }
    leaf loss-period-len-max {
      type string;
      description
        "Longest loss period length";
    }
    leaf inter-loss-period-len-min {
      type string;
      description
        "Shortest inter loss period length";
    }
    leaf inter-loss-period-len-max {
      type string;
      description
        "Longest inter loss period length";
    }
  }

  grouping ncs_template_voice-score {
    description
      "Voice quality assessement info";
    leaf icpif {
      type string;
      description
        "Calculated planning impairment factor";
    }
    leaf mos {
      type string;
      description
        "Mean opinion score";
    }
  }

  grouping ncs_template_latest-rtt-type {
    description
      "Latest round-trip-time information";
    choice latestrtt-choice {
      description
        "Last Round Trip Time recorded for this SLA";
      case rtt-known {
        leaf rtt {
          type string;
          description
            "Round trip time value";
        }
      }
      case rtt-unknown {
        leaf unknown {
          type empty;
          description
            "Round trip time is unknown";
        }
      }
      case rtt-could-not-find {
        leaf could-not-find {
          type empty;
          description
            "Round trip time could not be determined";
        }
      }
    }
  }

  grouping ncs_template_time-to-live-type {
    description
      "Latest time to live information";
    choice timetolive-choice {
      description
        "For the timetolive-choice item, ip sla items can be configured to have a set (finite) time-to-live, or they can just be configured to go forever.";
      case ttl-finite {
        leaf ttl {
          type string;
          description
            "Time to live value";
        }
      }
      case ttl-forever {
        leaf forever {
          type empty;
          description
            "Time to live unbound";
        }
      }
    }
  }

  grouping ncs_template_rtt-info {
    description
      "Round trip time information";
    container latest-rtt {
      description
        "The last Round Trip Time recorded for this SLA";
      uses ip-sla-ios-xe-oper:ncs_template_latest-rtt-type;
    }
    container time-to-live {
      description
        "Time-to-live for the SLA operation";
      uses ip-sla-ios-xe-oper:ncs_template_time-to-live-type;
    }
  }

  grouping ncs_template_y1731-interval-stats {
    description
      "Y.1731 internal statistics";
    leaf intv-start-time {
      type string;
      description
        "Interval start time";
    }
    leaf init-count {
      type string;
      description
        "Initial count";
    }
    leaf complete-count {
      type string;
      description
        "Complete count";
    }
    leaf valid {
      type string;
      description
        "Validity";
    }
  }

  grouping ncs_template_rtt {
    description
      "RTT information";
    leaf rtt-count {
      type string;
      description
        "RTT count";
    }
    container sla-time-values {
      description
        "Timing information";
      uses ip-sla-ios-xe-oper:ncs_template_sla-time-values;
    }
  }

  grouping ncs_template_oneway-latency {
    description
      "Latency information";
    leaf sample-count {
      type string;
      description
        "Sample count";
    }
    container sd {
      description
        "Source to Destination for the one-way latency";
      uses ip-sla-ios-xe-oper:ncs_template_sla-time-values;
    }
    container ds {
      description
        "Destination to Source for the one-way latency";
      uses ip-sla-ios-xe-oper:ncs_template_sla-time-values;
    }
  }

  grouping ncs_template_jitter {
    description
      "Jitter information";
    leaf sd-sample-count {
      type string;
      description
        "Sample count";
    }
    leaf ds-sample-count {
      type string;
      description
        "Sample count";
    }
    container sd {
      description
        "Source to Destination for the jitter";
      uses ip-sla-ios-xe-oper:ncs_template_sla-time-values;
    }
    container ds {
      description
        "Destination to Source for the jitter";
      uses ip-sla-ios-xe-oper:ncs_template_sla-time-values;
    }
  }

  grouping ncs_template_over-threshold {
    description
      "Over the threshold information";
    leaf rtt-count {
      type string;
      description
        "Round Trip Time (RTT) over threshold count (the number of times that the RTT was over the configured threshold)";
    }
    leaf percent {
      type string;
      description
        "Round Trip Time over threshold percentage (the percentage that the RTT was over the configured threshold)";
    }
  }

  grouping ncs_template_packet-loss {
    description
      "Packet loss information";
    leaf unprocessed-packets {
      type string;
      description
        "Unprocessed packet count";
    }
    leaf sd-count {
      type string;
      description
        "Number of packets lost from Source to Destination";
    }
    container sd-loss {
      description
        "Source to Destination packet loss details";
      uses ip-sla-ios-xe-oper:ncs_template_sla-packet-loss-info;
    }
    leaf ds-count {
      type string;
      description
        "Number of packets lost from Destination to Source";
    }
    container ds-loss {
      description
        "Destination to Source packet loss details";
      uses ip-sla-ios-xe-oper:ncs_template_sla-packet-loss-info;
    }
    leaf out-of-sequence {
      type string;
      description
        "Out of sequence packet count";
    }
    leaf drops {
      type string;
      description
        "Dropped packet count";
    }
    leaf late-arrivals {
      type string;
      description
        "Late arrival packet count";
    }
    leaf skipped-packets {
      type string;
      description
        "Skipped packet count";
    }
  }

  grouping ncs_template_icmp-packet-loss {
    description
      "ICMP packet loss information";
    leaf late-arrivals {
      type string;
      description
        "Late arrival packet count";
    }
    leaf out-of-sequence {
      type string;
      description
        "Out of sequence packet count";
    }
    leaf out-of-sequence-sd {
      type string;
      description
        "Out of sequence packet count";
    }
    leaf out-of-sequence-ds {
      type string;
      description
        "Out of sequence packet count";
    }
    leaf out-of-sequence-both {
      type string;
      description
        "Out of sequence packet count";
    }
    leaf skipped-packets {
      type string;
      description
        "Skipped packet count";
    }
    leaf unprocessed-packets {
      type string;
      description
        "Unprocessed packet count";
    }
    leaf packet-loss {
      type string;
      description
        "Lost packet count";
    }
    leaf loss-period-count {
      type string;
      description
        "Loss period count";
    }
    leaf loss-period-len-min {
      type string;
      description
        "Shortest loss period length";
    }
    leaf loss-period-len-max {
      type string;
      description
        "Longest loss period length";
    }
    leaf inter-loss-period-len-min {
      type string;
      description
        "Shortest inter loss period length";
    }
    leaf inter-loss-period-len-max {
      type string;
      description
        "Longest inter loss period length";
    }
  }

  grouping ncs_template_stats {
    description
      "Statistics";
    container rtt {
      description
        "RTT value";
      uses ip-sla-ios-xe-oper:ncs_template_rtt;
    }
    container oneway-latency {
      description
        "Latency information";
      uses ip-sla-ios-xe-oper:ncs_template_oneway-latency;
    }
    container jitter {
      description
        "Jitter information";
      uses ip-sla-ios-xe-oper:ncs_template_jitter;
    }
    container over-threshold {
      description
        "Over threshold information";
      uses ip-sla-ios-xe-oper:ncs_template_over-threshold;
    }
    container packet-loss {
      description
        "Packet loss information";
      uses ip-sla-ios-xe-oper:ncs_template_packet-loss;
    }
    container icmp-packet-loss {
      description
        "ICMP packet loss information";
      uses ip-sla-ios-xe-oper:ncs_template_icmp-packet-loss;
    }
    container voice-score {
      description
        "Voice score information";
      uses ip-sla-ios-xe-oper:ncs_template_voice-score;
    }
  }

  grouping ncs_template_sla-oper-entry {
    description
      "SLA operational data entry";
    leaf oper-id {
      type string;
      description
        "Entry unique identifier";
    }
    leaf oper-type {
      type string;
      description
        "Entry type";
    }
    leaf latest-return-code {
      type string;
      description
        "Latest return code";
    }
    leaf success-count {
      type string;
      description
        "Success count";
    }
    leaf failure-count {
      type string;
      description
        "Failure count";
    }
    leaf latest-oper-start-time {
      type string;
      description
        "Latest start time";
    }
    container rtt-info {
      description
        "RTT information";
      uses ip-sla-ios-xe-oper:ncs_template_rtt-info;
    }
    container measure-stats {
      description
        "Measured statistics";
      uses ip-sla-ios-xe-oper:ncs_template_y1731-interval-stats;
    }
    container stats {
      description
        "Statistics";
      uses ip-sla-ios-xe-oper:ncs_template_stats;
    }
  }

  grouping ncs_rpc_notif_sla-time-values {
    description
      "SLA time values";
    leaf min {
      type uint32;
      description
        "Minimum value reading";
    }
    leaf avg {
      type uint32;
      description
        "Average value reading";
    }
    leaf max {
      type uint32;
      description
        "Maximum value reading";
    }
    leaf accuracy {
      type ip-sla-ios-xe-oper:accuracy-type;
      description
        "Reading accuracy";
    }
  }

  grouping ncs_rpc_notif_sla-packet-loss-info {
    description
      "SLA packet loss information";
    leaf loss-period-count {
      type uint32;
      description
        "Loss period count";
    }
    leaf loss-period-len-min {
      type uint32;
      description
        "Shortest loss period length";
    }
    leaf loss-period-len-max {
      type uint32;
      description
        "Longest loss period length";
    }
    leaf inter-loss-period-len-min {
      type uint32;
      description
        "Shortest inter loss period length";
    }
    leaf inter-loss-period-len-max {
      type uint32;
      description
        "Longest inter loss period length";
    }
  }

  grouping ncs_rpc_notif_voice-score {
    description
      "Voice quality assessement info";
    leaf icpif {
      type uint32;
      description
        "Calculated planning impairment factor";
    }
    leaf mos {
      type uint32;
      description
        "Mean opinion score";
    }
  }

  grouping ncs_rpc_notif_latest-rtt-type {
    description
      "Latest round-trip-time information";
    choice latestrtt-choice {
      description
        "Last Round Trip Time recorded for this SLA";
      case rtt-known {
        leaf rtt {
          type uint64;
          description
            "Round trip time value";
        }
      }
      case rtt-unknown {
        leaf unknown {
          type empty;
          description
            "Round trip time is unknown";
        }
      }
      case rtt-could-not-find {
        leaf could-not-find {
          type empty;
          description
            "Round trip time could not be determined";
        }
      }
    }
  }

  grouping ncs_rpc_notif_time-to-live-type {
    description
      "Latest time to live information";
    choice timetolive-choice {
      description
        "For the timetolive-choice item, ip sla items can be configured to have a set (finite) time-to-live, or they can just be configured to go forever.";
      case ttl-finite {
        leaf ttl {
          type uint64;
          description
            "Time to live value";
        }
      }
      case ttl-forever {
        leaf forever {
          type empty;
          description
            "Time to live unbound";
        }
      }
    }
  }

  grouping ncs_rpc_notif_rtt-info {
    description
      "Round trip time information";
    container latest-rtt {
      description
        "The last Round Trip Time recorded for this SLA";
      uses ip-sla-ios-xe-oper:ncs_rpc_notif_latest-rtt-type;
    }
    container time-to-live {
      description
        "Time-to-live for the SLA operation";
      uses ip-sla-ios-xe-oper:ncs_rpc_notif_time-to-live-type;
    }
  }

  grouping ncs_rpc_notif_y1731-interval-stats {
    description
      "Y.1731 internal statistics";
    leaf intv-start-time {
      type yang:date-and-time;
      description
        "Interval start time";
    }
    leaf init-count {
      type uint32;
      description
        "Initial count";
    }
    leaf complete-count {
      type uint32;
      description
        "Complete count";
    }
    leaf valid {
      type boolean;
      description
        "Validity";
    }
  }

  grouping ncs_rpc_notif_rtt {
    description
      "RTT information";
    leaf rtt-count {
      type uint32;
      description
        "RTT count";
    }
    container sla-time-values {
      description
        "Timing information";
      uses ip-sla-ios-xe-oper:ncs_rpc_notif_sla-time-values;
    }
  }

  grouping ncs_rpc_notif_oneway-latency {
    description
      "Latency information";
    leaf sample-count {
      type uint32;
      description
        "Sample count";
    }
    container sd {
      description
        "Source to Destination for the one-way latency";
      uses ip-sla-ios-xe-oper:ncs_rpc_notif_sla-time-values;
    }
    container ds {
      description
        "Destination to Source for the one-way latency";
      uses ip-sla-ios-xe-oper:ncs_rpc_notif_sla-time-values;
    }
  }

  grouping ncs_rpc_notif_jitter {
    description
      "Jitter information";
    leaf sd-sample-count {
      type uint32;
      description
        "Sample count";
    }
    leaf ds-sample-count {
      type uint32;
      description
        "Sample count";
    }
    container sd {
      description
        "Source to Destination for the jitter";
      uses ip-sla-ios-xe-oper:ncs_rpc_notif_sla-time-values;
    }
    container ds {
      description
        "Destination to Source for the jitter";
      uses ip-sla-ios-xe-oper:ncs_rpc_notif_sla-time-values;
    }
  }

  grouping ncs_rpc_notif_over-threshold {
    description
      "Over the threshold information";
    leaf rtt-count {
      type uint32;
      description
        "Round Trip Time (RTT) over threshold count (the number of times that the RTT was over the configured threshold)";
    }
    leaf percent {
      type uint8;
      description
        "Round Trip Time over threshold percentage (the percentage that the RTT was over the configured threshold)";
    }
  }

  grouping ncs_rpc_notif_packet-loss {
    description
      "Packet loss information";
    leaf unprocessed-packets {
      type uint32;
      description
        "Unprocessed packet count";
    }
    leaf sd-count {
      type uint32;
      description
        "Number of packets lost from Source to Destination";
    }
    container sd-loss {
      description
        "Source to Destination packet loss details";
      uses ip-sla-ios-xe-oper:ncs_rpc_notif_sla-packet-loss-info;
    }
    leaf ds-count {
      type uint32;
      description
        "Number of packets lost from Destination to Source";
    }
    container ds-loss {
      description
        "Destination to Source packet loss details";
      uses ip-sla-ios-xe-oper:ncs_rpc_notif_sla-packet-loss-info;
    }
    leaf out-of-sequence {
      type uint32;
      description
        "Out of sequence packet count";
    }
    leaf drops {
      type uint32;
      description
        "Dropped packet count";
    }
    leaf late-arrivals {
      type uint32;
      description
        "Late arrival packet count";
    }
    leaf skipped-packets {
      type uint32;
      description
        "Skipped packet count";
    }
  }

  grouping ncs_rpc_notif_icmp-packet-loss {
    description
      "ICMP packet loss information";
    leaf late-arrivals {
      type uint32;
      description
        "Late arrival packet count";
    }
    leaf out-of-sequence {
      type uint32;
      description
        "Out of sequence packet count";
    }
    leaf out-of-sequence-sd {
      type uint32;
      description
        "Out of sequence packet count";
    }
    leaf out-of-sequence-ds {
      type uint32;
      description
        "Out of sequence packet count";
    }
    leaf out-of-sequence-both {
      type uint32;
      description
        "Out of sequence packet count";
    }
    leaf skipped-packets {
      type uint32;
      description
        "Skipped packet count";
    }
    leaf unprocessed-packets {
      type uint32;
      description
        "Unprocessed packet count";
    }
    leaf packet-loss {
      type uint32;
      description
        "Lost packet count";
    }
    leaf loss-period-count {
      type uint32;
      description
        "Loss period count";
    }
    leaf loss-period-len-min {
      type uint32;
      description
        "Shortest loss period length";
    }
    leaf loss-period-len-max {
      type uint32;
      description
        "Longest loss period length";
    }
    leaf inter-loss-period-len-min {
      type uint32;
      description
        "Shortest inter loss period length";
    }
    leaf inter-loss-period-len-max {
      type uint32;
      description
        "Longest inter loss period length";
    }
  }

  grouping ncs_rpc_notif_stats {
    description
      "Statistics";
    container rtt {
      description
        "RTT value";
      uses ip-sla-ios-xe-oper:ncs_rpc_notif_rtt;
    }
    container oneway-latency {
      description
        "Latency information";
      uses ip-sla-ios-xe-oper:ncs_rpc_notif_oneway-latency;
    }
    container jitter {
      description
        "Jitter information";
      uses ip-sla-ios-xe-oper:ncs_rpc_notif_jitter;
    }
    container over-threshold {
      description
        "Over threshold information";
      uses ip-sla-ios-xe-oper:ncs_rpc_notif_over-threshold;
    }
    container packet-loss {
      description
        "Packet loss information";
      uses ip-sla-ios-xe-oper:ncs_rpc_notif_packet-loss;
    }
    container icmp-packet-loss {
      description
        "ICMP packet loss information";
      uses ip-sla-ios-xe-oper:ncs_rpc_notif_icmp-packet-loss;
    }
    container voice-score {
      description
        "Voice score information";
      uses ip-sla-ios-xe-oper:ncs_rpc_notif_voice-score;
    }
  }

  grouping ncs_rpc_notif_sla-oper-entry {
    description
      "SLA operational data entry";
    leaf oper-id {
      type uint32;
      description
        "Entry unique identifier";
    }
    leaf oper-type {
      type ip-sla-ios-xe-oper:sla-oper-type;
      description
        "Entry type";
    }
    leaf latest-return-code {
      type ip-sla-ios-xe-oper:sla-return-code;
      description
        "Latest return code";
    }
    leaf success-count {
      type uint32;
      description
        "Success count";
    }
    leaf failure-count {
      type uint32;
      description
        "Failure count";
    }
    leaf latest-oper-start-time {
      type yang:date-and-time;
      description
        "Latest start time";
    }
    container rtt-info {
      description
        "RTT information";
      uses ip-sla-ios-xe-oper:ncs_rpc_notif_rtt-info;
    }
    container measure-stats {
      description
        "Measured statistics";
      uses ip-sla-ios-xe-oper:ncs_rpc_notif_y1731-interval-stats;
    }
    container stats {
      description
        "Statistics";
      uses ip-sla-ios-xe-oper:ncs_rpc_notif_stats;
    }
  }

  grouping live_ncs_sla-time-values {
    description
      "SLA time values";
    leaf min {
      type uint32;
      description
        "Minimum value reading";
    }
    leaf avg {
      type uint32;
      description
        "Average value reading";
    }
    leaf max {
      type uint32;
      description
        "Maximum value reading";
    }
    leaf accuracy {
      type ip-sla-ios-xe-oper:accuracy-type;
      description
        "Reading accuracy";
    }
  }

  grouping live_ncs_sla-packet-loss-info {
    description
      "SLA packet loss information";
    leaf loss-period-count {
      type uint32;
      description
        "Loss period count";
    }
    leaf loss-period-len-min {
      type uint32;
      description
        "Shortest loss period length";
    }
    leaf loss-period-len-max {
      type uint32;
      description
        "Longest loss period length";
    }
    leaf inter-loss-period-len-min {
      type uint32;
      description
        "Shortest inter loss period length";
    }
    leaf inter-loss-period-len-max {
      type uint32;
      description
        "Longest inter loss period length";
    }
  }

  grouping live_ncs_voice-score {
    description
      "Voice quality assessement info";
    leaf icpif {
      type uint32;
      description
        "Calculated planning impairment factor";
    }
    leaf mos {
      type uint32;
      description
        "Mean opinion score";
    }
  }

  grouping live_ncs_latest-rtt-type {
    description
      "Latest round-trip-time information";
    choice latestrtt-choice {
      description
        "Last Round Trip Time recorded for this SLA";
      case rtt-known {
        leaf rtt {
          type uint64;
          description
            "Round trip time value";
        }
      }
      case rtt-unknown {
        leaf unknown {
          type empty;
          description
            "Round trip time is unknown";
        }
      }
      case rtt-could-not-find {
        leaf could-not-find {
          type empty;
          description
            "Round trip time could not be determined";
        }
      }
    }
  }

  grouping live_ncs_time-to-live-type {
    description
      "Latest time to live information";
    choice timetolive-choice {
      description
        "For the timetolive-choice item, ip sla items can be configured to have a set (finite) time-to-live, or they can just be configured to go forever.";
      case ttl-finite {
        leaf ttl {
          type uint64;
          description
            "Time to live value";
        }
      }
      case ttl-forever {
        leaf forever {
          type empty;
          description
            "Time to live unbound";
        }
      }
    }
  }

  grouping live_ncs_rtt-info {
    description
      "Round trip time information";
    container latest-rtt {
      description
        "The last Round Trip Time recorded for this SLA";
      uses ip-sla-ios-xe-oper:live_ncs_latest-rtt-type;
    }
    container time-to-live {
      description
        "Time-to-live for the SLA operation";
      uses ip-sla-ios-xe-oper:live_ncs_time-to-live-type;
    }
  }

  grouping live_ncs_y1731-interval-stats {
    description
      "Y.1731 internal statistics";
    leaf intv-start-time {
      type yang:date-and-time;
      description
        "Interval start time";
    }
    leaf init-count {
      type uint32;
      description
        "Initial count";
    }
    leaf complete-count {
      type uint32;
      description
        "Complete count";
    }
    leaf valid {
      type boolean;
      description
        "Validity";
    }
  }

  grouping live_ncs_rtt {
    description
      "RTT information";
    leaf rtt-count {
      type uint32;
      description
        "RTT count";
    }
    container sla-time-values {
      description
        "Timing information";
      uses ip-sla-ios-xe-oper:live_ncs_sla-time-values;
    }
  }

  grouping live_ncs_oneway-latency {
    description
      "Latency information";
    leaf sample-count {
      type uint32;
      description
        "Sample count";
    }
    container sd {
      description
        "Source to Destination for the one-way latency";
      uses ip-sla-ios-xe-oper:live_ncs_sla-time-values;
    }
    container ds {
      description
        "Destination to Source for the one-way latency";
      uses ip-sla-ios-xe-oper:live_ncs_sla-time-values;
    }
  }

  grouping live_ncs_jitter {
    description
      "Jitter information";
    leaf sd-sample-count {
      type uint32;
      description
        "Sample count";
    }
    leaf ds-sample-count {
      type uint32;
      description
        "Sample count";
    }
    container sd {
      description
        "Source to Destination for the jitter";
      uses ip-sla-ios-xe-oper:live_ncs_sla-time-values;
    }
    container ds {
      description
        "Destination to Source for the jitter";
      uses ip-sla-ios-xe-oper:live_ncs_sla-time-values;
    }
  }

  grouping live_ncs_over-threshold {
    description
      "Over the threshold information";
    leaf rtt-count {
      type uint32;
      description
        "Round Trip Time (RTT) over threshold count (the number of times that the RTT was over the configured threshold)";
    }
    leaf percent {
      type uint8;
      description
        "Round Trip Time over threshold percentage (the percentage that the RTT was over the configured threshold)";
    }
  }

  grouping live_ncs_packet-loss {
    description
      "Packet loss information";
    leaf unprocessed-packets {
      type uint32;
      description
        "Unprocessed packet count";
    }
    leaf sd-count {
      type uint32;
      description
        "Number of packets lost from Source to Destination";
    }
    container sd-loss {
      description
        "Source to Destination packet loss details";
      uses ip-sla-ios-xe-oper:live_ncs_sla-packet-loss-info;
    }
    leaf ds-count {
      type uint32;
      description
        "Number of packets lost from Destination to Source";
    }
    container ds-loss {
      description
        "Destination to Source packet loss details";
      uses ip-sla-ios-xe-oper:live_ncs_sla-packet-loss-info;
    }
    leaf out-of-sequence {
      type uint32;
      description
        "Out of sequence packet count";
    }
    leaf drops {
      type uint32;
      description
        "Dropped packet count";
    }
    leaf late-arrivals {
      type uint32;
      description
        "Late arrival packet count";
    }
    leaf skipped-packets {
      type uint32;
      description
        "Skipped packet count";
    }
  }

  grouping live_ncs_icmp-packet-loss {
    description
      "ICMP packet loss information";
    leaf late-arrivals {
      type uint32;
      description
        "Late arrival packet count";
    }
    leaf out-of-sequence {
      type uint32;
      description
        "Out of sequence packet count";
    }
    leaf out-of-sequence-sd {
      type uint32;
      description
        "Out of sequence packet count";
    }
    leaf out-of-sequence-ds {
      type uint32;
      description
        "Out of sequence packet count";
    }
    leaf out-of-sequence-both {
      type uint32;
      description
        "Out of sequence packet count";
    }
    leaf skipped-packets {
      type uint32;
      description
        "Skipped packet count";
    }
    leaf unprocessed-packets {
      type uint32;
      description
        "Unprocessed packet count";
    }
    leaf packet-loss {
      type uint32;
      description
        "Lost packet count";
    }
    leaf loss-period-count {
      type uint32;
      description
        "Loss period count";
    }
    leaf loss-period-len-min {
      type uint32;
      description
        "Shortest loss period length";
    }
    leaf loss-period-len-max {
      type uint32;
      description
        "Longest loss period length";
    }
    leaf inter-loss-period-len-min {
      type uint32;
      description
        "Shortest inter loss period length";
    }
    leaf inter-loss-period-len-max {
      type uint32;
      description
        "Longest inter loss period length";
    }
  }

  grouping live_ncs_stats {
    description
      "Statistics";
    container rtt {
      description
        "RTT value";
      uses ip-sla-ios-xe-oper:live_ncs_rtt;
    }
    container oneway-latency {
      description
        "Latency information";
      uses ip-sla-ios-xe-oper:live_ncs_oneway-latency;
    }
    container jitter {
      description
        "Jitter information";
      uses ip-sla-ios-xe-oper:live_ncs_jitter;
    }
    container over-threshold {
      description
        "Over threshold information";
      uses ip-sla-ios-xe-oper:live_ncs_over-threshold;
    }
    container packet-loss {
      description
        "Packet loss information";
      uses ip-sla-ios-xe-oper:live_ncs_packet-loss;
    }
    container icmp-packet-loss {
      description
        "ICMP packet loss information";
      uses ip-sla-ios-xe-oper:live_ncs_icmp-packet-loss;
    }
    container voice-score {
      description
        "Voice score information";
      uses ip-sla-ios-xe-oper:live_ncs_voice-score;
    }
  }

  grouping live_ncs_sla-oper-entry {
    description
      "SLA operational data entry";
    leaf oper-id {
      type uint32;
      description
        "Entry unique identifier";
    }
    leaf oper-type {
      type ip-sla-ios-xe-oper:sla-oper-type;
      description
        "Entry type";
    }
    leaf latest-return-code {
      type ip-sla-ios-xe-oper:sla-return-code;
      description
        "Latest return code";
    }
    leaf success-count {
      type uint32;
      description
        "Success count";
    }
    leaf failure-count {
      type uint32;
      description
        "Failure count";
    }
    leaf latest-oper-start-time {
      type yang:date-and-time;
      description
        "Latest start time";
    }
    container rtt-info {
      description
        "RTT information";
      uses ip-sla-ios-xe-oper:live_ncs_rtt-info;
    }
    container measure-stats {
      description
        "Measured statistics";
      uses ip-sla-ios-xe-oper:live_ncs_y1731-interval-stats;
    }
    container stats {
      description
        "Statistics";
      uses ip-sla-ios-xe-oper:live_ncs_stats;
    }
  }

  grouping sla-time-values {
    description
      "SLA time values";
    leaf min {
      type uint32;
      description
        "Minimum value reading";
    }
    leaf avg {
      type uint32;
      description
        "Average value reading";
    }
    leaf max {
      type uint32;
      description
        "Maximum value reading";
    }
    leaf accuracy {
      type ip-sla-ios-xe-oper:accuracy-type;
      description
        "Reading accuracy";
    }
  }

  grouping sla-packet-loss-info {
    description
      "SLA packet loss information";
    leaf loss-period-count {
      type uint32;
      description
        "Loss period count";
    }
    leaf loss-period-len-min {
      type uint32;
      description
        "Shortest loss period length";
    }
    leaf loss-period-len-max {
      type uint32;
      description
        "Longest loss period length";
    }
    leaf inter-loss-period-len-min {
      type uint32;
      description
        "Shortest inter loss period length";
    }
    leaf inter-loss-period-len-max {
      type uint32;
      description
        "Longest inter loss period length";
    }
  }

  grouping voice-score {
    description
      "Voice quality assessement info";
    leaf icpif {
      type uint32;
      description
        "Calculated planning impairment factor";
    }
    leaf mos {
      type uint32;
      description
        "Mean opinion score";
    }
  }

  grouping latest-rtt-type {
    description
      "Latest round-trip-time information";
    choice latestrtt-choice {
      description
        "Last Round Trip Time recorded for this SLA";
      case rtt-known {
        leaf rtt {
          type uint64;
          description
            "Round trip time value";
        }
      }
      case rtt-unknown {
        leaf unknown {
          type empty;
          description
            "Round trip time is unknown";
        }
      }
      case rtt-could-not-find {
        leaf could-not-find {
          type empty;
          description
            "Round trip time could not be determined";
        }
      }
    }
  }

  grouping time-to-live-type {
    description
      "Latest time to live information";
    choice timetolive-choice {
      description
        "For the timetolive-choice item, ip sla items can be configured to have a set (finite) time-to-live, or they can just be configured to go forever.";
      case ttl-finite {
        leaf ttl {
          type uint64;
          description
            "Time to live value";
        }
      }
      case ttl-forever {
        leaf forever {
          type empty;
          description
            "Time to live unbound";
        }
      }
    }
  }

  grouping rtt-info {
    description
      "Round trip time information";
    container latest-rtt {
      description
        "The last Round Trip Time recorded for this SLA";
      uses ip-sla-ios-xe-oper:latest-rtt-type;
    }
    container time-to-live {
      description
        "Time-to-live for the SLA operation";
      uses ip-sla-ios-xe-oper:time-to-live-type;
    }
  }

  grouping y1731-interval-stats {
    description
      "Y.1731 internal statistics";
    leaf intv-start-time {
      type yang:date-and-time;
      description
        "Interval start time";
    }
    leaf init-count {
      type uint32;
      description
        "Initial count";
    }
    leaf complete-count {
      type uint32;
      description
        "Complete count";
    }
    leaf valid {
      type boolean;
      description
        "Validity";
    }
  }

  grouping rtt {
    description
      "RTT information";
    leaf rtt-count {
      type uint32;
      description
        "RTT count";
    }
    container sla-time-values {
      description
        "Timing information";
      uses ip-sla-ios-xe-oper:sla-time-values;
    }
  }

  grouping oneway-latency {
    description
      "Latency information";
    leaf sample-count {
      type uint32;
      description
        "Sample count";
    }
    container sd {
      description
        "Source to Destination for the one-way latency";
      uses ip-sla-ios-xe-oper:sla-time-values;
    }
    container ds {
      description
        "Destination to Source for the one-way latency";
      uses ip-sla-ios-xe-oper:sla-time-values;
    }
  }

  grouping jitter {
    description
      "Jitter information";
    leaf sd-sample-count {
      type uint32;
      description
        "Sample count";
    }
    leaf ds-sample-count {
      type uint32;
      description
        "Sample count";
    }
    container sd {
      description
        "Source to Destination for the jitter";
      uses ip-sla-ios-xe-oper:sla-time-values;
    }
    container ds {
      description
        "Destination to Source for the jitter";
      uses ip-sla-ios-xe-oper:sla-time-values;
    }
  }

  grouping over-threshold {
    description
      "Over the threshold information";
    leaf rtt-count {
      type uint32;
      description
        "Round Trip Time (RTT) over threshold count (the number of times that the RTT was over the configured threshold)";
    }
    leaf percent {
      type uint8;
      description
        "Round Trip Time over threshold percentage (the percentage that the RTT was over the configured threshold)";
    }
  }

  grouping packet-loss {
    description
      "Packet loss information";
    leaf unprocessed-packets {
      type uint32;
      description
        "Unprocessed packet count";
    }
    leaf sd-count {
      type uint32;
      description
        "Number of packets lost from Source to Destination";
    }
    container sd-loss {
      description
        "Source to Destination packet loss details";
      uses ip-sla-ios-xe-oper:sla-packet-loss-info;
    }
    leaf ds-count {
      type uint32;
      description
        "Number of packets lost from Destination to Source";
    }
    container ds-loss {
      description
        "Destination to Source packet loss details";
      uses ip-sla-ios-xe-oper:sla-packet-loss-info;
    }
    leaf out-of-sequence {
      type uint32;
      description
        "Out of sequence packet count";
    }
    leaf drops {
      type uint32;
      description
        "Dropped packet count";
    }
    leaf late-arrivals {
      type uint32;
      description
        "Late arrival packet count";
    }
    leaf skipped-packets {
      type uint32;
      description
        "Skipped packet count";
    }
  }

  grouping icmp-packet-loss {
    description
      "ICMP packet loss information";
    leaf late-arrivals {
      type uint32;
      description
        "Late arrival packet count";
    }
    leaf out-of-sequence {
      type uint32;
      description
        "Out of sequence packet count";
    }
    leaf out-of-sequence-sd {
      type uint32;
      description
        "Out of sequence packet count";
    }
    leaf out-of-sequence-ds {
      type uint32;
      description
        "Out of sequence packet count";
    }
    leaf out-of-sequence-both {
      type uint32;
      description
        "Out of sequence packet count";
    }
    leaf skipped-packets {
      type uint32;
      description
        "Skipped packet count";
    }
    leaf unprocessed-packets {
      type uint32;
      description
        "Unprocessed packet count";
    }
    leaf packet-loss {
      type uint32;
      description
        "Lost packet count";
    }
    leaf loss-period-count {
      type uint32;
      description
        "Loss period count";
    }
    leaf loss-period-len-min {
      type uint32;
      description
        "Shortest loss period length";
    }
    leaf loss-period-len-max {
      type uint32;
      description
        "Longest loss period length";
    }
    leaf inter-loss-period-len-min {
      type uint32;
      description
        "Shortest inter loss period length";
    }
    leaf inter-loss-period-len-max {
      type uint32;
      description
        "Longest inter loss period length";
    }
  }

  grouping stats {
    description
      "Statistics";
    container rtt {
      description
        "RTT value";
      uses ip-sla-ios-xe-oper:rtt;
    }
    container oneway-latency {
      description
        "Latency information";
      uses ip-sla-ios-xe-oper:oneway-latency;
    }
    container jitter {
      description
        "Jitter information";
      uses ip-sla-ios-xe-oper:jitter;
    }
    container over-threshold {
      description
        "Over threshold information";
      uses ip-sla-ios-xe-oper:over-threshold;
    }
    container packet-loss {
      description
        "Packet loss information";
      uses ip-sla-ios-xe-oper:packet-loss;
    }
    container icmp-packet-loss {
      description
        "ICMP packet loss information";
      uses ip-sla-ios-xe-oper:icmp-packet-loss;
    }
    container voice-score {
      description
        "Voice score information";
      uses ip-sla-ios-xe-oper:voice-score;
    }
  }

  grouping sla-oper-entry {
    description
      "SLA operational data entry";
    leaf oper-id {
      type uint32;
      description
        "Entry unique identifier";
    }
    leaf oper-type {
      type ip-sla-ios-xe-oper:sla-oper-type;
      description
        "Entry type";
    }
    leaf latest-return-code {
      type ip-sla-ios-xe-oper:sla-return-code;
      description
        "Latest return code";
    }
    leaf success-count {
      type uint32;
      description
        "Success count";
    }
    leaf failure-count {
      type uint32;
      description
        "Failure count";
    }
    leaf latest-oper-start-time {
      type yang:date-and-time;
      description
        "Latest start time";
    }
    container rtt-info {
      description
        "RTT information";
      uses ip-sla-ios-xe-oper:rtt-info;
    }
    container measure-stats {
      description
        "Measured statistics";
      uses ip-sla-ios-xe-oper:y1731-interval-stats;
    }
    container stats {
      description
        "Statistics";
      uses ip-sla-ios-xe-oper:stats;
    }
  }

  augment "/ncs:devices/ncs:device/ncs:config" {
    // NCS drop config false container 'ip-sla-stats'
  }
  augment "/ncs:devices/ncs:device/ncs:live-status" {
    container ip-sla-stats {
      tailf:ncs-device-type "netconf";
      tailf:display-when "not(../../ncs:module) or ../../ncs:module[ncs:name='Cisco-IOS-XE-ip-sla-oper'] or (../../ncs:live-status-protocol[not(ncs:capability)]) or (../../ncs:live-status-protocol/ncs:capability/ncs:module[.='Cisco-IOS-XE-ip-sla-oper'])";
      description
        "Data nodes for All IP SLA Statistics";
      list sla-oper-entry {
        key "oper-id";
        description
          "The list of IP SLA operations with statistics info";
        uses ip-sla-ios-xe-oper:live_ncs_sla-oper-entry;
      }
    }
  }
  augment "/ncs:devices/ncs:template/ncs:config" {
    // NCS drop config false container 'ip-sla-stats'
  }
}
