module Cisco-IOS-XE-nat {
  // Generated by yanger -t ncs
  tailf:ncs-device-type "netconf";

  namespace "http://cisco.com/ns/yang/Cisco-IOS-XE-nat";
  prefix ios-nat;

  import ietf-inet-types {
    prefix inet;
  }
  import Cisco-IOS-XE-types {
    prefix ios-types;
  }
  import Cisco-IOS-XE-native {
    prefix ios;
  }
  import Cisco-IOS-XE-interface-common {
    prefix ios-ifc;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Network Address Translation (NAT) Yang model.
     Copyright (c) 2016-2017 by Cisco Systems, Inc.
     All rights reserved.";

  revision 2017-06-16 {
    description
      "Native Yang Support for NATv6";
  }
  revision 2017-03-14 {
    description
      "Add Container node Pool, Oer and Overload
       under node Route-map.";
  }
  revision 2017-02-07 {
    description
      "Initial revision";
  }

  grouping ncs_template_config-interface-ip-nat-grouping {
    container nat {
      description
        "NAT interface commands";
      leaf allow-static-host {
        description
          "Allow static-ip clients";
        type empty;
      }
      leaf enable {
        description
          "Enable Address Translation (NVI)";
        type empty;
      }
      choice nat-choice {
        leaf inside {
          description
            "Inside interface for address translation";
          type empty;
        }
        leaf outside {
          description
            "Outside interface for address translation";
          type empty;
        }
      }
    }
  }

  grouping ncs_template_config-ip-nat-pool-interface-grouping {
    choice pool-or-interface {
      case pool-choice {
        leaf pool {
          description
            "Name pool of global addresses";
          type string;
        }
        leaf redundancy {
          description
            "NAT redundancy operation";
          type string;
        }
        leaf mapping-id {
          description
            "Associate a mapping id to this mapping";
          type string;
        }
      }
      case interface-choice {
        container interface {
          description
            "Specify interface for global address";
          uses ios-ifc:ncs_template_interface-grouping;
        }
      }
    }
    leaf no-payload {
      description
        "No translation of embedded address/port in the payload";
      type empty;
    }
    leaf reversible {
      // NCS drop when statement
      type empty;
    }
    leaf vrf {
      description
        "Specify vrf";
      type string;
    }
    leaf match-in-vrf {
      description
        "Match incoming vrf";
      // NCS drop when statement
      type empty;
    }
    leaf overload {
      description
        "Overload an address translation";
      type empty;
    }
    leaf oer {
      description
        "Use with vtemplate only. On new translation, if OER BR is UP,
         OER will select IP from outgoing Interface.
         All packets matching translation are forwarded over Interface
         for duration of translation.";
      type empty;
    }
  }

  grouping ncs_template_config-ip-nat-grouping {
    container nat {
      description
        "NAT configuration commands";
      list pool {
        // NCS patched for predictable order
        ordered-by user;
        description
          "Define pool of addresses";
        key "id";
        leaf id {
          type string;
        }
        leaf start-address {
          type string;
        }
        leaf end-address {
          // NCS drop when statement
          type string;
        }
        choice prefix-choice {
          leaf netmask {
            description
              "Specify the network mask";
            type string;
          }
          leaf prefix-length {
            description
              "Specify the prefix length";
            type string;
          }
        }
        leaf accounting {
          description
            "Specify the accounting";
          type string;
        }
        choice nat-choice {
          leaf arp-ping {
            description
              "WLAN ARP Ping";
            type empty;
          }
          leaf type {
            description
              "Specify the pool type";
            type string;
          }
          leaf add-route {
            description
              "Add special route to Virtual Interface";
            type empty;
          }
        }
      }
      container inside {
        description
          "Inside address translation";
        container source {
          description
            "Source address translation";
          list list {
            // NCS patched for predictable order
            ordered-by user;
            description
              "Specify access list describing local addresses";
            key "id";
            leaf id {
              type string;
            }
            uses ncs_template_config-ip-nat-pool-interface-grouping;
          }
          list route-map {
            // NCS patched for predictable order
            ordered-by user;
            description
              "Specify route-map";
            key "route-map-name";
            leaf route-map-name {
              description
                "Route-map name";
              type string;
            }
            container pool {
              description
                "Name pool of global addresses";
              leaf pool-name {
                description
                  "Pool name for global addresses";
                type string;
              }
              leaf vrf {
                description
                  "Specify vrf";
                type string;
              }
              leaf match-in-vrf {
                description
                  "Match incoming vrf";
                type empty;
              }
            }
            container interface {
              description
                "Specify interface for global address";
              uses ios-ifc:ncs_template_interface-grouping;
            }
            container oer {
              description
                "Use with vtemplate only.  On new translation,
                 if OER BR is UP, OER will select IP from outgoing Interface.
                 All packets matching translation are forwarded over
                 Interface for duration of translation.";
              leaf overload {
                description
                  "Overload an address translation";
                type empty;
              }
              leaf extended {
                description
                  "Overload extended";
                type empty;
              }
            }
            container overload {
              description
                "Overload an address translation";
              leaf extended {
                description
                  "Overload extended";
                type empty;
              }
              leaf oer {
                description
                  "Use with vtemplate only.  On new translation,
                   if OER BR is UP, OER will select IP from outgoing
                   Interface.  All packets matching translation are
                   forwarded over Interface for duration of translation.";
                type empty;
              }
            }
            list vrf {
              // NCS patched for predictable order
              ordered-by user;
              description
                "Specify vrf";
              key "vrf-name";
              leaf vrf-name {
                description
                  "vrf name";
                type string;
              }
              container oer {
                description
                  "Use with vtemplate only.  On new translation,
                   if OER BR is UP, OER will select IP from outgoing
                   Interface.  All packets matching translation are
                   forwarded over Interface for duration of translation.";
                presence "true";
                leaf overload {
                  description
                    "Overload an address translation";
                  type empty;
                }
              }
              container overload {
                description
                  "Overload an address translation";
                presence "true";
                leaf oer {
                  description
                    "Use with vtemplate only.  On new translation,
                     if OER BR is UP, OER will select IP from outgoing
                     Interface.  All packets matching translation are
                     forwarded over Interface for duration of translation.";
                  type empty;
                }
              }
            }
          }
          container static {
            description
              "Specify static local->global mapping";
            list nat-static-transport-list {
              // NCS patched for predictable order
              ordered-by user;
              key "local-ip global-ip";
              leaf local-ip {
                type string;
              }
              leaf global-ip {
                type string;
              }
              leaf proto {
                type string;
              }
              leaf network {
                description
                  "Subnet translation";
                type empty;
              }
              leaf local-port {
                type string;
              }
              leaf mask {
                type string;
              }
              leaf global-port {
                type string;
              }
              leaf extendable {
                description
                  "Extend this translation when used";
                type empty;
              }
              leaf no-alias {
                description
                  "Do not create an alias for the global address";
                type empty;
              }
              leaf no-payload {
                description
                  "No translation of embedded address/port in the payload";
                type empty;
              }
              leaf route-map {
                description
                  "Specify route-map";
                type string;
              }
              leaf reversible {
                // NCS drop when statement
                type empty;
              }
              leaf redundancy {
                description
                  "NAT redundancy operation";
                type string;
              }
              leaf mapping-id {
                description
                  "Associate a mapping id to this mapping";
                // NCS drop when statement
                type string;
              }
              leaf vrf {
                description
                  "Specify vrf";
                type string;
              }
              leaf match-in-vrf {
                description
                  "Match incoming vrf";
                // NCS drop when statement
                type empty;
              }
              leaf forced {
                description
                  "Delete this entry and its children, even if in use";
                type empty;
              }
              leaf overload {
                description
                  "Overload an address translation";
                type empty;
              }
            }
            list nat-static-transport-interface-list {
              // NCS patched for predictable order
              ordered-by user;
              key "proto local-ip local-port";
              leaf proto {
                type string;
              }
              leaf local-ip {
                type string;
              }
              leaf local-port {
                type string;
              }
              container interface {
                description
                  "Specify interface for global address";
                uses ios-ifc:ncs_template_interface-grouping;
              }
              leaf global-port {
                type string;
              }
            }
          }
        }
        container destination {
          description
            "Destination address translation";
          list list {
            // NCS patched for predictable order
            ordered-by user;
            description
              "Specify access list describing global addresses";
            key "id";
            leaf id {
              type string;
            }
            leaf pool {
              description
                "Name pool of local addresses";
              type string;
            }
            leaf redundancy {
              description
                "NAT redundancy operation";
              type string;
            }
            leaf mapping-id {
              description
                "Associate a mapping id to this mapping";
              type string;
            }
          }
        }
      }
      container outside {
        description
          "Outside address translation";
        container source {
          description
            "Source address translation";
          container static {
            description
              "Specify static global->local mapping";
            list nat-static-transport-list {
              // NCS patched for predictable order
              ordered-by user;
              key "global-ip local-ip";
              leaf global-ip {
                type string;
              }
              leaf local-ip {
                type string;
              }
              leaf vrf {
                description
                  "Specify vrf";
                type string;
              }
              leaf extendable {
                description
                  "Extend this translation when used";
                type empty;
              }
              leaf no-payload {
                description
                  "No translation of embedded address/port in the payload";
                type empty;
              }
            }
          }
        }
        list list {
          // NCS patched for predictable order
          ordered-by user;
          description
            "Specify access list describing global addresses";
          key "id";
          leaf id {
            type string;
          }
          leaf pool {
            description
              "Name pool of local addresses";
            type string;
          }
          leaf mapping-id {
            description
              "Associate a mapping id to this mapping";
            type string;
          }
          leaf vrf {
            description
              "Specify vrf";
            type string;
          }
          leaf add-route {
            description
              "Add a static route for outside local address";
            type empty;
          }
        }
        list route-map {
          // NCS patched for predictable order
          ordered-by user;
          description
            "Specify route-map";
          key "id";
          leaf id {
            type string;
          }
          leaf pool {
            description
              "Name pool of local addresses";
            type string;
          }
          leaf mapping-id {
            description
              "Associate a mapping id to this mapping";
            type string;
          }
          leaf vrf {
            description
              "Specify vrf";
            type string;
          }
          leaf add-route {
            description
              "Add a static route for outside local address";
            type empty;
          }
        }
      }
    }
  }

  grouping ncs_template_config-nat66-grouping {
    container nat66 {
      description
        "NAT66 configuration commands";
      container prefix {
        description
          "NAT66 prefix";
        list inside {
          // NCS patched for predictable order
          ordered-by user;
          description
            "inside prefix";
          key "inside-pfx";
          leaf inside-pfx {
            description
              "IPv6 prefix";
            type string;
          }
          leaf outside {
            description
              "outside prefix";
            type string;
          }
        }
      }
    }
  }

  grouping ncs_template_config-interface-nat66-grouping {
    leaf nat66 {
      description
        "NAT66 interface commands";
      type string;
    }
  }

  grouping ncs_rpc_notif_config-interface-ip-nat-grouping {
    container nat {
      description
        "NAT interface commands";
      leaf allow-static-host {
        description
          "Allow static-ip clients";
        type empty;
      }
      leaf enable {
        description
          "Enable Address Translation (NVI)";
        type empty;
      }
      choice nat-choice {
        leaf inside {
          description
            "Inside interface for address translation";
          type empty;
        }
        leaf outside {
          description
            "Outside interface for address translation";
          type empty;
        }
      }
    }
  }

  grouping ncs_rpc_notif_config-ip-nat-pool-interface-grouping {
    choice pool-or-interface {
      case pool-choice {
        leaf pool {
          description
            "Name pool of global addresses";
          type string;
        }
        leaf redundancy {
          description
            "NAT redundancy operation";
          type uint8 {
            range "1..2";
          }
        }
        leaf mapping-id {
          description
            "Associate a mapping id to this mapping";
          type uint32 {
            range "1..2147483647";
          }
        }
      }
      case interface-choice {
        container interface {
          description
            "Specify interface for global address";
          uses ios-ifc:ncs_rpc_notif_interface-grouping;
        }
      }
    }
    leaf no-payload {
      description
        "No translation of embedded address/port in the payload";
      type empty;
    }
    leaf reversible {
      when "../../route-map" {
        tailf:xpath-root 3;
      }
      type empty;
    }
    leaf vrf {
      description
        "Specify vrf";
      type string;
    }
    leaf match-in-vrf {
      description
        "Match incoming vrf";
      when "../vrf" {
        tailf:xpath-root 3;
      }
      type empty;
    }
    leaf overload {
      description
        "Overload an address translation";
      type empty;
    }
    leaf oer {
      description
        "Use with vtemplate only. On new translation, if OER BR is UP,
         OER will select IP from outgoing Interface.
         All packets matching translation are forwarded over Interface
         for duration of translation.";
      type empty;
    }
  }

  grouping ncs_rpc_notif_config-ip-nat-grouping {
    container nat {
      description
        "NAT configuration commands";
      list pool {
        description
          "Define pool of addresses";
        key "id";
        leaf id {
          type string;
        }
        leaf start-address {
          type inet:ipv4-address;
        }
        leaf end-address {
          when "../start-address" {
            tailf:xpath-root 3;
          }
          type inet:ipv4-address;
        }
        choice prefix-choice {
          leaf netmask {
            description
              "Specify the network mask";
            type inet:ipv4-address;
          }
          leaf prefix-length {
            description
              "Specify the prefix length";
            type uint8 {
              range "1..32";
            }
          }
        }
        leaf accounting {
          description
            "Specify the accounting";
          type string;
        }
        choice nat-choice {
          leaf arp-ping {
            description
              "WLAN ARP Ping";
            type empty;
          }
          leaf type {
            description
              "Specify the pool type";
            type enumeration {
              enum "match-host";
              enum "rotary";
            }
          }
          leaf add-route {
            description
              "Add special route to Virtual Interface";
            type empty;
          }
        }
      }
      container inside {
        description
          "Inside address translation";
        container source {
          description
            "Source address translation";
          list list {
            description
              "Specify access list describing local addresses";
            key "id";
            leaf id {
              type union {
                type uint16 {
                  range "1..2699";
                }
                type string;
              }
            }
            uses ncs_rpc_notif_config-ip-nat-pool-interface-grouping;
          }
          list route-map {
            description
              "Specify route-map";
            key "route-map-name";
            leaf route-map-name {
              description
                "Route-map name";
              type string;
            }
            container pool {
              description
                "Name pool of global addresses";
              leaf pool-name {
                description
                  "Pool name for global addresses";
                type string;
              }
              leaf vrf {
                description
                  "Specify vrf";
                type string;
              }
              leaf match-in-vrf {
                description
                  "Match incoming vrf";
                type empty;
              }
            }
            container interface {
              description
                "Specify interface for global address";
              uses ios-ifc:ncs_rpc_notif_interface-grouping;
            }
            container oer {
              description
                "Use with vtemplate only.  On new translation,
                 if OER BR is UP, OER will select IP from outgoing Interface.
                 All packets matching translation are forwarded over
                 Interface for duration of translation.";
              leaf overload {
                description
                  "Overload an address translation";
                type empty;
              }
              leaf extended {
                description
                  "Overload extended";
                type empty;
              }
            }
            container overload {
              description
                "Overload an address translation";
              leaf extended {
                description
                  "Overload extended";
                type empty;
              }
              leaf oer {
                description
                  "Use with vtemplate only.  On new translation,
                   if OER BR is UP, OER will select IP from outgoing
                   Interface.  All packets matching translation are
                   forwarded over Interface for duration of translation.";
                type empty;
              }
            }
            list vrf {
              description
                "Specify vrf";
              key "vrf-name";
              leaf vrf-name {
                description
                  "vrf name";
                type string;
              }
              container oer {
                description
                  "Use with vtemplate only.  On new translation,
                   if OER BR is UP, OER will select IP from outgoing
                   Interface.  All packets matching translation are
                   forwarded over Interface for duration of translation.";
                presence "true";
                leaf overload {
                  description
                    "Overload an address translation";
                  type empty;
                }
              }
              container overload {
                description
                  "Overload an address translation";
                presence "true";
                leaf oer {
                  description
                    "Use with vtemplate only.  On new translation,
                     if OER BR is UP, OER will select IP from outgoing
                     Interface.  All packets matching translation are
                     forwarded over Interface for duration of translation.";
                  type empty;
                }
              }
            }
          }
          container static {
            description
              "Specify static local->global mapping";
            list nat-static-transport-list {
              key "local-ip global-ip";
              leaf local-ip {
                type inet:ipv4-address;
              }
              leaf global-ip {
                type inet:ipv4-address;
              }
              leaf proto {
                type enumeration {
                  enum "tcp";
                  enum "udp";
                }
              }
              leaf network {
                description
                  "Subnet translation";
                type empty;
              }
              leaf local-port {
                type uint16 {
                  range "1..65535";
                }
              }
              leaf mask {
                type union {
                  type string;
                  type inet:ipv4-address;
                }
              }
              leaf global-port {
                type uint16 {
                  range "1..65535";
                }
              }
              leaf extendable {
                description
                  "Extend this translation when used";
                type empty;
              }
              leaf no-alias {
                description
                  "Do not create an alias for the global address";
                type empty;
              }
              leaf no-payload {
                description
                  "No translation of embedded address/port in the payload";
                type empty;
              }
              leaf route-map {
                description
                  "Specify route-map";
                type string;
              }
              leaf reversible {
                when "../route-map" {
                  tailf:xpath-root 3;
                }
                type empty;
              }
              leaf redundancy {
                description
                  "NAT redundancy operation";
                type union {
                  type uint8;
                  type string;
                }
              }
              leaf mapping-id {
                description
                  "Associate a mapping id to this mapping";
                when "../redundancy" {
                  tailf:xpath-root 3;
                }
                type uint32 {
                  range "1..2147483647";
                }
              }
              leaf vrf {
                description
                  "Specify vrf";
                type string;
              }
              leaf match-in-vrf {
                description
                  "Match incoming vrf";
                when "../vrf" {
                  tailf:xpath-root 3;
                }
                type empty;
              }
              leaf forced {
                description
                  "Delete this entry and its children, even if in use";
                type empty;
              }
              leaf overload {
                description
                  "Overload an address translation";
                type empty;
              }
            }
            list nat-static-transport-interface-list {
              key "proto local-ip local-port";
              leaf proto {
                type enumeration {
                  enum "tcp";
                  enum "udp";
                }
              }
              leaf local-ip {
                type inet:ipv4-address;
              }
              leaf local-port {
                type uint16 {
                  range "1..65535";
                }
              }
              container interface {
                description
                  "Specify interface for global address";
                uses ios-ifc:ncs_rpc_notif_interface-grouping;
              }
              leaf global-port {
                type uint16 {
                  range "1..65535";
                }
              }
            }
          }
        }
        container destination {
          description
            "Destination address translation";
          list list {
            description
              "Specify access list describing global addresses";
            key "id";
            leaf id {
              type union {
                type uint16 {
                  range "1..2699";
                }
                type string;
              }
            }
            leaf pool {
              description
                "Name pool of local addresses";
              type string;
            }
            leaf redundancy {
              description
                "NAT redundancy operation";
              type uint8 {
                range "1..2";
              }
            }
            leaf mapping-id {
              description
                "Associate a mapping id to this mapping";
              type uint32 {
                range "1..2147483647";
              }
            }
          }
        }
      }
      container outside {
        description
          "Outside address translation";
        container source {
          description
            "Source address translation";
          container static {
            description
              "Specify static global->local mapping";
            list nat-static-transport-list {
              key "global-ip local-ip";
              leaf global-ip {
                type inet:ipv4-address;
              }
              leaf local-ip {
                type inet:ipv4-address;
              }
              leaf vrf {
                description
                  "Specify vrf";
                type string;
              }
              leaf extendable {
                description
                  "Extend this translation when used";
                type empty;
              }
              leaf no-payload {
                description
                  "No translation of embedded address/port in the payload";
                type empty;
              }
            }
          }
        }
        list list {
          description
            "Specify access list describing global addresses";
          key "id";
          leaf id {
            type union {
              type uint16 {
                range "1..2699";
              }
              type string;
            }
          }
          leaf pool {
            description
              "Name pool of local addresses";
            type string;
          }
          leaf mapping-id {
            description
              "Associate a mapping id to this mapping";
            type uint32 {
              range "1..2147483647";
            }
          }
          leaf vrf {
            description
              "Specify vrf";
            type string;
          }
          leaf add-route {
            description
              "Add a static route for outside local address";
            type empty;
          }
        }
        list route-map {
          description
            "Specify route-map";
          key "id";
          leaf id {
            type string;
          }
          leaf pool {
            description
              "Name pool of local addresses";
            type string;
          }
          leaf mapping-id {
            description
              "Associate a mapping id to this mapping";
            type uint32 {
              range "1..2147483647";
            }
          }
          leaf vrf {
            description
              "Specify vrf";
            type string;
          }
          leaf add-route {
            description
              "Add a static route for outside local address";
            type empty;
          }
        }
      }
    }
  }

  grouping ncs_rpc_notif_config-nat66-grouping {
    container nat66 {
      description
        "NAT66 configuration commands";
      container prefix {
        description
          "NAT66 prefix";
        list inside {
          description
            "inside prefix";
          key "inside-pfx";
          leaf inside-pfx {
            description
              "IPv6 prefix";
            type ios-types:ipv6-prefix;
          }
          leaf outside {
            description
              "outside prefix";
            type ios-types:ipv6-prefix;
          }
        }
      }
    }
  }

  grouping ncs_rpc_notif_config-interface-nat66-grouping {
    leaf nat66 {
      description
        "NAT66 interface commands";
      type enumeration {
        enum "inside";
        enum "outside";
      }
    }
  }

  grouping live_ncs_config-interface-ip-nat-grouping {
    container nat {
      description
        "NAT interface commands";
      leaf allow-static-host {
        description
          "Allow static-ip clients";
        type empty;
      }
      leaf enable {
        description
          "Enable Address Translation (NVI)";
        type empty;
      }
      choice nat-choice {
        leaf inside {
          description
            "Inside interface for address translation";
          type empty;
        }
        leaf outside {
          description
            "Outside interface for address translation";
          type empty;
        }
      }
    }
  }

  grouping live_ncs_config-ip-nat-pool-interface-grouping {
    choice pool-or-interface {
      case pool-choice {
        leaf pool {
          description
            "Name pool of global addresses";
          type string;
        }
        leaf redundancy {
          description
            "NAT redundancy operation";
          type uint8 {
            range "1..2";
          }
        }
        leaf mapping-id {
          description
            "Associate a mapping id to this mapping";
          type uint32 {
            range "1..2147483647";
          }
        }
      }
      case interface-choice {
        container interface {
          description
            "Specify interface for global address";
          uses ios-ifc:live_ncs_interface-grouping;
        }
      }
    }
    leaf no-payload {
      description
        "No translation of embedded address/port in the payload";
      type empty;
    }
    leaf reversible {
      // NCS drop when statement
      type empty;
    }
    leaf vrf {
      description
        "Specify vrf";
      type string;
    }
    leaf match-in-vrf {
      description
        "Match incoming vrf";
      // NCS drop when statement
      type empty;
    }
    leaf overload {
      description
        "Overload an address translation";
      type empty;
    }
    leaf oer {
      description
        "Use with vtemplate only. On new translation, if OER BR is UP,
         OER will select IP from outgoing Interface.
         All packets matching translation are forwarded over Interface
         for duration of translation.";
      type empty;
    }
  }

  grouping live_ncs_config-ip-nat-grouping {
    container nat {
      description
        "NAT configuration commands";
      list pool {
        description
          "Define pool of addresses";
        key "id";
        leaf id {
          type string;
        }
        leaf start-address {
          type inet:ipv4-address;
        }
        leaf end-address {
          // NCS drop when statement
          type inet:ipv4-address;
        }
        choice prefix-choice {
          leaf netmask {
            description
              "Specify the network mask";
            type inet:ipv4-address;
          }
          leaf prefix-length {
            description
              "Specify the prefix length";
            type uint8 {
              range "1..32";
            }
          }
        }
        leaf accounting {
          description
            "Specify the accounting";
          type string;
        }
        choice nat-choice {
          leaf arp-ping {
            description
              "WLAN ARP Ping";
            type empty;
          }
          leaf type {
            description
              "Specify the pool type";
            type enumeration {
              enum "match-host";
              enum "rotary";
            }
          }
          leaf add-route {
            description
              "Add special route to Virtual Interface";
            type empty;
          }
        }
      }
      container inside {
        description
          "Inside address translation";
        container source {
          description
            "Source address translation";
          list list {
            description
              "Specify access list describing local addresses";
            key "id";
            leaf id {
              type union {
                type uint16 {
                  range "1..2699";
                }
                type string;
              }
            }
            uses live_ncs_config-ip-nat-pool-interface-grouping;
          }
          list route-map {
            description
              "Specify route-map";
            key "route-map-name";
            leaf route-map-name {
              description
                "Route-map name";
              type string;
            }
            container pool {
              description
                "Name pool of global addresses";
              leaf pool-name {
                description
                  "Pool name for global addresses";
                type string;
              }
              leaf vrf {
                description
                  "Specify vrf";
                type string;
              }
              leaf match-in-vrf {
                description
                  "Match incoming vrf";
                type empty;
              }
            }
            container interface {
              description
                "Specify interface for global address";
              uses ios-ifc:live_ncs_interface-grouping;
            }
            container oer {
              description
                "Use with vtemplate only.  On new translation,
                 if OER BR is UP, OER will select IP from outgoing Interface.
                 All packets matching translation are forwarded over
                 Interface for duration of translation.";
              leaf overload {
                description
                  "Overload an address translation";
                type empty;
              }
              leaf extended {
                description
                  "Overload extended";
                type empty;
              }
            }
            container overload {
              description
                "Overload an address translation";
              leaf extended {
                description
                  "Overload extended";
                type empty;
              }
              leaf oer {
                description
                  "Use with vtemplate only.  On new translation,
                   if OER BR is UP, OER will select IP from outgoing
                   Interface.  All packets matching translation are
                   forwarded over Interface for duration of translation.";
                type empty;
              }
            }
            list vrf {
              description
                "Specify vrf";
              key "vrf-name";
              leaf vrf-name {
                description
                  "vrf name";
                type string;
              }
              container oer {
                description
                  "Use with vtemplate only.  On new translation,
                   if OER BR is UP, OER will select IP from outgoing
                   Interface.  All packets matching translation are
                   forwarded over Interface for duration of translation.";
                presence "true";
                leaf overload {
                  description
                    "Overload an address translation";
                  type empty;
                }
              }
              container overload {
                description
                  "Overload an address translation";
                presence "true";
                leaf oer {
                  description
                    "Use with vtemplate only.  On new translation,
                     if OER BR is UP, OER will select IP from outgoing
                     Interface.  All packets matching translation are
                     forwarded over Interface for duration of translation.";
                  type empty;
                }
              }
            }
          }
          container static {
            description
              "Specify static local->global mapping";
            list nat-static-transport-list {
              key "local-ip global-ip";
              leaf local-ip {
                type inet:ipv4-address;
              }
              leaf global-ip {
                type inet:ipv4-address;
              }
              leaf proto {
                type enumeration {
                  enum "tcp";
                  enum "udp";
                }
              }
              leaf network {
                description
                  "Subnet translation";
                type empty;
              }
              leaf local-port {
                type uint16 {
                  range "1..65535";
                }
              }
              leaf mask {
                type union {
                  type string;
                  type inet:ipv4-address;
                }
              }
              leaf global-port {
                type uint16 {
                  range "1..65535";
                }
              }
              leaf extendable {
                description
                  "Extend this translation when used";
                type empty;
              }
              leaf no-alias {
                description
                  "Do not create an alias for the global address";
                type empty;
              }
              leaf no-payload {
                description
                  "No translation of embedded address/port in the payload";
                type empty;
              }
              leaf route-map {
                description
                  "Specify route-map";
                type string;
              }
              leaf reversible {
                // NCS drop when statement
                type empty;
              }
              leaf redundancy {
                description
                  "NAT redundancy operation";
                type union {
                  type uint8;
                  type string;
                }
              }
              leaf mapping-id {
                description
                  "Associate a mapping id to this mapping";
                // NCS drop when statement
                type uint32 {
                  range "1..2147483647";
                }
              }
              leaf vrf {
                description
                  "Specify vrf";
                type string;
              }
              leaf match-in-vrf {
                description
                  "Match incoming vrf";
                // NCS drop when statement
                type empty;
              }
              leaf forced {
                description
                  "Delete this entry and its children, even if in use";
                type empty;
              }
              leaf overload {
                description
                  "Overload an address translation";
                type empty;
              }
            }
            list nat-static-transport-interface-list {
              key "proto local-ip local-port";
              leaf proto {
                type enumeration {
                  enum "tcp";
                  enum "udp";
                }
              }
              leaf local-ip {
                type inet:ipv4-address;
              }
              leaf local-port {
                type uint16 {
                  range "1..65535";
                }
              }
              container interface {
                description
                  "Specify interface for global address";
                uses ios-ifc:live_ncs_interface-grouping;
              }
              leaf global-port {
                type uint16 {
                  range "1..65535";
                }
              }
            }
          }
        }
        container destination {
          description
            "Destination address translation";
          list list {
            description
              "Specify access list describing global addresses";
            key "id";
            leaf id {
              type union {
                type uint16 {
                  range "1..2699";
                }
                type string;
              }
            }
            leaf pool {
              description
                "Name pool of local addresses";
              type string;
            }
            leaf redundancy {
              description
                "NAT redundancy operation";
              type uint8 {
                range "1..2";
              }
            }
            leaf mapping-id {
              description
                "Associate a mapping id to this mapping";
              type uint32 {
                range "1..2147483647";
              }
            }
          }
        }
      }
      container outside {
        description
          "Outside address translation";
        container source {
          description
            "Source address translation";
          container static {
            description
              "Specify static global->local mapping";
            list nat-static-transport-list {
              key "global-ip local-ip";
              leaf global-ip {
                type inet:ipv4-address;
              }
              leaf local-ip {
                type inet:ipv4-address;
              }
              leaf vrf {
                description
                  "Specify vrf";
                type string;
              }
              leaf extendable {
                description
                  "Extend this translation when used";
                type empty;
              }
              leaf no-payload {
                description
                  "No translation of embedded address/port in the payload";
                type empty;
              }
            }
          }
        }
        list list {
          description
            "Specify access list describing global addresses";
          key "id";
          leaf id {
            type union {
              type uint16 {
                range "1..2699";
              }
              type string;
            }
          }
          leaf pool {
            description
              "Name pool of local addresses";
            type string;
          }
          leaf mapping-id {
            description
              "Associate a mapping id to this mapping";
            type uint32 {
              range "1..2147483647";
            }
          }
          leaf vrf {
            description
              "Specify vrf";
            type string;
          }
          leaf add-route {
            description
              "Add a static route for outside local address";
            type empty;
          }
        }
        list route-map {
          description
            "Specify route-map";
          key "id";
          leaf id {
            type string;
          }
          leaf pool {
            description
              "Name pool of local addresses";
            type string;
          }
          leaf mapping-id {
            description
              "Associate a mapping id to this mapping";
            type uint32 {
              range "1..2147483647";
            }
          }
          leaf vrf {
            description
              "Specify vrf";
            type string;
          }
          leaf add-route {
            description
              "Add a static route for outside local address";
            type empty;
          }
        }
      }
    }
  }

  grouping live_ncs_config-nat66-grouping {
    container nat66 {
      description
        "NAT66 configuration commands";
      container prefix {
        description
          "NAT66 prefix";
        list inside {
          description
            "inside prefix";
          key "inside-pfx";
          leaf inside-pfx {
            description
              "IPv6 prefix";
            type ios-types:ipv6-prefix;
          }
          leaf outside {
            description
              "outside prefix";
            type ios-types:ipv6-prefix;
          }
        }
      }
    }
  }

  grouping live_ncs_config-interface-nat66-grouping {
    leaf nat66 {
      description
        "NAT66 interface commands";
      type enumeration {
        enum "inside";
        enum "outside";
      }
    }
  }

  grouping config-interface-ip-nat-grouping {
    container nat {
      description
        "NAT interface commands";
      leaf allow-static-host {
        description
          "Allow static-ip clients";
        type empty;
      }
      leaf enable {
        description
          "Enable Address Translation (NVI)";
        type empty;
      }
      choice nat-choice {
        leaf inside {
          description
            "Inside interface for address translation";
          type empty;
        }
        leaf outside {
          description
            "Outside interface for address translation";
          type empty;
        }
      }
    }
  }

  grouping config-ip-nat-pool-interface-grouping {
    choice pool-or-interface {
      case pool-choice {
        leaf pool {
          description
            "Name pool of global addresses";
          type string;
        }
        leaf redundancy {
          description
            "NAT redundancy operation";
          type uint8 {
            range "1..2";
          }
        }
        leaf mapping-id {
          description
            "Associate a mapping id to this mapping";
          type uint32 {
            range "1..2147483647";
          }
        }
      }
      case interface-choice {
        container interface {
          description
            "Specify interface for global address";
          uses ios-ifc:interface-grouping;
        }
      }
    }
    leaf no-payload {
      description
        "No translation of embedded address/port in the payload";
      type empty;
    }
    leaf reversible {
      when "../../route-map" {
        tailf:xpath-root 3;
      }
      type empty;
    }
    leaf vrf {
      description
        "Specify vrf";
      type string;
    }
    leaf match-in-vrf {
      description
        "Match incoming vrf";
      when "../vrf" {
        tailf:xpath-root 3;
      }
      type empty;
    }
    leaf overload {
      description
        "Overload an address translation";
      type empty;
    }
    leaf oer {
      description
        "Use with vtemplate only. On new translation, if OER BR is UP,
         OER will select IP from outgoing Interface.
         All packets matching translation are forwarded over Interface
         for duration of translation.";
      type empty;
    }
  }

  grouping config-ip-nat-grouping {
    container nat {
      description
        "NAT configuration commands";
      list pool {
        description
          "Define pool of addresses";
        key "id";
        leaf id {
          type string;
        }
        leaf start-address {
          type inet:ipv4-address;
        }
        leaf end-address {
          when "../start-address" {
            tailf:xpath-root 3;
          }
          type inet:ipv4-address;
        }
        choice prefix-choice {
          leaf netmask {
            description
              "Specify the network mask";
            type inet:ipv4-address;
          }
          leaf prefix-length {
            description
              "Specify the prefix length";
            type uint8 {
              range "1..32";
            }
          }
        }
        leaf accounting {
          description
            "Specify the accounting";
          type string;
        }
        choice nat-choice {
          leaf arp-ping {
            description
              "WLAN ARP Ping";
            type empty;
          }
          leaf type {
            description
              "Specify the pool type";
            type enumeration {
              enum "match-host";
              enum "rotary";
            }
          }
          leaf add-route {
            description
              "Add special route to Virtual Interface";
            type empty;
          }
        }
      }
      container inside {
        description
          "Inside address translation";
        container source {
          description
            "Source address translation";
          list list {
            description
              "Specify access list describing local addresses";
            key "id";
            leaf id {
              type union {
                type uint16 {
                  range "1..2699";
                }
                type string;
              }
            }
            uses config-ip-nat-pool-interface-grouping;
          }
          list route-map {
            description
              "Specify route-map";
            key "route-map-name";
            leaf route-map-name {
              description
                "Route-map name";
              type string;
            }
            container pool {
              description
                "Name pool of global addresses";
              leaf pool-name {
                description
                  "Pool name for global addresses";
                type string;
              }
              leaf vrf {
                description
                  "Specify vrf";
                type string;
              }
              leaf match-in-vrf {
                description
                  "Match incoming vrf";
                type empty;
              }
            }
            container interface {
              description
                "Specify interface for global address";
              uses ios-ifc:interface-grouping;
            }
            container oer {
              description
                "Use with vtemplate only.  On new translation,
                 if OER BR is UP, OER will select IP from outgoing Interface.
                 All packets matching translation are forwarded over
                 Interface for duration of translation.";
              leaf overload {
                description
                  "Overload an address translation";
                type empty;
              }
              leaf extended {
                description
                  "Overload extended";
                type empty;
              }
            }
            container overload {
              description
                "Overload an address translation";
              leaf extended {
                description
                  "Overload extended";
                type empty;
              }
              leaf oer {
                description
                  "Use with vtemplate only.  On new translation,
                   if OER BR is UP, OER will select IP from outgoing
                   Interface.  All packets matching translation are
                   forwarded over Interface for duration of translation.";
                type empty;
              }
            }
            list vrf {
              description
                "Specify vrf";
              key "vrf-name";
              leaf vrf-name {
                description
                  "vrf name";
                type string;
              }
              container oer {
                description
                  "Use with vtemplate only.  On new translation,
                   if OER BR is UP, OER will select IP from outgoing
                   Interface.  All packets matching translation are
                   forwarded over Interface for duration of translation.";
                presence "true";
                leaf overload {
                  description
                    "Overload an address translation";
                  type empty;
                }
              }
              container overload {
                description
                  "Overload an address translation";
                presence "true";
                leaf oer {
                  description
                    "Use with vtemplate only.  On new translation,
                     if OER BR is UP, OER will select IP from outgoing
                     Interface.  All packets matching translation are
                     forwarded over Interface for duration of translation.";
                  type empty;
                }
              }
            }
          }
          container static {
            description
              "Specify static local->global mapping";
            list nat-static-transport-list {
              key "local-ip global-ip";
              leaf local-ip {
                type inet:ipv4-address;
              }
              leaf global-ip {
                type inet:ipv4-address;
              }
              leaf proto {
                type enumeration {
                  enum "tcp";
                  enum "udp";
                }
              }
              leaf network {
                description
                  "Subnet translation";
                type empty;
              }
              leaf local-port {
                type uint16 {
                  range "1..65535";
                }
              }
              leaf mask {
                type union {
                  type string;
                  type inet:ipv4-address;
                }
              }
              leaf global-port {
                type uint16 {
                  range "1..65535";
                }
              }
              leaf extendable {
                description
                  "Extend this translation when used";
                type empty;
              }
              leaf no-alias {
                description
                  "Do not create an alias for the global address";
                type empty;
              }
              leaf no-payload {
                description
                  "No translation of embedded address/port in the payload";
                type empty;
              }
              leaf route-map {
                description
                  "Specify route-map";
                type string;
              }
              leaf reversible {
                when "../route-map" {
                  tailf:xpath-root 3;
                }
                type empty;
              }
              leaf redundancy {
                description
                  "NAT redundancy operation";
                type union {
                  type uint8;
                  type string;
                }
              }
              leaf mapping-id {
                description
                  "Associate a mapping id to this mapping";
                when "../redundancy" {
                  tailf:xpath-root 3;
                }
                type uint32 {
                  range "1..2147483647";
                }
              }
              leaf vrf {
                description
                  "Specify vrf";
                type string;
              }
              leaf match-in-vrf {
                description
                  "Match incoming vrf";
                when "../vrf" {
                  tailf:xpath-root 3;
                }
                type empty;
              }
              leaf forced {
                description
                  "Delete this entry and its children, even if in use";
                type empty;
              }
              leaf overload {
                description
                  "Overload an address translation";
                type empty;
              }
            }
            list nat-static-transport-interface-list {
              key "proto local-ip local-port";
              leaf proto {
                type enumeration {
                  enum "tcp";
                  enum "udp";
                }
              }
              leaf local-ip {
                type inet:ipv4-address;
              }
              leaf local-port {
                type uint16 {
                  range "1..65535";
                }
              }
              container interface {
                description
                  "Specify interface for global address";
                uses ios-ifc:interface-grouping;
              }
              leaf global-port {
                type uint16 {
                  range "1..65535";
                }
              }
            }
          }
        }
        container destination {
          description
            "Destination address translation";
          list list {
            description
              "Specify access list describing global addresses";
            key "id";
            leaf id {
              type union {
                type uint16 {
                  range "1..2699";
                }
                type string;
              }
            }
            leaf pool {
              description
                "Name pool of local addresses";
              type string;
            }
            leaf redundancy {
              description
                "NAT redundancy operation";
              type uint8 {
                range "1..2";
              }
            }
            leaf mapping-id {
              description
                "Associate a mapping id to this mapping";
              type uint32 {
                range "1..2147483647";
              }
            }
          }
        }
      }
      container outside {
        description
          "Outside address translation";
        container source {
          description
            "Source address translation";
          container static {
            description
              "Specify static global->local mapping";
            list nat-static-transport-list {
              key "global-ip local-ip";
              leaf global-ip {
                type inet:ipv4-address;
              }
              leaf local-ip {
                type inet:ipv4-address;
              }
              leaf vrf {
                description
                  "Specify vrf";
                type string;
              }
              leaf extendable {
                description
                  "Extend this translation when used";
                type empty;
              }
              leaf no-payload {
                description
                  "No translation of embedded address/port in the payload";
                type empty;
              }
            }
          }
        }
        list list {
          description
            "Specify access list describing global addresses";
          key "id";
          leaf id {
            type union {
              type uint16 {
                range "1..2699";
              }
              type string;
            }
          }
          leaf pool {
            description
              "Name pool of local addresses";
            type string;
          }
          leaf mapping-id {
            description
              "Associate a mapping id to this mapping";
            type uint32 {
              range "1..2147483647";
            }
          }
          leaf vrf {
            description
              "Specify vrf";
            type string;
          }
          leaf add-route {
            description
              "Add a static route for outside local address";
            type empty;
          }
        }
        list route-map {
          description
            "Specify route-map";
          key "id";
          leaf id {
            type string;
          }
          leaf pool {
            description
              "Name pool of local addresses";
            type string;
          }
          leaf mapping-id {
            description
              "Associate a mapping id to this mapping";
            type uint32 {
              range "1..2147483647";
            }
          }
          leaf vrf {
            description
              "Specify vrf";
            type string;
          }
          leaf add-route {
            description
              "Add a static route for outside local address";
            type empty;
          }
        }
      }
    }
  }

  grouping config-nat66-grouping {
    container nat66 {
      description
        "NAT66 configuration commands";
      container prefix {
        description
          "NAT66 prefix";
        list inside {
          description
            "inside prefix";
          key "inside-pfx";
          leaf inside-pfx {
            description
              "IPv6 prefix";
            type ios-types:ipv6-prefix;
          }
          leaf outside {
            description
              "outside prefix";
            type ios-types:ipv6-prefix;
          }
        }
      }
    }
  }

  grouping config-interface-nat66-grouping {
    leaf nat66 {
      description
        "NAT66 interface commands";
      type enumeration {
        enum "inside";
        enum "outside";
      }
    }
  }

  augment "/ncs:devices/ncs:template/ncs:config/ios:native/ios:ip" {
    uses ncs_template_config-ip-nat-grouping;
  }
  augment "/ncs:devices/ncs:device/ncs:live-status/ios:native/ios:ip" {
    uses live_ncs_config-ip-nat-grouping {
      refine nat {
        tailf:ncs-device-type "netconf";
        tailf:display-when "not(../../../../ncs:module) or ../../../../ncs:module[ncs:name='Cisco-IOS-XE-nat'] or (../../../../ncs:live-status-protocol[not(ncs:capability)]) or (../../../../ncs:live-status-protocol/ncs:capability/ncs:module[.='Cisco-IOS-XE-nat'])";
      }
    }
  }
  augment "/ncs:devices/ncs:device/ncs:config/ios:native/ios:ip" {
    uses config-ip-nat-grouping {
      refine nat {
        tailf:ncs-device-type "netconf";
        tailf:display-when "not(../../../../ncs:module) or ../../../../ncs:module[ncs:name='Cisco-IOS-XE-nat']";
      }
    }
  }
  augment "/ncs:devices/ncs:template/ncs:config/ios:native/ios:interface/ios:FastEthernet/ios:ip" {
    uses ncs_template_config-interface-ip-nat-grouping;
  }
  augment "/ncs:devices/ncs:device/ncs:live-status/ios:native/ios:interface/ios:FastEthernet/ios:ip" {
    uses live_ncs_config-interface-ip-nat-grouping {
      refine nat {
        tailf:ncs-device-type "netconf";
        tailf:display-when "not(../../../../../../ncs:module) or ../../../../../../ncs:module[ncs:name='Cisco-IOS-XE-nat'] or (../../../../../../ncs:live-status-protocol[not(ncs:capability)]) or (../../../../../../ncs:live-status-protocol/ncs:capability/ncs:module[.='Cisco-IOS-XE-nat'])";
      }
    }
  }
  augment "/ncs:devices/ncs:device/ncs:config/ios:native/ios:interface/ios:FastEthernet/ios:ip" {
    uses config-interface-ip-nat-grouping {
      refine nat {
        tailf:ncs-device-type "netconf";
        tailf:display-when "not(../../../../../../ncs:module) or ../../../../../../ncs:module[ncs:name='Cisco-IOS-XE-nat']";
      }
    }
  }
  augment "/ncs:devices/ncs:template/ncs:config/ios:native/ios:interface/ios:GigabitEthernet/ios:ip" {
    uses ncs_template_config-interface-ip-nat-grouping;
  }
  augment "/ncs:devices/ncs:device/ncs:live-status/ios:native/ios:interface/ios:GigabitEthernet/ios:ip" {
    uses live_ncs_config-interface-ip-nat-grouping {
      refine nat {
        tailf:ncs-device-type "netconf";
        tailf:display-when "not(../../../../../../ncs:module) or ../../../../../../ncs:module[ncs:name='Cisco-IOS-XE-nat'] or (../../../../../../ncs:live-status-protocol[not(ncs:capability)]) or (../../../../../../ncs:live-status-protocol/ncs:capability/ncs:module[.='Cisco-IOS-XE-nat'])";
      }
    }
  }
  augment "/ncs:devices/ncs:device/ncs:config/ios:native/ios:interface/ios:GigabitEthernet/ios:ip" {
    uses config-interface-ip-nat-grouping {
      refine nat {
        tailf:ncs-device-type "netconf";
        tailf:display-when "not(../../../../../../ncs:module) or ../../../../../../ncs:module[ncs:name='Cisco-IOS-XE-nat']";
      }
    }
  }
  augment "/ncs:devices/ncs:template/ncs:config/ios:native/ios:interface/ios:TenGigabitEthernet/ios:ip" {
    uses ncs_template_config-interface-ip-nat-grouping;
  }
  augment "/ncs:devices/ncs:device/ncs:live-status/ios:native/ios:interface/ios:TenGigabitEthernet/ios:ip" {
    uses live_ncs_config-interface-ip-nat-grouping {
      refine nat {
        tailf:ncs-device-type "netconf";
        tailf:display-when "not(../../../../../../ncs:module) or ../../../../../../ncs:module[ncs:name='Cisco-IOS-XE-nat'] or (../../../../../../ncs:live-status-protocol[not(ncs:capability)]) or (../../../../../../ncs:live-status-protocol/ncs:capability/ncs:module[.='Cisco-IOS-XE-nat'])";
      }
    }
  }
  augment "/ncs:devices/ncs:device/ncs:config/ios:native/ios:interface/ios:TenGigabitEthernet/ios:ip" {
    uses config-interface-ip-nat-grouping {
      refine nat {
        tailf:ncs-device-type "netconf";
        tailf:display-when "not(../../../../../../ncs:module) or ../../../../../../ncs:module[ncs:name='Cisco-IOS-XE-nat']";
      }
    }
  }
  augment "/ncs:devices/ncs:template/ncs:config/ios:native/ios:interface/ios:Port-channel/ios:ip" {
    uses ncs_template_config-interface-ip-nat-grouping;
  }
  augment "/ncs:devices/ncs:device/ncs:live-status/ios:native/ios:interface/ios:Port-channel/ios:ip" {
    uses live_ncs_config-interface-ip-nat-grouping {
      refine nat {
        tailf:ncs-device-type "netconf";
        tailf:display-when "not(../../../../../../ncs:module) or ../../../../../../ncs:module[ncs:name='Cisco-IOS-XE-nat'] or (../../../../../../ncs:live-status-protocol[not(ncs:capability)]) or (../../../../../../ncs:live-status-protocol/ncs:capability/ncs:module[.='Cisco-IOS-XE-nat'])";
      }
    }
  }
  augment "/ncs:devices/ncs:device/ncs:config/ios:native/ios:interface/ios:Port-channel/ios:ip" {
    uses config-interface-ip-nat-grouping {
      refine nat {
        tailf:ncs-device-type "netconf";
        tailf:display-when "not(../../../../../../ncs:module) or ../../../../../../ncs:module[ncs:name='Cisco-IOS-XE-nat']";
      }
    }
  }
  augment "/ncs:devices/ncs:template/ncs:config/ios:native/ios:interface/ios:Loopback/ios:ip" {
    uses ncs_template_config-interface-ip-nat-grouping;
  }
  augment "/ncs:devices/ncs:device/ncs:live-status/ios:native/ios:interface/ios:Loopback/ios:ip" {
    uses live_ncs_config-interface-ip-nat-grouping {
      refine nat {
        tailf:ncs-device-type "netconf";
        tailf:display-when "not(../../../../../../ncs:module) or ../../../../../../ncs:module[ncs:name='Cisco-IOS-XE-nat'] or (../../../../../../ncs:live-status-protocol[not(ncs:capability)]) or (../../../../../../ncs:live-status-protocol/ncs:capability/ncs:module[.='Cisco-IOS-XE-nat'])";
      }
    }
  }
  augment "/ncs:devices/ncs:device/ncs:config/ios:native/ios:interface/ios:Loopback/ios:ip" {
    uses config-interface-ip-nat-grouping {
      refine nat {
        tailf:ncs-device-type "netconf";
        tailf:display-when "not(../../../../../../ncs:module) or ../../../../../../ncs:module[ncs:name='Cisco-IOS-XE-nat']";
      }
    }
  }
  augment "/ncs:devices/ncs:template/ncs:config/ios:native" {
    uses ncs_template_config-nat66-grouping;
  }
  augment "/ncs:devices/ncs:device/ncs:live-status/ios:native" {
    uses live_ncs_config-nat66-grouping {
      refine nat66 {
        tailf:ncs-device-type "netconf";
        tailf:display-when "not(../../../ncs:module) or ../../../ncs:module[ncs:name='Cisco-IOS-XE-nat'] or (../../../ncs:live-status-protocol[not(ncs:capability)]) or (../../../ncs:live-status-protocol/ncs:capability/ncs:module[.='Cisco-IOS-XE-nat'])";
      }
    }
  }
  augment "/ncs:devices/ncs:device/ncs:config/ios:native" {
    uses config-nat66-grouping {
      refine nat66 {
        tailf:ncs-device-type "netconf";
        tailf:display-when "not(../../../ncs:module) or ../../../ncs:module[ncs:name='Cisco-IOS-XE-nat']";
      }
    }
  }
  augment "/ncs:devices/ncs:template/ncs:config/ios:native/ios:interface/ios:FastEthernet" {
    uses ncs_template_config-interface-nat66-grouping;
  }
  augment "/ncs:devices/ncs:device/ncs:live-status/ios:native/ios:interface/ios:FastEthernet" {
    uses live_ncs_config-interface-nat66-grouping {
      refine nat66 {
        tailf:ncs-device-type "netconf";
        tailf:display-when "not(../../../../../ncs:module) or ../../../../../ncs:module[ncs:name='Cisco-IOS-XE-nat'] or (../../../../../ncs:live-status-protocol[not(ncs:capability)]) or (../../../../../ncs:live-status-protocol/ncs:capability/ncs:module[.='Cisco-IOS-XE-nat'])";
      }
    }
  }
  augment "/ncs:devices/ncs:device/ncs:config/ios:native/ios:interface/ios:FastEthernet" {
    uses config-interface-nat66-grouping {
      refine nat66 {
        tailf:ncs-device-type "netconf";
        tailf:display-when "not(../../../../../ncs:module) or ../../../../../ncs:module[ncs:name='Cisco-IOS-XE-nat']";
      }
    }
  }
  augment "/ncs:devices/ncs:template/ncs:config/ios:native/ios:interface/ios:GigabitEthernet" {
    uses ncs_template_config-interface-nat66-grouping;
  }
  augment "/ncs:devices/ncs:device/ncs:live-status/ios:native/ios:interface/ios:GigabitEthernet" {
    uses live_ncs_config-interface-nat66-grouping {
      refine nat66 {
        tailf:ncs-device-type "netconf";
        tailf:display-when "not(../../../../../ncs:module) or ../../../../../ncs:module[ncs:name='Cisco-IOS-XE-nat'] or (../../../../../ncs:live-status-protocol[not(ncs:capability)]) or (../../../../../ncs:live-status-protocol/ncs:capability/ncs:module[.='Cisco-IOS-XE-nat'])";
      }
    }
  }
  augment "/ncs:devices/ncs:device/ncs:config/ios:native/ios:interface/ios:GigabitEthernet" {
    uses config-interface-nat66-grouping {
      refine nat66 {
        tailf:ncs-device-type "netconf";
        tailf:display-when "not(../../../../../ncs:module) or ../../../../../ncs:module[ncs:name='Cisco-IOS-XE-nat']";
      }
    }
  }
  augment "/ncs:devices/ncs:template/ncs:config/ios:native/ios:interface/ios:TenGigabitEthernet" {
    uses ncs_template_config-interface-nat66-grouping;
  }
  augment "/ncs:devices/ncs:device/ncs:live-status/ios:native/ios:interface/ios:TenGigabitEthernet" {
    uses live_ncs_config-interface-nat66-grouping {
      refine nat66 {
        tailf:ncs-device-type "netconf";
        tailf:display-when "not(../../../../../ncs:module) or ../../../../../ncs:module[ncs:name='Cisco-IOS-XE-nat'] or (../../../../../ncs:live-status-protocol[not(ncs:capability)]) or (../../../../../ncs:live-status-protocol/ncs:capability/ncs:module[.='Cisco-IOS-XE-nat'])";
      }
    }
  }
  augment "/ncs:devices/ncs:device/ncs:config/ios:native/ios:interface/ios:TenGigabitEthernet" {
    uses config-interface-nat66-grouping {
      refine nat66 {
        tailf:ncs-device-type "netconf";
        tailf:display-when "not(../../../../../ncs:module) or ../../../../../ncs:module[ncs:name='Cisco-IOS-XE-nat']";
      }
    }
  }
  augment "/ncs:devices/ncs:template/ncs:config/ios:native/ios:interface/ios:Port-channel" {
    uses ncs_template_config-interface-nat66-grouping;
  }
  augment "/ncs:devices/ncs:device/ncs:live-status/ios:native/ios:interface/ios:Port-channel" {
    uses live_ncs_config-interface-nat66-grouping {
      refine nat66 {
        tailf:ncs-device-type "netconf";
        tailf:display-when "not(../../../../../ncs:module) or ../../../../../ncs:module[ncs:name='Cisco-IOS-XE-nat'] or (../../../../../ncs:live-status-protocol[not(ncs:capability)]) or (../../../../../ncs:live-status-protocol/ncs:capability/ncs:module[.='Cisco-IOS-XE-nat'])";
      }
    }
  }
  augment "/ncs:devices/ncs:device/ncs:config/ios:native/ios:interface/ios:Port-channel" {
    uses config-interface-nat66-grouping {
      refine nat66 {
        tailf:ncs-device-type "netconf";
        tailf:display-when "not(../../../../../ncs:module) or ../../../../../ncs:module[ncs:name='Cisco-IOS-XE-nat']";
      }
    }
  }
  augment "/ncs:devices/ncs:template/ncs:config/ios:native/ios:interface/ios:Loopback" {
    uses ncs_template_config-interface-nat66-grouping;
  }
  augment "/ncs:devices/ncs:device/ncs:live-status/ios:native/ios:interface/ios:Loopback" {
    uses live_ncs_config-interface-nat66-grouping {
      refine nat66 {
        tailf:ncs-device-type "netconf";
        tailf:display-when "not(../../../../../ncs:module) or ../../../../../ncs:module[ncs:name='Cisco-IOS-XE-nat'] or (../../../../../ncs:live-status-protocol[not(ncs:capability)]) or (../../../../../ncs:live-status-protocol/ncs:capability/ncs:module[.='Cisco-IOS-XE-nat'])";
      }
    }
  }
  augment "/ncs:devices/ncs:device/ncs:config/ios:native/ios:interface/ios:Loopback" {
    uses config-interface-nat66-grouping {
      refine nat66 {
        tailf:ncs-device-type "netconf";
        tailf:display-when "not(../../../../../ncs:module) or ../../../../../ncs:module[ncs:name='Cisco-IOS-XE-nat']";
      }
    }
  }
  augment "/ncs:devices/ncs:template/ncs:config/ios:native/ios:interface/ios:Tunnel" {
    uses ncs_template_config-interface-nat66-grouping;
  }
  augment "/ncs:devices/ncs:device/ncs:live-status/ios:native/ios:interface/ios:Tunnel" {
    uses live_ncs_config-interface-nat66-grouping {
      refine nat66 {
        tailf:ncs-device-type "netconf";
        tailf:display-when "not(../../../../../ncs:module) or ../../../../../ncs:module[ncs:name='Cisco-IOS-XE-nat'] or (../../../../../ncs:live-status-protocol[not(ncs:capability)]) or (../../../../../ncs:live-status-protocol/ncs:capability/ncs:module[.='Cisco-IOS-XE-nat'])";
      }
    }
  }
  augment "/ncs:devices/ncs:device/ncs:config/ios:native/ios:interface/ios:Tunnel" {
    uses config-interface-nat66-grouping {
      refine nat66 {
        tailf:ncs-device-type "netconf";
        tailf:display-when "not(../../../../../ncs:module) or ../../../../../ncs:module[ncs:name='Cisco-IOS-XE-nat']";
      }
    }
  }
}
