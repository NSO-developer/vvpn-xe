module Cisco-IOS-XE-nbar {
  // Generated by yanger -t ncs
  tailf:ncs-device-type "netconf";

  namespace "http://cisco.com/ns/yang/Cisco-IOS-XE-nbar";
  prefix ios-nbar;

  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Network-Based Application Recognition (NBAR) Yang model.
     Copyright (c) 2016 by Cisco Systems, Inc.
     All rights reserved.";

  revision 2017-02-07 {
    description
      "Initial revision";
  }

  grouping ncs_template_ip-nbar-attribute-custom-grouping {
    list custom {
      // NCS patched for predictable order
      ordered-by user;
      description
        "custom group value to be created for attribute";
      key "name";
      leaf name {
        type string;
      }
      leaf help {
        type string;
      }
    }
  }

  grouping ncs_template_config-interface-ip-nbar-grouping {
    container nbar {
      description
        "Network-Based Application Recognition";
      container protocol-discovery {
        description
          "Enable protocol discovery for both ipv4 and ipv6";
        presence "true";
        leaf ipv4-ipv6 {
          type string;
        }
      }
    }
  }

  grouping ncs_template_config-ip-nbar-grouping {
    container nbar {
      description
        "NBAR - Network Based Application Recognition";
      container attribute {
        description
          "Attribute for which custom group value can be created";
        container application-group {
          description
            "Application-group attribute";
          uses ncs_template_ip-nbar-attribute-custom-grouping;
        }
        container category {
          description
            "Category attribute";
          uses ncs_template_ip-nbar-attribute-custom-grouping;
        }
        container sub-category {
          description
            "Sub-category attribute";
          uses ncs_template_ip-nbar-attribute-custom-grouping;
        }
      }
      list attribute-map {
        // NCS patched for predictable order
        ordered-by user;
        description
          "Attribute Map";
        key "name";
        leaf name {
          type string;
        }
        container attribute {
          description
            "Attribute Name";
          leaf application-group {
            description
              "Application-group attribute";
            type string;
          }
          leaf business-relevance {
            description
              "Application business-relevance";
            type string;
          }
          leaf category {
            description
              "Category attribute";
            type string;
          }
          leaf encrypted {
            description
              "Encrypted applications";
            type string;
          }
          leaf sub-category {
            description
              "Sub-category attribute";
            type string;
          }
          leaf traffic-class {
            description
              "SRND class";
            type string;
          }
          leaf tunnel {
            description
              "Tunnelled applications";
            type string;
          }
        }
      }
      list attribute-set {
        // NCS patched for predictable order
        ordered-by user;
        description
          "Set attribute Map";
        key "protocol-name";
        leaf protocol-name {
          type string;
        }
        leaf profile-name {
          type string;
        }
      }
      list custom {
        // NCS patched for predictable order
        ordered-by user;
        description
          "Custom PDL (protocol description language) Module";
        key "name";
        leaf name {
          type string;
        }
        container http {
          description
            "Custom protocols based on http parameters";
          leaf cookie {
            description
              "HTTP Cookie";
            type string;
          }
          leaf host {
            description
              "Host name of Origin Server containing resource";
            type string;
          }
          leaf method {
            description
              "HTTP method";
            type string;
          }
          leaf referer {
            description
              "Address the resource request was obtained from";
            type string;
          }
          choice http-uv {
            case url-case {
              leaf url {
                description
                  "Uniform Resource Locator path";
                type string;
              }
            }
            case user-agent-case {
              leaf user-agent {
                description
                  "Software used by agent sending the request";
                type string;
              }
            }
            case version-case {
              leaf version {
                description
                  "HTTP version";
                type string;
              }
            }
            case via-case {
              leaf via {
                description
                  "HTTP via field";
                type string;
              }
            }
          }
          leaf id {
            description
              "Selector ID";
            type string;
          }
        }
      }
    }
  }

  grouping ncs_rpc_notif_ip-nbar-attribute-custom-grouping {
    list custom {
      description
        "custom group value to be created for attribute";
      key "name";
      leaf name {
        type string;
      }
      leaf help {
        type string;
      }
    }
  }

  grouping ncs_rpc_notif_config-interface-ip-nbar-grouping {
    container nbar {
      description
        "Network-Based Application Recognition";
      container protocol-discovery {
        description
          "Enable protocol discovery for both ipv4 and ipv6";
        presence "true";
        leaf ipv4-ipv6 {
          type enumeration {
            enum "ipv4";
            enum "ipv6";
          }
        }
      }
    }
  }

  grouping ncs_rpc_notif_config-ip-nbar-grouping {
    container nbar {
      description
        "NBAR - Network Based Application Recognition";
      container attribute {
        description
          "Attribute for which custom group value can be created";
        container application-group {
          description
            "Application-group attribute";
          uses ncs_rpc_notif_ip-nbar-attribute-custom-grouping;
        }
        container category {
          description
            "Category attribute";
          uses ncs_rpc_notif_ip-nbar-attribute-custom-grouping;
        }
        container sub-category {
          description
            "Sub-category attribute";
          uses ncs_rpc_notif_ip-nbar-attribute-custom-grouping;
        }
      }
      list attribute-map {
        description
          "Attribute Map";
        key "name";
        leaf name {
          type string;
        }
        container attribute {
          description
            "Attribute Name";
          leaf application-group {
            description
              "Application-group attribute";
            type union {
              type string;
              type enumeration {
                enum "aol-group";
                enum "apple-group";
                enum "apple-talk-group";
                enum "banyan-group";
                enum "bittorrent-group";
                enum "capwap-group";
                enum "cisco-jabber-group";
                enum "cisco-phone-group";
                enum "corba-group";
                enum "dameware-group";
                enum "edonkey-emule-group";
                enum "espn-group";
                enum "fasttrack-group";
                enum "flash-group";
                enum "fring-group";
                enum "ftp-group";
                enum "gnutella-group";
                enum "google-group";
                enum "gtalk-group";
                enum "icq-group";
                enum "imap-group";
                enum "ipsec-group";
                enum "irc-group";
                enum "kakao-group";
                enum "kerberos-group";
                enum "ldap-group";
                enum "ms-cloud-group";
                enum "ms-crm-group";
                enum "ms-lync-group";
                enum "msn-messenger-group";
                enum "netbios-group";
                enum "nntp-group";
                enum "npmp-group";
                enum "other";
                enum "pop3-group";
                enum "prm-group";
                enum "qq-group";
                enum "skype-group";
                enum "smtp-group";
                enum "snmp-group";
                enum "sqlsvr-group";
                enum "stun-group";
                enum "telepresence-group";
                enum "tftp-group";
                enum "vmware-group";
                enum "vnc-group";
                enum "wap-group";
                enum "webex-group";
                enum "xns-xerox-group";
                enum "xunlei-group";
                enum "yahoo-group";
                enum "yahoo-messenger-group";
              }
            }
          }
          leaf business-relevance {
            description
              "Application business-relevance";
            type enumeration {
              enum "business-irrelevant";
              enum "business-relevant";
              enum "default";
            }
          }
          leaf category {
            description
              "Category attribute";
            type union {
              type string;
              type enumeration {
                enum "anonymizers";
                enum "backup-and-storage";
                enum "browsing";
                enum "business-and-productivity-tools";
                enum "consumer-file-sharing";
                enum "consumer-internet";
                enum "consumer-messaging";
                enum "consumer-streaming";
                enum "database";
                enum "email";
                enum "epayement";
                enum "file-sharing";
                enum "gaming";
                enum "industrial-protocols";
                enum "instant-messaging";
                enum "inter-process-rpc";
                enum "internet-security";
                enum "layer3-over-ip";
                enum "location-based-services";
                enum "net-admin";
                enum "newsgroup";
                enum "other";
                enum "social-networking";
                enum "software-updates";
                enum "trojan";
                enum "voice-and-video";
              }
            }
          }
          leaf encrypted {
            description
              "Encrypted applications";
            type enumeration {
              enum "encrypted-no";
              enum "encrypted-unassigned";
              enum "encrypted-yes";
            }
          }
          leaf sub-category {
            description
              "Sub-category attribute";
            type union {
              type string;
              type enumeration {
                enum "authentication-services";
                enum "backup-systems";
                enum "consumer-audio-streaming";
                enum "consumer-cloud-storage";
                enum "consumer-multimedia-messaging";
                enum "consumer-video-streaming";
                enum "consumer-web-browsing";
                enum "control-and-signaling";
                enum "desktop-virtualization";
                enum "enterprise-cloud-data-storage";
                enum "enterprise-cloud-services";
                enum "enterprise-data-center-storage";
                enum "enterprise-media-conferencing";
                enum "enterprise-realtime-apps";
                enum "enterprise-rich-media-content";
                enum "enterprise-sw-deployment-tools";
                enum "enterprise-transactional-apps";
                enum "enterprise-video-broadcast";
                enum "enterprise-voice-collaboration";
                enum "file-transfer";
                enum "naming-services";
                enum "network-management";
                enum "os-updates";
                enum "other";
                enum "p2p-file-transfer";
                enum "p2p-networking";
                enum "remote-access-terminal";
                enum "routing-protocol";
                enum "tunneling-protocols";
              }
            }
          }
          leaf traffic-class {
            description
              "SRND class";
            type enumeration {
              enum "broadcast-video";
              enum "bulk-data";
              enum "multimedia-conferencing";
              enum "multimedia-streaming";
              enum "network-control";
              enum "ops-admin-mgmt";
              enum "real-time-interactive";
              enum "signaling";
              enum "transactional-data";
              enum "voip-telephony";
            }
          }
          leaf tunnel {
            description
              "Tunnelled applications";
            type enumeration {
              enum "tunnel-no";
              enum "tunnel-unassigned";
              enum "tunnel-yes";
            }
          }
        }
      }
      list attribute-set {
        description
          "Set attribute Map";
        key "protocol-name";
        leaf protocol-name {
          type string;
        }
        leaf profile-name {
          type string;
        }
      }
      list custom {
        description
          "Custom PDL (protocol description language) Module";
        key "name";
        leaf name {
          type string;
        }
        container http {
          description
            "Custom protocols based on http parameters";
          leaf cookie {
            description
              "HTTP Cookie";
            type string;
          }
          leaf host {
            description
              "Host name of Origin Server containing resource";
            type string;
          }
          leaf method {
            description
              "HTTP method";
            type string;
          }
          leaf referer {
            description
              "Address the resource request was obtained from";
            type string;
          }
          choice http-uv {
            case url-case {
              leaf url {
                description
                  "Uniform Resource Locator path";
                type string;
              }
            }
            case user-agent-case {
              leaf user-agent {
                description
                  "Software used by agent sending the request";
                type string;
              }
            }
            case version-case {
              leaf version {
                description
                  "HTTP version";
                type string;
              }
            }
            case via-case {
              leaf via {
                description
                  "HTTP via field";
                type string;
              }
            }
          }
          leaf id {
            description
              "Selector ID";
            type uint16;
          }
        }
      }
    }
  }

  grouping live_ncs_ip-nbar-attribute-custom-grouping {
    list custom {
      description
        "custom group value to be created for attribute";
      key "name";
      leaf name {
        type string;
      }
      leaf help {
        type string;
      }
    }
  }

  grouping live_ncs_config-interface-ip-nbar-grouping {
    container nbar {
      description
        "Network-Based Application Recognition";
      container protocol-discovery {
        description
          "Enable protocol discovery for both ipv4 and ipv6";
        presence "true";
        leaf ipv4-ipv6 {
          type enumeration {
            enum "ipv4";
            enum "ipv6";
          }
        }
      }
    }
  }

  grouping live_ncs_config-ip-nbar-grouping {
    container nbar {
      description
        "NBAR - Network Based Application Recognition";
      container attribute {
        description
          "Attribute for which custom group value can be created";
        container application-group {
          description
            "Application-group attribute";
          uses live_ncs_ip-nbar-attribute-custom-grouping;
        }
        container category {
          description
            "Category attribute";
          uses live_ncs_ip-nbar-attribute-custom-grouping;
        }
        container sub-category {
          description
            "Sub-category attribute";
          uses live_ncs_ip-nbar-attribute-custom-grouping;
        }
      }
      list attribute-map {
        description
          "Attribute Map";
        key "name";
        leaf name {
          type string;
        }
        container attribute {
          description
            "Attribute Name";
          leaf application-group {
            description
              "Application-group attribute";
            type union {
              type string;
              type enumeration {
                enum "aol-group";
                enum "apple-group";
                enum "apple-talk-group";
                enum "banyan-group";
                enum "bittorrent-group";
                enum "capwap-group";
                enum "cisco-jabber-group";
                enum "cisco-phone-group";
                enum "corba-group";
                enum "dameware-group";
                enum "edonkey-emule-group";
                enum "espn-group";
                enum "fasttrack-group";
                enum "flash-group";
                enum "fring-group";
                enum "ftp-group";
                enum "gnutella-group";
                enum "google-group";
                enum "gtalk-group";
                enum "icq-group";
                enum "imap-group";
                enum "ipsec-group";
                enum "irc-group";
                enum "kakao-group";
                enum "kerberos-group";
                enum "ldap-group";
                enum "ms-cloud-group";
                enum "ms-crm-group";
                enum "ms-lync-group";
                enum "msn-messenger-group";
                enum "netbios-group";
                enum "nntp-group";
                enum "npmp-group";
                enum "other";
                enum "pop3-group";
                enum "prm-group";
                enum "qq-group";
                enum "skype-group";
                enum "smtp-group";
                enum "snmp-group";
                enum "sqlsvr-group";
                enum "stun-group";
                enum "telepresence-group";
                enum "tftp-group";
                enum "vmware-group";
                enum "vnc-group";
                enum "wap-group";
                enum "webex-group";
                enum "xns-xerox-group";
                enum "xunlei-group";
                enum "yahoo-group";
                enum "yahoo-messenger-group";
              }
            }
          }
          leaf business-relevance {
            description
              "Application business-relevance";
            type enumeration {
              enum "business-irrelevant";
              enum "business-relevant";
              enum "default";
            }
          }
          leaf category {
            description
              "Category attribute";
            type union {
              type string;
              type enumeration {
                enum "anonymizers";
                enum "backup-and-storage";
                enum "browsing";
                enum "business-and-productivity-tools";
                enum "consumer-file-sharing";
                enum "consumer-internet";
                enum "consumer-messaging";
                enum "consumer-streaming";
                enum "database";
                enum "email";
                enum "epayement";
                enum "file-sharing";
                enum "gaming";
                enum "industrial-protocols";
                enum "instant-messaging";
                enum "inter-process-rpc";
                enum "internet-security";
                enum "layer3-over-ip";
                enum "location-based-services";
                enum "net-admin";
                enum "newsgroup";
                enum "other";
                enum "social-networking";
                enum "software-updates";
                enum "trojan";
                enum "voice-and-video";
              }
            }
          }
          leaf encrypted {
            description
              "Encrypted applications";
            type enumeration {
              enum "encrypted-no";
              enum "encrypted-unassigned";
              enum "encrypted-yes";
            }
          }
          leaf sub-category {
            description
              "Sub-category attribute";
            type union {
              type string;
              type enumeration {
                enum "authentication-services";
                enum "backup-systems";
                enum "consumer-audio-streaming";
                enum "consumer-cloud-storage";
                enum "consumer-multimedia-messaging";
                enum "consumer-video-streaming";
                enum "consumer-web-browsing";
                enum "control-and-signaling";
                enum "desktop-virtualization";
                enum "enterprise-cloud-data-storage";
                enum "enterprise-cloud-services";
                enum "enterprise-data-center-storage";
                enum "enterprise-media-conferencing";
                enum "enterprise-realtime-apps";
                enum "enterprise-rich-media-content";
                enum "enterprise-sw-deployment-tools";
                enum "enterprise-transactional-apps";
                enum "enterprise-video-broadcast";
                enum "enterprise-voice-collaboration";
                enum "file-transfer";
                enum "naming-services";
                enum "network-management";
                enum "os-updates";
                enum "other";
                enum "p2p-file-transfer";
                enum "p2p-networking";
                enum "remote-access-terminal";
                enum "routing-protocol";
                enum "tunneling-protocols";
              }
            }
          }
          leaf traffic-class {
            description
              "SRND class";
            type enumeration {
              enum "broadcast-video";
              enum "bulk-data";
              enum "multimedia-conferencing";
              enum "multimedia-streaming";
              enum "network-control";
              enum "ops-admin-mgmt";
              enum "real-time-interactive";
              enum "signaling";
              enum "transactional-data";
              enum "voip-telephony";
            }
          }
          leaf tunnel {
            description
              "Tunnelled applications";
            type enumeration {
              enum "tunnel-no";
              enum "tunnel-unassigned";
              enum "tunnel-yes";
            }
          }
        }
      }
      list attribute-set {
        description
          "Set attribute Map";
        key "protocol-name";
        leaf protocol-name {
          type string;
        }
        leaf profile-name {
          type string;
        }
      }
      list custom {
        description
          "Custom PDL (protocol description language) Module";
        key "name";
        leaf name {
          type string;
        }
        container http {
          description
            "Custom protocols based on http parameters";
          leaf cookie {
            description
              "HTTP Cookie";
            type string;
          }
          leaf host {
            description
              "Host name of Origin Server containing resource";
            type string;
          }
          leaf method {
            description
              "HTTP method";
            type string;
          }
          leaf referer {
            description
              "Address the resource request was obtained from";
            type string;
          }
          choice http-uv {
            case url-case {
              leaf url {
                description
                  "Uniform Resource Locator path";
                type string;
              }
            }
            case user-agent-case {
              leaf user-agent {
                description
                  "Software used by agent sending the request";
                type string;
              }
            }
            case version-case {
              leaf version {
                description
                  "HTTP version";
                type string;
              }
            }
            case via-case {
              leaf via {
                description
                  "HTTP via field";
                type string;
              }
            }
          }
          leaf id {
            description
              "Selector ID";
            type uint16;
          }
        }
      }
    }
  }

  grouping ip-nbar-attribute-custom-grouping {
    list custom {
      description
        "custom group value to be created for attribute";
      key "name";
      leaf name {
        type string;
      }
      leaf help {
        type string;
      }
    }
  }

  grouping config-interface-ip-nbar-grouping {
    container nbar {
      description
        "Network-Based Application Recognition";
      container protocol-discovery {
        description
          "Enable protocol discovery for both ipv4 and ipv6";
        presence "true";
        leaf ipv4-ipv6 {
          type enumeration {
            enum "ipv4";
            enum "ipv6";
          }
        }
      }
    }
  }

  grouping config-ip-nbar-grouping {
    container nbar {
      description
        "NBAR - Network Based Application Recognition";
      container attribute {
        description
          "Attribute for which custom group value can be created";
        container application-group {
          description
            "Application-group attribute";
          uses ip-nbar-attribute-custom-grouping;
        }
        container category {
          description
            "Category attribute";
          uses ip-nbar-attribute-custom-grouping;
        }
        container sub-category {
          description
            "Sub-category attribute";
          uses ip-nbar-attribute-custom-grouping;
        }
      }
      list attribute-map {
        description
          "Attribute Map";
        key "name";
        leaf name {
          type string;
        }
        container attribute {
          description
            "Attribute Name";
          leaf application-group {
            description
              "Application-group attribute";
            type union {
              type string;
              type enumeration {
                enum "aol-group";
                enum "apple-group";
                enum "apple-talk-group";
                enum "banyan-group";
                enum "bittorrent-group";
                enum "capwap-group";
                enum "cisco-jabber-group";
                enum "cisco-phone-group";
                enum "corba-group";
                enum "dameware-group";
                enum "edonkey-emule-group";
                enum "espn-group";
                enum "fasttrack-group";
                enum "flash-group";
                enum "fring-group";
                enum "ftp-group";
                enum "gnutella-group";
                enum "google-group";
                enum "gtalk-group";
                enum "icq-group";
                enum "imap-group";
                enum "ipsec-group";
                enum "irc-group";
                enum "kakao-group";
                enum "kerberos-group";
                enum "ldap-group";
                enum "ms-cloud-group";
                enum "ms-crm-group";
                enum "ms-lync-group";
                enum "msn-messenger-group";
                enum "netbios-group";
                enum "nntp-group";
                enum "npmp-group";
                enum "other";
                enum "pop3-group";
                enum "prm-group";
                enum "qq-group";
                enum "skype-group";
                enum "smtp-group";
                enum "snmp-group";
                enum "sqlsvr-group";
                enum "stun-group";
                enum "telepresence-group";
                enum "tftp-group";
                enum "vmware-group";
                enum "vnc-group";
                enum "wap-group";
                enum "webex-group";
                enum "xns-xerox-group";
                enum "xunlei-group";
                enum "yahoo-group";
                enum "yahoo-messenger-group";
              }
            }
          }
          leaf business-relevance {
            description
              "Application business-relevance";
            type enumeration {
              enum "business-irrelevant";
              enum "business-relevant";
              enum "default";
            }
          }
          leaf category {
            description
              "Category attribute";
            type union {
              type string;
              type enumeration {
                enum "anonymizers";
                enum "backup-and-storage";
                enum "browsing";
                enum "business-and-productivity-tools";
                enum "consumer-file-sharing";
                enum "consumer-internet";
                enum "consumer-messaging";
                enum "consumer-streaming";
                enum "database";
                enum "email";
                enum "epayement";
                enum "file-sharing";
                enum "gaming";
                enum "industrial-protocols";
                enum "instant-messaging";
                enum "inter-process-rpc";
                enum "internet-security";
                enum "layer3-over-ip";
                enum "location-based-services";
                enum "net-admin";
                enum "newsgroup";
                enum "other";
                enum "social-networking";
                enum "software-updates";
                enum "trojan";
                enum "voice-and-video";
              }
            }
          }
          leaf encrypted {
            description
              "Encrypted applications";
            type enumeration {
              enum "encrypted-no";
              enum "encrypted-unassigned";
              enum "encrypted-yes";
            }
          }
          leaf sub-category {
            description
              "Sub-category attribute";
            type union {
              type string;
              type enumeration {
                enum "authentication-services";
                enum "backup-systems";
                enum "consumer-audio-streaming";
                enum "consumer-cloud-storage";
                enum "consumer-multimedia-messaging";
                enum "consumer-video-streaming";
                enum "consumer-web-browsing";
                enum "control-and-signaling";
                enum "desktop-virtualization";
                enum "enterprise-cloud-data-storage";
                enum "enterprise-cloud-services";
                enum "enterprise-data-center-storage";
                enum "enterprise-media-conferencing";
                enum "enterprise-realtime-apps";
                enum "enterprise-rich-media-content";
                enum "enterprise-sw-deployment-tools";
                enum "enterprise-transactional-apps";
                enum "enterprise-video-broadcast";
                enum "enterprise-voice-collaboration";
                enum "file-transfer";
                enum "naming-services";
                enum "network-management";
                enum "os-updates";
                enum "other";
                enum "p2p-file-transfer";
                enum "p2p-networking";
                enum "remote-access-terminal";
                enum "routing-protocol";
                enum "tunneling-protocols";
              }
            }
          }
          leaf traffic-class {
            description
              "SRND class";
            type enumeration {
              enum "broadcast-video";
              enum "bulk-data";
              enum "multimedia-conferencing";
              enum "multimedia-streaming";
              enum "network-control";
              enum "ops-admin-mgmt";
              enum "real-time-interactive";
              enum "signaling";
              enum "transactional-data";
              enum "voip-telephony";
            }
          }
          leaf tunnel {
            description
              "Tunnelled applications";
            type enumeration {
              enum "tunnel-no";
              enum "tunnel-unassigned";
              enum "tunnel-yes";
            }
          }
        }
      }
      list attribute-set {
        description
          "Set attribute Map";
        key "protocol-name";
        leaf protocol-name {
          type string;
        }
        leaf profile-name {
          type string;
        }
      }
      list custom {
        description
          "Custom PDL (protocol description language) Module";
        key "name";
        leaf name {
          type string;
        }
        container http {
          description
            "Custom protocols based on http parameters";
          leaf cookie {
            description
              "HTTP Cookie";
            type string;
          }
          leaf host {
            description
              "Host name of Origin Server containing resource";
            type string;
          }
          leaf method {
            description
              "HTTP method";
            type string;
          }
          leaf referer {
            description
              "Address the resource request was obtained from";
            type string;
          }
          choice http-uv {
            case url-case {
              leaf url {
                description
                  "Uniform Resource Locator path";
                type string;
              }
            }
            case user-agent-case {
              leaf user-agent {
                description
                  "Software used by agent sending the request";
                type string;
              }
            }
            case version-case {
              leaf version {
                description
                  "HTTP version";
                type string;
              }
            }
            case via-case {
              leaf via {
                description
                  "HTTP via field";
                type string;
              }
            }
          }
          leaf id {
            description
              "Selector ID";
            type uint16;
          }
        }
      }
    }
  }

  augment "/ncs:devices/ncs:template/ncs:config/ios:native/ios:ip" {
    uses ncs_template_config-ip-nbar-grouping;
  }
  augment "/ncs:devices/ncs:device/ncs:live-status/ios:native/ios:ip" {
    uses live_ncs_config-ip-nbar-grouping {
      refine nbar {
        tailf:ncs-device-type "netconf";
        tailf:display-when "not(../../../../ncs:module) or ../../../../ncs:module[ncs:name='Cisco-IOS-XE-nbar'] or (../../../../ncs:live-status-protocol[not(ncs:capability)]) or (../../../../ncs:live-status-protocol/ncs:capability/ncs:module[.='Cisco-IOS-XE-nbar'])";
      }
    }
  }
  augment "/ncs:devices/ncs:device/ncs:config/ios:native/ios:ip" {
    uses config-ip-nbar-grouping {
      refine nbar {
        tailf:ncs-device-type "netconf";
        tailf:display-when "not(../../../../ncs:module) or ../../../../ncs:module[ncs:name='Cisco-IOS-XE-nbar']";
      }
    }
  }
  augment "/ncs:devices/ncs:template/ncs:config/ios:native/ios:interface/ios:FastEthernet/ios:ip" {
    uses ncs_template_config-interface-ip-nbar-grouping;
  }
  augment "/ncs:devices/ncs:device/ncs:live-status/ios:native/ios:interface/ios:FastEthernet/ios:ip" {
    uses live_ncs_config-interface-ip-nbar-grouping {
      refine nbar {
        tailf:ncs-device-type "netconf";
        tailf:display-when "not(../../../../../../ncs:module) or ../../../../../../ncs:module[ncs:name='Cisco-IOS-XE-nbar'] or (../../../../../../ncs:live-status-protocol[not(ncs:capability)]) or (../../../../../../ncs:live-status-protocol/ncs:capability/ncs:module[.='Cisco-IOS-XE-nbar'])";
      }
    }
  }
  augment "/ncs:devices/ncs:device/ncs:config/ios:native/ios:interface/ios:FastEthernet/ios:ip" {
    uses config-interface-ip-nbar-grouping {
      refine nbar {
        tailf:ncs-device-type "netconf";
        tailf:display-when "not(../../../../../../ncs:module) or ../../../../../../ncs:module[ncs:name='Cisco-IOS-XE-nbar']";
      }
    }
  }
  augment "/ncs:devices/ncs:template/ncs:config/ios:native/ios:interface/ios:GigabitEthernet/ios:ip" {
    uses ncs_template_config-interface-ip-nbar-grouping;
  }
  augment "/ncs:devices/ncs:device/ncs:live-status/ios:native/ios:interface/ios:GigabitEthernet/ios:ip" {
    uses live_ncs_config-interface-ip-nbar-grouping {
      refine nbar {
        tailf:ncs-device-type "netconf";
        tailf:display-when "not(../../../../../../ncs:module) or ../../../../../../ncs:module[ncs:name='Cisco-IOS-XE-nbar'] or (../../../../../../ncs:live-status-protocol[not(ncs:capability)]) or (../../../../../../ncs:live-status-protocol/ncs:capability/ncs:module[.='Cisco-IOS-XE-nbar'])";
      }
    }
  }
  augment "/ncs:devices/ncs:device/ncs:config/ios:native/ios:interface/ios:GigabitEthernet/ios:ip" {
    uses config-interface-ip-nbar-grouping {
      refine nbar {
        tailf:ncs-device-type "netconf";
        tailf:display-when "not(../../../../../../ncs:module) or ../../../../../../ncs:module[ncs:name='Cisco-IOS-XE-nbar']";
      }
    }
  }
  augment "/ncs:devices/ncs:template/ncs:config/ios:native/ios:interface/ios:TenGigabitEthernet/ios:ip" {
    uses ncs_template_config-interface-ip-nbar-grouping;
  }
  augment "/ncs:devices/ncs:device/ncs:live-status/ios:native/ios:interface/ios:TenGigabitEthernet/ios:ip" {
    uses live_ncs_config-interface-ip-nbar-grouping {
      refine nbar {
        tailf:ncs-device-type "netconf";
        tailf:display-when "not(../../../../../../ncs:module) or ../../../../../../ncs:module[ncs:name='Cisco-IOS-XE-nbar'] or (../../../../../../ncs:live-status-protocol[not(ncs:capability)]) or (../../../../../../ncs:live-status-protocol/ncs:capability/ncs:module[.='Cisco-IOS-XE-nbar'])";
      }
    }
  }
  augment "/ncs:devices/ncs:device/ncs:config/ios:native/ios:interface/ios:TenGigabitEthernet/ios:ip" {
    uses config-interface-ip-nbar-grouping {
      refine nbar {
        tailf:ncs-device-type "netconf";
        tailf:display-when "not(../../../../../../ncs:module) or ../../../../../../ncs:module[ncs:name='Cisco-IOS-XE-nbar']";
      }
    }
  }
  augment "/ncs:devices/ncs:template/ncs:config/ios:native/ios:interface/ios:Port-channel/ios:ip" {
    uses ncs_template_config-interface-ip-nbar-grouping;
  }
  augment "/ncs:devices/ncs:device/ncs:live-status/ios:native/ios:interface/ios:Port-channel/ios:ip" {
    uses live_ncs_config-interface-ip-nbar-grouping {
      refine nbar {
        tailf:ncs-device-type "netconf";
        tailf:display-when "not(../../../../../../ncs:module) or ../../../../../../ncs:module[ncs:name='Cisco-IOS-XE-nbar'] or (../../../../../../ncs:live-status-protocol[not(ncs:capability)]) or (../../../../../../ncs:live-status-protocol/ncs:capability/ncs:module[.='Cisco-IOS-XE-nbar'])";
      }
    }
  }
  augment "/ncs:devices/ncs:device/ncs:config/ios:native/ios:interface/ios:Port-channel/ios:ip" {
    uses config-interface-ip-nbar-grouping {
      refine nbar {
        tailf:ncs-device-type "netconf";
        tailf:display-when "not(../../../../../../ncs:module) or ../../../../../../ncs:module[ncs:name='Cisco-IOS-XE-nbar']";
      }
    }
  }
  augment "/ncs:devices/ncs:template/ncs:config/ios:native/ios:interface/ios:Loopback/ios:ip" {
    uses ncs_template_config-interface-ip-nbar-grouping;
  }
  augment "/ncs:devices/ncs:device/ncs:live-status/ios:native/ios:interface/ios:Loopback/ios:ip" {
    uses live_ncs_config-interface-ip-nbar-grouping {
      refine nbar {
        tailf:ncs-device-type "netconf";
        tailf:display-when "not(../../../../../../ncs:module) or ../../../../../../ncs:module[ncs:name='Cisco-IOS-XE-nbar'] or (../../../../../../ncs:live-status-protocol[not(ncs:capability)]) or (../../../../../../ncs:live-status-protocol/ncs:capability/ncs:module[.='Cisco-IOS-XE-nbar'])";
      }
    }
  }
  augment "/ncs:devices/ncs:device/ncs:config/ios:native/ios:interface/ios:Loopback/ios:ip" {
    uses config-interface-ip-nbar-grouping {
      refine nbar {
        tailf:ncs-device-type "netconf";
        tailf:display-when "not(../../../../../../ncs:module) or ../../../../../../ncs:module[ncs:name='Cisco-IOS-XE-nbar']";
      }
    }
  }
  augment "/ncs:devices/ncs:template/ncs:config/ios:native/ios:interface/ios:Tunnel/ios:ip" {
    uses ncs_template_config-interface-ip-nbar-grouping;
  }
  augment "/ncs:devices/ncs:device/ncs:live-status/ios:native/ios:interface/ios:Tunnel/ios:ip" {
    uses live_ncs_config-interface-ip-nbar-grouping {
      refine nbar {
        tailf:ncs-device-type "netconf";
        tailf:display-when "not(../../../../../../ncs:module) or ../../../../../../ncs:module[ncs:name='Cisco-IOS-XE-nbar'] or (../../../../../../ncs:live-status-protocol[not(ncs:capability)]) or (../../../../../../ncs:live-status-protocol/ncs:capability/ncs:module[.='Cisco-IOS-XE-nbar'])";
      }
    }
  }
  augment "/ncs:devices/ncs:device/ncs:config/ios:native/ios:interface/ios:Tunnel/ios:ip" {
    uses config-interface-ip-nbar-grouping {
      refine nbar {
        tailf:ncs-device-type "netconf";
        tailf:display-when "not(../../../../../../ncs:module) or ../../../../../../ncs:module[ncs:name='Cisco-IOS-XE-nbar']";
      }
    }
  }
  augment "/ncs:devices/ncs:template/ncs:config/ios:native/ios:interface/ios:Vlan/ios:ip" {
    uses ncs_template_config-interface-ip-nbar-grouping;
  }
  augment "/ncs:devices/ncs:device/ncs:live-status/ios:native/ios:interface/ios:Vlan/ios:ip" {
    uses live_ncs_config-interface-ip-nbar-grouping {
      refine nbar {
        tailf:ncs-device-type "netconf";
        tailf:display-when "not(../../../../../../ncs:module) or ../../../../../../ncs:module[ncs:name='Cisco-IOS-XE-nbar'] or (../../../../../../ncs:live-status-protocol[not(ncs:capability)]) or (../../../../../../ncs:live-status-protocol/ncs:capability/ncs:module[.='Cisco-IOS-XE-nbar'])";
      }
    }
  }
  augment "/ncs:devices/ncs:device/ncs:config/ios:native/ios:interface/ios:Vlan/ios:ip" {
    uses config-interface-ip-nbar-grouping {
      refine nbar {
        tailf:ncs-device-type "netconf";
        tailf:display-when "not(../../../../../../ncs:module) or ../../../../../../ncs:module[ncs:name='Cisco-IOS-XE-nbar']";
      }
    }
  }
}
