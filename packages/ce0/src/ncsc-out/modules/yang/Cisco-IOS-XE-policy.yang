module Cisco-IOS-XE-policy {
  // Generated by yanger -t ncs
  tailf:ncs-device-type "netconf";

  namespace "http://cisco.com/ns/yang/Cisco-IOS-XE-policy";
  prefix ios-policy;

  import ietf-inet-types {
    prefix inet;
  }
  import ietf-yang-types {
    prefix yang;
  }
  import Cisco-IOS-XE-types {
    prefix ios-types;
  }
  import Cisco-IOS-XE-features {
    prefix ios-features;
  }
  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Policy Map Yang Model.
     Copyright (c) 2016-2017 by Cisco Systems, Inc.
     All rights reserved.";

  revision 2017-06-07 {
    description
      "add dependency match group-object security source";
  }
  revision 2017-03-31 {
    description
      "fix conform-action issue under policy-map";
  }
  revision 2017-03-20 {
    description
      "Add class-map match group-object";
  }
  revision 2017-02-09 {
    description
      "policy-map shape average option - account";
  }
  revision 2017-02-07 {
    description
      "Initial revision";
  }

  typedef police-burst-type {
    type uint32 {
      range "1000..512000000";
    }
  }

  typedef police-bps-type {
    type uint64 {
      range "8000..64000000000";
    }
  }

  typedef police-pps-bps-type {
    type enumeration {
      enum "pps";
      enum "bps";
    }
  }

  typedef police-packets-bytes-type {
    type enumeration {
      enum "packets";
      enum "bytes";
    }
  }

  typedef class-name-type {
    type union {
      type string;
      type enumeration {
        enum "class-default";
      }
    }
  }

  typedef policy-action-type {
    type enumeration {
      enum "bandwidth";
      enum "compression";
      enum "drop";
      enum "estimate";
      enum "fair-queue";
      enum "forward";
      enum "netflow-sampler";
      enum "police";
      enum "priority";
      enum "queue-limit";
      enum "random-detect";
      enum "service-policy";
      enum "set";
      enum "shape";
      enum "trust";
      enum "dbl";
      enum "queue-buffers";
    }
  }

  typedef precedence-type2 {
    type union {
      type uint8 {
        range "0..7";
      }
      type enumeration {
        enum "rsvp";
      }
    }
  }

  grouping ncs_template_police-action-transmit-grouping {
    leaf transmit {
      description
        "transmit packet";
      type empty;
    }
  }

  grouping ncs_template_police-action-drop-grouping {
    leaf drop {
      description
        "drop packet";
      type empty;
    }
  }

  grouping ncs_template_police-conform-action-grouping {
    container conform-set-clp-transmit {
      container conform-action {
        description
          "action when rate is less than conform burst";
        leaf set-clp-transmit {
          description
            "set atm clp and send it";
          type empty;
        }
      }
    }
    container conform-set-cos-transmit {
      container conform-action {
        description
          "action when rate is less than conform burst";
        leaf set-cos-transmit {
          description
            "rewrite packet cos and send it";
          type string;
        }
      }
    }
    container conform-set-cos-transmit-table {
      container conform-action {
        description
          "action when rate is less than conform burst";
        leaf set-cos-transmit {
          description
            "rewrite packet cos and send it";
          type string;
        }
        leaf table {
          description
            "Specify table-map";
          type string;
        }
      }
    }
    container conform-set-discard-class-transmit {
      container conform-action {
        description
          "action when rate is less than conform burst";
        leaf set-discard-class-transmit {
          description
            "set discard-class and send it";
          type string;
        }
      }
    }
    container conform-set-dscp-transmit {
      container conform-action {
        description
          "action when rate is less than conform burst";
        leaf set-dscp-transmit {
          description
            "set dscp and send it";
          type string;
        }
      }
    }
    container conform-set-dscp-transmit-table {
      container conform-action {
        description
          "action when rate is less than conform burst";
        leaf set-dscp-transmit {
          description
            "set dscp and send it";
          type string;
        }
        leaf table {
          description
            "Specify table-map";
          type string;
        }
      }
    }
    container conform-set-frde-transmit {
      container conform-action {
        description
          "action when rate is less than conform burst";
        leaf set-frde-transmit {
          description
            "set FR DE and send it";
          type empty;
        }
      }
    }
    container conform-set-mpls-exp-imposition-transmit {
      container conform-action {
        description
          "action when rate is less than conform burst";
        leaf set-mpls-exp-imposition-transmit {
          description
            "set exp at tag imposition and send it";
          type string;
        }
      }
    }
    container conform-set-mpls-exp-imposition-transmit-table {
      container conform-action {
        description
          "action when rate is less than conform burst";
        leaf set-mpls-exp-imposition-transmit {
          description
            "set exp at tag imposition and send it";
          type string;
        }
        leaf table {
          description
            "Specify table-map";
          type string;
        }
      }
    }
    container conform-set-mpls-exp-topmost-transmit {
      container conform-action {
        description
          "action when rate is less than conform burst";
        leaf set-mpls-exp-topmost-transmit {
          description
            "set exp on topmost label and send it";
          type string;
        }
      }
    }
    container conform-set-mpls-exp-topmost-transmit-table {
      container conform-action {
        description
          "action when rate is less than conform burst";
        leaf set-mpls-exp-topmost-transmit {
          description
            "set exp on topmost label and send it";
          type string;
        }
        leaf table {
          description
            "Specify table-map";
          type string;
        }
      }
    }
    container conform-set-prec-transmit {
      container conform-action {
        description
          "action when rate is less than conform burst";
        leaf set-prec-transmit {
          description
            "rewrite packet precedence and send it";
          type string;
        }
      }
    }
    container conform-set-prec-transmit-table {
      container conform-action {
        description
          "action when rate is less than conform burst";
        leaf set-prec-transmit {
          description
            "rewrite packet precedence and send it";
          type string;
        }
        leaf table {
          description
            "Specify table-map";
          type string;
        }
      }
    }
    container conform-set-qos-transmit {
      container conform-action {
        description
          "action when rate is less than conform burst";
        leaf set-qos-transmit {
          description
            "set qos-group and send it";
          type string;
        }
      }
    }
    container conform-set-qos-transmit-table {
      container conform-action {
        description
          "action when rate is less than conform burst";
        leaf set-qos-transmit {
          description
            "set qos-group and send it";
          type string;
        }
        leaf table {
          description
            "Specify table-map";
          type string;
        }
      }
    }
    container conform-transmit {
      container conform-action {
        description
          "action when rate is less than conform burst";
        uses ncs_template_police-action-transmit-grouping;
      }
    }
    container conform-drop {
      container conform-action {
        description
          "action when rate is less than conform burst";
        uses ncs_template_police-action-drop-grouping;
      }
    }
  }

  grouping ncs_template_police-exceed-action-grouping {
    container exceed-dscp {
      container exceed-action {
        description
          "action when rate is within conform and conform + exceed burst";
        leaf dscp {
          type string;
        }
      }
    }
    container exceed-set-clp-transmit {
      container exceed-action {
        description
          "action when rate is within conform and conform + exceed burst";
        leaf set-clp-transmit {
          description
            "set atm clp and send it";
          type empty;
        }
      }
    }
    container exceed-set-cos-transmit {
      container exceed-action {
        description
          "action when rate is within conform and conform + exceed burst";
        leaf set-cos-transmit {
          description
            "rewrite packet cos and send it";
          type string;
        }
        leaf table {
          description
            "Specify table-map";
          type string;
        }
      }
    }
    container exceed-set-discard-class-transmit {
      container exceed-action {
        description
          "action when rate is within conform and conform + exceed burst";
        leaf set-discard-class-transmit {
          description
            "set discard-class and send it";
          type string;
        }
      }
    }
    container exceed-set-dscp-transmit {
      container exceed-action {
        description
          "action when rate is within conform and conform + exceed burst";
        container set-dscp-transmit {
          container dscp {
            leaf table {
              type string;
            }
          }
        }
      }
    }
    container exceed-set-dscp-transmit-table {
      container exceed-action {
        description
          "action when rate is within conform and conform + exceed burst";
        leaf set-dscp-transmit {
          description
            "set dscp and send it";
          type string;
        }
        leaf table {
          description
            "Specify table-map";
          type string;
        }
      }
    }
    container exceed-set-frde-transmit {
      container exceed-action {
        description
          "action when rate is within conform and conform + exceed burst";
        leaf set-frde-transmit {
          description
            "set FR DE and send it";
          type empty;
        }
      }
    }
    container exceed-set-mpls-exp-imposition-transmit {
      container exceed-action {
        description
          "action when rate is within conform and conform + exceed burst";
        leaf set-mpls-exp-imposition-transmit {
          description
            "set exp at tag imposition and send it";
          type string;
        }
      }
    }
    container exceed-set-mpls-exp-topmost-transmit {
      container exceed-action {
        description
          "action when rate is within conform and conform + exceed burst";
        leaf set-mpls-exp-topmost-transmit {
          description
            "set exp on topmost label and send it";
          type string;
        }
      }
    }
    container exceed-set-prec-transmit {
      container exceed-action {
        description
          "action when rate is within conform and conform + exceed burst";
        leaf set-prec-transmit {
          description
            "rewrite packet precedence and send it";
          type string;
        }
        leaf table {
          description
            "Specify table-map";
          type string;
        }
      }
    }
    container exceed-set-qos-transmit {
      container exceed-action {
        description
          "action when rate is within conform and conform + exceed burst";
        leaf set-qos-transmit {
          description
            "set qos-group and send it";
          type string;
        }
      }
    }
    container exceed-transmit {
      container exceed-action {
        description
          "action when rate is within conform and conform + exceed burst";
        uses ncs_template_police-action-transmit-grouping;
      }
    }
    container exceed-drop {
      container exceed-action {
        description
          "action when rate is within conform and conform + exceed burst";
        uses ncs_template_police-action-drop-grouping;
      }
    }
  }

  grouping ncs_template_police-violate-action-grouping {
    container violate-set-clp-transmit {
      container violate-action {
        description
          "action when rate is greater than conform + exceed burst";
        leaf set-clp-transmit {
          description
            "set atm clp and send it";
          type empty;
        }
      }
    }
    container violate-set-cos-transmit {
      container violate-action {
        description
          "action when rate is greater than conform + exceed burst";
        leaf set-cos-transmit {
          description
            "rewrite packet cos and send it";
          type string;
        }
        leaf table {
          description
            "Specify table-map";
          type string;
        }
      }
    }
    container violate-set-discard-class-transmit {
      container violate-action {
        description
          "action when rate is greater than conform + exceed burst";
        leaf set-discard-class-transmit {
          description
            "set discard-class and send it";
          type string;
        }
      }
    }
    container violate-set-dscp-transmit {
      container violate-action {
        description
          "action when rate is greater than conform + exceed burst";
        leaf set-dscp-transmit {
          description
            "set dscp and send it";
          type string;
        }
        leaf table {
          description
            "Specify table-map";
          type string;
        }
      }
    }
    container violate-set-frde-transmit {
      container violate-action {
        description
          "action when rate is greater than conform + exceed burst";
        leaf set-frde-transmit {
          description
            "set FR DE and send it";
          type empty;
        }
      }
    }
    container violate-set-mpls-exp-imposition-transmit {
      container violate-action {
        description
          "action when rate is greater than conform + exceed burst";
        leaf set-mpls-exp-imposition-transmit {
          description
            "set exp at tag imposition and send it";
          type string;
        }
      }
    }
    container violate-set-mpls-exp-topmost-transmit {
      container violate-action {
        description
          "action when rate is greater than conform + exceed burst";
        leaf set-mpls-exp-topmost-transmit {
          description
            "set exp on topmost label and send it";
          type string;
        }
      }
    }
    container violate-set-prec-transmit {
      container violate-action {
        description
          "action when rate is greater than conform + exceed burst";
        leaf set-prec-transmit {
          description
            "rewrite packet precedence and send it";
          type string;
        }
        leaf table {
          description
            "Specify table-map";
          type string;
        }
      }
    }
    container violate-set-qos-transmit {
      container violate-action {
        description
          "action when rate is greater than conform + exceed burst";
        leaf set-qos-transmit {
          description
            "set qos-group and send it";
          type string;
        }
      }
    }
    container violate-transmit {
      container violate-action {
        description
          "action when rate is greater than conform + exceed burst";
        uses ncs_template_police-action-transmit-grouping;
      }
    }
    container violate-drop {
      container violate-action {
        description
          "action when rate is greater than conform + exceed burst";
        uses ncs_template_police-action-drop-grouping;
      }
    }
  }

  grouping ncs_template_police-action-grouping {
    container actions {
      uses ncs_template_police-conform-action-grouping;
      uses ncs_template_police-exceed-action-grouping;
      uses ncs_template_police-violate-action-grouping;
    }
  }

  grouping ncs_template_random-detect-grouping {
    leaf min-threshold {
      type string;
    }
    leaf max-threshold {
      type string;
    }
    leaf denominator {
      type string;
    }
  }

  grouping ncs_template_config-policy-map-grouping {
    list policy-map {
      // NCS patched for predictable order
      ordered-by user;
      description
        "Configure QoS Policy Map";
      key "name";
      leaf name {
        type string;
      }
      leaf type {
        description
          "type of the policy-map";
        type string;
      }
      leaf subscriber {
        type empty;
      }
      leaf protocol {
        // NCS drop when statement
        type string;
      }
      list event {
        // NCS patched for predictable order
        ordered-by user;
        description
          "The event type this control class-map triggers upon";
        key "event-type";
        leaf event-type {
          type string;
        }
        leaf match-type {
          type string;
        }
        list class-number {
          // NCS patched for predictable order
          ordered-by user;
          description
            "class number, 1 for 1st class, 2 for 2nd...";
          key "number";
          leaf number {
            type string;
          }
          leaf class {
            description
              "The class type this control policy-map triggers upon";
            type string;
          }
          leaf execution-type {
            type string;
          }
          list action-number {
            // NCS patched for predictable order
            ordered-by user;
            description
              "action number, 1 for 1st class, 2 for 2nd...";
            key "number";
            leaf number {
              type string;
            }
            container terminate {
              description
                "terminate auth method";
              leaf dot1x {
                description
                  "dot1x method";
                type empty;
              }
              leaf mab {
                description
                  "mab method";
                type empty;
              }
              leaf webauth {
                description
                  "webauth method";
                type empty;
              }
            }
            leaf clear-session {
              description
                "clears an active session";
              type empty;
            }
            container resume {
              description
                "resume operation to be specified";
              leaf reauthentication {
                description
                  "resume reauthentication";
                type empty;
              }
            }
            leaf authentication-restart {
              description
                "restarts the auth sequence after the specified number of sec";
              type string;
            }
            container pause {
              description
                "pause operation to be specified";
              leaf reauthentication {
                description
                  "pause reauthentication";
                type empty;
              }
            }
            leaf authorize {
              description
                "authorize session";
              type empty;
            }
            container activate {
              description
                "activate template or policy";
              leaf service-template {
                description
                  "activate service template";
                type string;
              }
            }
            container authenticate {
              description
                "authenticate a session";
              container using {
                description
                  "authenticate a session";
                leaf method {
                  type string;
                }
                leaf both {
                  description
                    "Enabling Dot1x Authenticator & Supplicant";
                  type empty;
                }
                leaf retries {
                  description
                    "Number of times to retry failed authentications";
                  type string;
                }
                leaf retry-time {
                  description
                    "Time interval between retries";
                  type string;
                }
                leaf priority {
                  description
                    "Method priority";
                  type string;
                }
              }
            }
          }
        }
      }
      list class {
        // NCS patched for predictable order
        ordered-by user;
        description
          "policy criteria";
        key "name";
        leaf name {
          type string;
        }
        leaf type {
          description
            "type of the class-map";
          type string;
        }
        leaf insert-before {
          description
            "Insert the class before a specified class";
          // NCS drop when statement
          type string;
        }
        container appnav-policy {
          // NCS drop when statement
          list distribute {
            // NCS patched for predictable order
            ordered-by user;
            description
              "Distribute action";
            key "service-node-group";
            leaf service-node-group {
              description
                "Distribute to service-node-group";
              type string;
            }
            leaf insert-before {
              description
                "Insert before specific node";
              type string;
            }
          }
          leaf monitor-load {
            description
              "Monitor AO";
            // NCS drop when statement
            type string;
          }
          leaf pass-through {
            description
              "pass-through action";
            type empty;
          }
        }
        container policy {
          // NCS drop when statement
          leaf action {
            type string;
          }
          leaf log {
            description
              "Send logging message for drop or pass";
            // NCS drop when statement
            type empty;
          }
          leaf parameter-map {
            // NCS drop when statement
            type string;
          }
          container dpi {
            // NCS drop when statement
            leaf type {
              type string;
            }
            leaf policy-map {
              type string;
            }
          }
        }
        container pm-policy {
          // NCS drop when statement
          container flow {
            description
              "Flow subcommands";
            leaf monitor {
              description
                "Apply a Flow Monitor";
              type string;
            }
          }
          container monitor {
            description
              "Monitor related parameters";
            container metric {
              description
                "Monitor metric";
              container rtp {
                description
                  "RTP metrics parameters";
                list clock-rate {
                  // NCS patched for predictable order
                  ordered-by user;
                  description
                    "RTP timestamp field's sampling frequency";
                  key "number";
                  leaf number {
                    type string;
                  }
                  leaf frequency {
                    type string;
                  }
                }
              }
            }
          }
          list react {
            // NCS patched for predictable order
            ordered-by user;
            description
              "Configure threshold crossing actions";
            key "id";
            leaf id {
              type string;
            }
            leaf mode {
              type string;
            }
            leaf description {
              description
                "Description for the instance";
              type string;
            }
            container action {
              description
                "Config react action";
              leaf snmp {
                description
                  "SNMP is notified of the event";
                type empty;
              }
              leaf syslog {
                description
                  "The threshold-crossing event is logged to syslog";
                type empty;
              }
            }
            container alarm {
              description
                "Config react alarm";
              leaf severity {
                description
                  "Alarm severity - default level none";
                type string;
              }
              container type {
                description
                  "Alarm raised type - for each flow or a group";
                leaf discrete {
                  description
                    "Alert for each flow within the class";
                  type empty;
                }
                container grouped {
                  description
                    "Alert if more than one flow cross the threshold";
                  leaf count {
                    description
                      "Number of flows in the group cross the threshold";
                    type string;
                  }
                  leaf percent {
                    description
                      "Percent of flows in the group cross the threshold";
                    type string;
                  }
                }
              }
            }
            container threshold {
              description
                "Config react threshold";
              container value {
                description
                  "Range of percentage loss that would trigger the alarm";
                leaf ge {
                  description
                    "greater and equal to";
                  type string;
                }
                leaf gt {
                  description
                    "greater than";
                  type string;
                }
                leaf le {
                  description
                    "less and equal to";
                  type string;
                }
                leaf lt {
                  description
                    "less than";
                  type string;
                }
                container range {
                  description
                    "threshold within the range of";
                  leaf low {
                    type string;
                  }
                  leaf high {
                    type string;
                  }
                }
              }
            }
          }
        }
        container inspect-police {
          // NCS drop when statement
          container police {
            description
              "Police";
            leaf rate {
              description
                "Specify police rate";
              type string;
            }
            leaf burst {
              description
                "Specify 'burst' parameter";
              type string;
            }
          }
        }
        list action-list {
          // NCS patched for predictable order
          ordered-by user;
          key "action-type";
          leaf action-type {
            type string;
          }
          choice action-param {
            case bandwidth-case {
              container bandwidth {
                // NCS drop when statement
                leaf bits {
                  type string;
                }
                leaf percent {
                  description
                    "% of total Bandwidth";
                  type string;
                }
                container remaining {
                  description
                    "% of the remaining bandwidth";
                  leaf rem-option {
                    type string;
                  }
                  leaf percent {
                    description
                      "% of the remaining bandwidth";
                    // NCS drop when statement
                    type string;
                  }
                  leaf ratio {
                    description
                      "ratio for sharing excess bandwidth";
                    // NCS drop when statement
                    type string;
                  }
                  container account {
                    description
                      "Overhead Accounting";
                    // NCS drop when statement
                    leaf user-defined {
                      description
                        "Offset Size";
                      type string;
                    }
                  }
                }
              }
            }
            case compression-case {
              container compression {
                // NCS drop when statement
                container header {
                  description
                    "configure header compression";
                  presence "configure header compression";
                  leaf ip {
                    description
                      "configure ip header compression";
                    type string;
                  }
                }
              }
            }
            case estimate-case {
              container estimate {
                // NCS drop when statement
                container bandwidth {
                  presence "bandwidth required to service this class";
                  description
                    "bandwidth required to service this class";
                  container delay-one-in {
                    description
                      "specify QoS target delay";
                    leaf doi {
                      type string;
                    }
                    leaf milliseconds {
                      type string;
                    }
                  }
                  leaf drop-one-in {
                    description
                      "specify QoS target loss rate";
                    type string;
                  }
                }
              }
            }
            case forward-case {
              container forward {
                // NCS drop when statement
                leaf service-path {
                  description
                    "Service Path Entries";
                  type string;
                }
                leaf service-index {
                  description
                    "Service Index";
                  type string;
                }
              }
            }
            case fair-queue-case {
              container fair-queue {
                // NCS drop when statement
                leaf dynamic-queues {
                  type string;
                }
                leaf queue-limit {
                  description
                    "per flow queue limit";
                  type string;
                }
              }
            }
            case netflow-sampler-case {
              leaf netflow-sampler {
                // NCS drop when statement
                type string;
              }
            }
            case police-case {
              choice police-choice {
                case police-aggregate-case {
                  container police-aggregate {
                    container police {
                      // NCS drop when statement
                      leaf aggregate {
                        description
                          "Choose aggregate policer for current class";
                        type string;
                      }
                    }
                  }
                }
                case police-policy-map-case {
                  container police-policy-map {
                    container police {
                      // NCS drop when statement
                      leaf cir {
                        description
                          "Committed information rate";
                        type string;
                      }
                      leaf bc {
                        description
                          "Conform burst";
                        type string;
                      }
                      leaf be {
                        description
                          "Excess burst";
                        // NCS drop when statement
                        type string;
                      }
                      leaf pir {
                        description
                          "Peak Information Rate";
                        type string;
                      }
                      container pir-be {
                        // NCS drop when statement
                        leaf be {
                          description
                            "Excess burst";
                          type string;
                        }
                      }
                      uses ncs_template_police-action-grouping;
                    }
                  }
                }
                case police-cir-percent-case {
                  container police-cir-percent {
                    container police {
                      // NCS drop when statement
                      container cir {
                        description
                          "Committed information rate";
                        container percent {
                          description
                            "% of interface bandwidth for Committed information rate";
                          leaf percentage {
                            type string;
                          }
                          leaf bc {
                            description
                              "Conform burst";
                            type string;
                          }
                          container bc-ms {
                            // NCS drop when statement
                            leaf ms {
                              description
                                "Milli seconds";
                              type empty;
                            }
                          }
                          leaf be {
                            // NCS drop when statement
                            type string;
                          }
                          container be-ms {
                            // NCS drop when statement
                            leaf ms {
                              description
                                "Milli seconds";
                              type empty;
                            }
                          }
                          container pir {
                            description
                              "Peak Information Rate";
                            leaf percent {
                              description
                                "% of interface bandwidth for Peak Information Rate";
                              type string;
                            }
                          }
                          container pir-be {
                            // NCS drop when statement
                            leaf be {
                              description
                                "Excess burst";
                              type string;
                            }
                          }
                          container pir-be-ms {
                            // NCS drop when statement
                            leaf ms {
                              description
                                "Milli seconds";
                              type empty;
                            }
                          }
                          uses ncs_template_police-action-grouping;
                        }
                      }
                    }
                  }
                }
                case police-rate-unit-case {
                  container police-rate-unit {
                    container police {
                      // NCS drop when statement
                      container rate {
                        description
                          "Specify police rate";
                        leaf units {
                          type string;
                        }
                        leaf xps {
                          type string;
                        }
                        container burst {
                          description
                            "Specify 'burst' parameter";
                          leaf burst-value {
                            type string;
                          }
                          leaf burst-type {
                            type string;
                          }
                        }
                        container peak-rate {
                          description
                            "Specify peak rate";
                          leaf peak-rate-value {
                            type string;
                          }
                          leaf xps {
                            type string;
                          }
                        }
                        container peak-burst {
                          description
                            "Specify 'peak-burst' parameter for peak-rate";
                          leaf burst-value {
                            type string;
                          }
                          leaf burst-type {
                            type string;
                          }
                        }
                        uses ncs_template_police-action-grouping;
                      }
                    }
                  }
                }
                case police-rate-percent-case {
                  container police-rate-percent {
                    container police {
                      // NCS drop when statement
                      container rate {
                        description
                          "Specify police rate";
                        container percent {
                          description
                            "% of interface bandwidth for rate";
                          leaf percentage {
                            type string;
                          }
                          leaf burst {
                            description
                              "Specify 'burst' parameter";
                            type string;
                          }
                          leaf ms {
                            description
                              "Treat 'burst' value in milliseconds";
                            // NCS drop when statement
                            type empty;
                          }
                          container peak-rate {
                            description
                              "Specify peak rate";
                            leaf percent {
                              description
                                "% of interface bandwidth for peak-rate";
                              type string;
                            }
                          }
                          leaf peak-burst {
                            description
                              "Specify 'peak-burst' parameter for 'peak-rate'";
                            type string;
                          }
                          container peak-burst-ms {
                            // NCS drop when statement
                            leaf ms {
                              description
                                "Milli seconds";
                              type empty;
                            }
                          }
                          uses ncs_template_police-action-grouping;
                        }
                      }
                    }
                  }
                }
                case police-rate-pdp-case {
                  container police-rate-pdp {
                    container police {
                      // NCS drop when statement
                      container rate {
                        description
                          "Specify police rate";
                        container pdp {
                          description
                            "% of interface bandwidth for rate";
                          leaf burst {
                            description
                              "Conform burst";
                            type string;
                          }
                          leaf peak-rate {
                            description
                              "Specify peak rate";
                            type string;
                          }
                          leaf peak-burst {
                            description
                              "Specify 'peak-burst' parameter for 'peak-rate'";
                            // NCS drop when statement
                            type string;
                          }
                          uses ncs_template_police-action-grouping;
                        }
                      }
                    }
                  }
                }
                case police-target-bitrate-case {
                  container police-target-bitrate {
                    container police {
                      // NCS drop when statement
                      leaf bit-rate {
                        description
                          "Target bit rate (bits per second) (postfix k, m, g optional),decimal point allowed";
                        type string;
                      }
                      leaf confirm_burst-byte {
                        description
                          "Burst Byte";
                        type string;
                      }
                      leaf excess_burst-byte {
                        description
                          "Burst Byte";
                        type string;
                      }
                      leaf conform-action {
                        description
                          "action when rate is less than conform burst";
                        type empty;
                      }
                      leaf transmit {
                        description
                          "transmit packet";
                        type empty;
                      }
                      leaf exceed-action {
                        description
                          "action when rate is within conform and conform + exceed burst";
                        type empty;
                      }
                      leaf drop {
                        description
                          "drop packet";
                        type empty;
                      }
                      leaf set-dscp-transmit {
                        description
                          "set dscp and send it";
                        type empty;
                      }
                      leaf dscp {
                        description
                          "Set packet dscp from dscp";
                        type empty;
                      }
                      leaf table {
                        description
                          "Specify table-map";
                        type string;
                      }
                      container actions {
                        uses ncs_template_police-conform-action-grouping;
                        uses ncs_template_police-exceed-action-grouping;
                        uses ncs_template_police-violate-action-grouping;
                      }
                    }
                  }
                }
                case police-flow-case {
                  container police-flow {
                    container police {
                      // NCS drop when statement
                      container flow {
                        description
                          "police each flow";
                        leaf mask {
                          description
                            "flow mask to be used for policing";
                          type string;
                        }
                        leaf bps {
                          type string;
                        }
                        leaf burst-normal {
                          type string;
                          // NCS drop when statement
                        }
                        uses ncs_template_police-action-grouping;
                      }
                    }
                  }
                }
                case police-catalyst-case {
                  container police-catalyst {
                    container police {
                      // NCS drop when statement
                      leaf bps-value {
                        type string;
                      }
                      leaf bps {
                        type empty;
                      }
                      leaf byte-value {
                        type string;
                      }
                      leaf byte {
                        type empty;
                      }
                      container actions {
                        uses ncs_template_police-conform-action-grouping;
                        uses ncs_template_police-exceed-action-grouping;
                        uses ncs_template_police-violate-action-grouping;
                      }
                    }
                  }
                }
                case police-switch-case {
                  container police-switch {
                    container police {
                      // NCS drop when statement
                      leaf cir {
                        type string;
                      }
                      leaf bc {
                        type string;
                      }
                      leaf exceed-action {
                        description
                          "action when rate is exceeded";
                        type string;
                      }
                    }
                  }
                }
              }
            }
            case priority-case {
              container priority {
                // NCS drop when statement
                leaf level {
                  description
                    "Multi-Level Priority Queue";
                  type string;
                }
                choice priority-type {
                  leaf kilo-bits {
                    type string;
                  }
                  leaf percent {
                    description
                      "% of total bandwidth";
                    type string;
                  }
                }
                leaf burst {
                  type string;
                }
              }
            }
            case queue-buffers-case {
              container queue-buffers {
                // NCS drop when statement
                leaf ratio {
                  description
                    "Relative buffer size for queue";
                  type string;
                }
              }
            }
            case queue-limit-case {
              container queue-limit {
                // NCS drop when statement
                leaf queue-limit-value {
                  type string;
                }
                leaf queue-limit-type {
                  type string;
                }
              }
              container queue-limit-dscp {
                // NCS drop when statement
                list dscp {
                  // NCS patched for predictable order
                  ordered-by user;
                  description
                    "parameters for each dscp value";
                  key "dscp-val";
                  leaf dscp-val {
                    type string;
                  }
                  leaf values {
                    description
                      "dscp values";
                    type empty;
                  }
                  leaf dscp-val1 {
                    type string;
                  }
                  leaf percent {
                    description
                      "% of threshold";
                    type string;
                  }
                }
              }
            }
            case random-detect {
              container random-detect {
                // NCS drop when statement
                container aggregate {
                  description
                    "aggregate subclasses";
                  presence "true";
                  leaf minimum-thresh {
                    description
                      "minimum threshold for red aggregate";
                    type string;
                  }
                  leaf maximum-thresh {
                    description
                      "maximum threshold for red aggregate";
                    type string;
                  }
                  leaf mark-probability {
                    description
                      "mark-probability for red aggregate";
                    type empty;
                  }
                  leaf denominator {
                    type string;
                  }
                }
                container discard-class {
                  description
                    "parameters for each discard-class value";
                  leaf dclass {
                    type string;
                  }
                  uses ncs_template_random-detect-grouping;
                }
                leaf discard-class-based {
                  description
                    "Enable discard-class-based WRED as drop policy";
                  type empty;
                }
                leaf dscp-based {
                  description
                    "Enable dscp-based WRED as drop policy";
                  type empty;
                }
                list dscp {
                  // NCS patched for predictable order
                  ordered-by user;
                  description
                    "parameters for each dscp value";
                  key "dscp-val";
                  leaf dscp-val {
                    type string;
                  }
                  uses ncs_template_random-detect-grouping;
                }
                leaf ecn {
                  description
                    "explicit congestion notification";
                  type empty;
                }
                leaf exponential-weighting-constant {
                  description
                    "weight for mean queue depth calculation";
                  type string;
                }
                leaf prec-based {
                  description
                    "Enable precedence-based WRED as drop policy";
                  type empty;
                }
                container precedence {
                  description
                    "parameters for each precedence value";
                  leaf prec {
                    type string;
                  }
                  uses ncs_template_random-detect-grouping;
                }
              }
            }
            case service-policy-case {
              leaf service-policy {
                type string;
              }
            }
            case set-case {
              container set {
                // NCS drop when statement
                leaf atm-clp {
                  description
                    "Set ATM CLP bit to 1";
                  type empty;
                }
                container cos {
                  description
                    "Set IEEE 802.1Q/ISL class of service/user priority";
                  choice cos-type {
                    case a {
                      leaf val {
                        type string;
                      }
                    }
                    case b {
                      leaf pack {
                        type string;
                      }
                      leaf user-priority {
                        description
                          "Set value from WLAN user-priority";
                        // NCS drop when statement
                        type empty;
                      }
                      leaf table {
                        description
                          "Set codepoint value based on tablemap.";
                        type string;
                      }
                    }
                  }
                }
                leaf discard-class {
                  description
                    "Discard behavior identifier";
                  type string;
                }
                container dscp {
                  description
                    "Set DSCP in IP(v4) and IPv6 packets";
                  container dscp {
                    description
                      "Set packet dscp from dscp";
                    presence "true";
                    leaf table {
                      description
                        "Set packet dscp from dscp based on table map.";
                      type string;
                    }
                  }
                  leaf tunnel {
                    description
                      "set tunnel packet dscp";
                    type empty;
                  }
                  leaf dscp-val {
                    type string;
                  }
                }
                leaf fr-de {
                  description
                    "Set FR DE bit to 1";
                  type empty;
                }
                container ip {
                  description
                    "Set IP specific values";
                  choice ip-choice {
                    container dscp {
                      description
                        "Set IP DSCP (DiffServ CodePointint)";
                      leaf tunnel {
                        description
                          "set tunnel packet dscp";
                        type empty;
                      }
                      leaf dscp-val {
                        type string;
                      }
                    }
                    container precedence {
                      description
                        "Set IP precedence";
                      presence "Set IP precedence";
                      leaf precedence-val {
                        type string;
                      }
                    }
                  }
                }
                container mpls {
                  description
                    "Set MPLS specific values";
                  container experimental {
                    description
                      "Set Experimental value";
                    container imposition {
                      description
                        "Set Experimental value at tag imposition";
                      leaf exp-value {
                        type string;
                      }
                    }
                    container topmost {
                      description
                        "Set Experimental value  on topmost label";
                      leaf exp-value {
                        type string;
                      }
                    }
                  }
                }
                container qos-group {
                  description
                    "Set QoS Group";
                  leaf qos-group-value {
                    type string;
                  }
                }
              }
            }
            case shape-case {
              container shape {
                // NCS drop when statement
                leaf adaptive {
                  description
                    "Enable Traffic Shaping adaptation to BECN";
                  type string;
                }
                container average {
                  description
                    "configure token bucket: CIR (bps) [Bc (bits) [Be (bits)]], send out Bc only per interval";
                  choice average-choice {
                    case a {
                      leaf bit-rate {
                        type string;
                      }
                      leaf bits-per-interval-sustained {
                        type string;
                      }
                      leaf bits-per-interval-excess {
                        // NCS drop when statement
                        type string;
                      }
                      container account {
                        description
                          "Overhead Accounting";
                        leaf user-defined {
                          description
                            "Offset Size";
                          type string;
                        }
                      }
                    }
                    case b {
                      leaf percent {
                        description
                          "% of interface bandwidth for Committed information rate";
                        type string;
                      }
                      leaf burst-size-sustained {
                        type string;
                      }
                      leaf ms {
                        description
                          "milliseconds";
                        type empty;
                      }
                      container bse {
                        leaf burst-size-excess {
                          type string;
                        }
                        leaf ms {
                          description
                            "milliseconds";
                          type empty;
                        }
                      }
                    }
                  }
                }
                leaf fecn-adapt {
                  description
                    "Enable Traffic Shaping reflection of FECN as BECN";
                  type empty;
                }
                container fr-voice-adapt {
                  description
                    "Enable rate adjustment depending on voice presence";
                  presence "Enable rate adjustment depending on voice presence";
                  leaf deactivation {
                    type string;
                  }
                }
                leaf max-buffers {
                  description
                    "Set Maximum Buffer Limit";
                  type string;
                }
              }
            }
            case trust-case {
              leaf trust {
                // NCS drop when statement
                type string;
              }
            }
          }
        }
      }
      leaf description {
        description
          "Policy-Map description";
        type string;
      }
      leaf sequence-interval {
        description
          "Enable sequence number capability";
        // NCS drop when statement
        type string;
      }
    }
  }

  grouping ncs_template_class-map-match-result-type-grouping {
    leaf aaa-timeout {
      description
        "aaa timeout type";
      type empty;
    }
    leaf agent-not-found {
      description
        "agent not found type";
      type empty;
    }
    leaf authoritative {
      description
        "failure type";
      type empty;
    }
    leaf method-timeout {
      description
        "method_timeout type";
      type empty;
    }
    leaf none {
      description
        "no type";
      type empty;
    }
    leaf success {
      description
        "success type";
      type empty;
    }
  }

  grouping ncs_template_class-map-control-filter-grouping {
    list activated-service-template {
      // NCS patched for predictable order
      ordered-by user;
      description
        "match name of service template activated on session";
      key "service-name";
      leaf service-name {
        description
          "Enter service name";
        type string;
      }
    }
    container authorization-status {
      description
        "match the authorization status of the session";
      leaf authorized {
        description
          "authorized";
        type empty;
      }
      leaf unauthorized {
        description
          "unauthorized";
        type empty;
      }
    }
    container authorizing-method-priority {
      description
        "match the priority against the authorizing method's priority";
      leaf eq {
        description
          "equal to";
        type string;
      }
      leaf gt {
        description
          "greater than";
        type string;
      }
      leaf lt {
        description
          "less than";
        type string;
      }
    }
    container method {
      description
        "match the type of authentication method from an event";
      leaf dot1x {
        description
          "dot1x";
        type empty;
      }
      leaf mab {
        description
          "mab";
        type empty;
      }
      leaf webauth {
        description
          "webauth";
        type empty;
      }
    }
    container result-type {
      description
        "match the result type, optionally for a specific method";
      container method {
        description
          "match the result of a particular method";
        container dot1x {
          description
            "dot1x result";
          uses ncs_template_class-map-match-result-type-grouping;
        }
        container mab {
          description
            "mab result";
          uses ncs_template_class-map-match-result-type-grouping;
        }
        container webauth {
          description
            "webauth result";
          uses ncs_template_class-map-match-result-type-grouping;
        }
      }
      uses ncs_template_class-map-match-result-type-grouping;
    }
  }

  grouping ncs_template_class-map-match-grouping {
    container current-method-priority {
      description
        "match the priority against the current method's priority";
      leaf eq {
        description
          "equal to";
        type string;
      }
      leaf gt {
        description
          "greater than";
        type string;
      }
      leaf lt {
        description
          "less than";
        type string;
      }
    }
    container application {
      description
        "Application to match";
      container application-group {
        description
          "Application Group to match";
        leaf telepresence-group {
          description
            "Telepresence Group";
          type empty;
        }
        leaf vmware-group {
          description
            "VMWARE Group";
          type empty;
        }
        leaf webex-group {
          description
            "WebEx Group";
          type empty;
        }
      }
      container attribute {
        description
          "Application attribute to match";
        leaf media-type {
          description
            "Media type attribute to match";
          type string;
        }
      }
    }
    container access-group {
      description
        "Access group";
      leaf index {
        type string;
      }
      leaf-list name {
        // NCS patched for predictable order
        ordered-by user;
        description
          "Named Access List";
        type string;
      }
    }
    leaf any {
      description
        "Any packets";
      type empty;
    }
    leaf-list class-map {
      // NCS patched for predictable order
      ordered-by user;
      description
        "Class map";
      type string;
    }
    leaf-list cos {
      // NCS patched for predictable order
      ordered-by user;
      description
        "IEEE 802.1Q/ISL class of service/user priority values";
      type string;
    }
    container destination-address {
      description
        "Destination address";
      leaf-list mac {
        // NCS patched for predictable order
        ordered-by user;
        description
          "MAC address";
        type string;
      }
    }
    leaf-list discard-class {
      // NCS patched for predictable order
      ordered-by user;
      description
        "Discard behavior identifier";
      type string;
    }
    leaf-list dscp {
      // NCS patched for predictable order
      ordered-by user;
      description
        "Match DSCP in IP(v4) and IPv6 packets";
      type string;
    }
    leaf fr-de {
      description
        "Match on Frame-relay DE bit";
      type empty;
    }
    leaf-list fr-dlci {
      // NCS patched for predictable order
      ordered-by user;
      description
        "Match on fr-dlci";
      type string;
    }
    container group-object {
      description
        "Match object-group";
      container security {
        description
          "Match object-group security";
        leaf-list source {
          // NCS patched for predictable order
          ordered-by user;
          description
            "Match source object-group security";
          type string;
        }
        leaf-list destination {
          // NCS patched for predictable order
          ordered-by user;
          description
            "Match destination object-group security";
          type string;
        }
      }
    }
    leaf-list input-interface {
      // NCS patched for predictable order
      ordered-by user;
      description
        "Select an input interface to match";
      type string;
    }
    container ip {
      description
        "IP specific values";
      leaf-list dscp {
        // NCS patched for predictable order
        ordered-by user;
        description
          "Match IP DSCP (DiffServ CodePoints)";
        type string;
      }
      leaf-list precedence {
        // NCS patched for predictable order
        ordered-by user;
        description
          "Match IP precedence";
        type string;
      }
      list rtp {
        // NCS patched for predictable order
        ordered-by user;
        description
          "Match RTP port nos";
        key "port1 port2";
        leaf port1 {
          type string;
        }
        leaf port2 {
          type string;
        }
      }
    }
    leaf non-client-nrt {
      type empty;
    }
    container mpls {
      description
        "Multi Protocol Label Switching specific values";
      container experimental {
        description
          "Match MPLS experimental";
        leaf-list topmost {
          // NCS patched for predictable order
          ordered-by user;
          description
            "Match MPLS experimental value on topmost label";
          type string;
        }
      }
    }
    container packet {
      description
        "Layer 3 Packet length";
      container length {
        description
          "Layer 3 Packet length";
        leaf max {
          description
            "Maximum length of packet";
          type string;
        }
        leaf min {
          description
            "Minimum length of packet";
          type string;
        }
      }
    }
    leaf-list precedence {
      // NCS patched for predictable order
      ordered-by user;
      description
        "Match Precedence in IP(v4) and IPv6 packets";
      type string;
    }
    container protocol {
      description
        "Protocol";
      leaf protocols {
        type string;
      }
      container citrix {
        description
          "Citrix Systems ICA protocol";
        presence "enable citrix system protocol matching";
        leaf ica-tag {
          description
            "Citrix ICA tag 0-high 1-medium 2-low 3-background";
          type string;
        }
      }
      leaf clns {
        description
          "ISO CLNS";
        type empty;
      }
      leaf clns_es {
        description
          "ISO CLNS End System";
        type empty;
      }
      leaf clns_is {
        description
          "ISO CLNS Intermediate System";
        type empty;
      }
      leaf cmns {
        description
          "ISO CMNS";
        type empty;
      }
      leaf compressedtcp {
        description
          "Compressed TCP (VJ";
        type empty;
      }
      leaf cuseeme {
        description
          "CU-SeeMe desktop video conference";
        type empty;
      }
      leaf decnet {
        description
          "DECnet";
        type empty;
      }
      leaf decnet_node {
        description
          "DECnet Node";
        type empty;
      }
      leaf decnet_router-l1 {
        description
          "DECnet Router L1";
        type empty;
      }
      leaf decnet_router-l2 {
        description
          "DECnet Router L2";
        type empty;
      }
      leaf dhcp {
        description
          "Dynamic Host Configuration";
        type empty;
      }
      leaf dlsw {
        type empty;
      }
      leaf dns {
        type empty;
      }
      leaf edonkey {
        type empty;
      }
      leaf egp {
        type empty;
      }
      leaf eigrp {
        type empty;
      }
      leaf exchange {
        type empty;
      }
      container fasttrack {
        description
          "FastTrack Traffic - KaZaA, Morpheus, Grokster";
        presence "enable fasttrack matching";
        leaf file-transfer {
          description
            "File transfer stream";
          type string;
        }
      }
      leaf finger {
        type empty;
      }
      leaf ftp {
        type empty;
      }
      container gnutella {
        description
          "Gnutella Version2 Traffic - BearShare, Shareeza, Morpheus";
        presence "enable gnutella matching";
        leaf file-transfer {
          description
            "File transfer stream";
          type string;
        }
      }
      leaf gopher {
        type empty;
      }
      leaf gre {
        type empty;
      }
      leaf h323 {
        type empty;
      }
      container http {
        description
          "World Wide Web traffic";
        presence "enable http traffic matching";
        leaf c-header-field {
          description
            "Client general Header Field";
          type string;
        }
        leaf host {
          description
            "Server Host Name";
          type string;
        }
        leaf mime {
          description
            "Match MIME Type";
          type string;
        }
        leaf s-header-field {
          description
            "Server general Header Field";
          type string;
        }
        leaf url {
          description
            "Match URL String";
          type string;
        }
      }
      leaf icmp {
        description
          "Internet Control Message";
        type empty;
      }
      leaf imap {
        description
          "Internet Message Access Protocol";
        type empty;
      }
      leaf ip {
        description
          "IP";
        type empty;
      }
      leaf ipinip {
        description
          "IP in IP (encapsulation";
        type empty;
      }
      leaf ipsec {
        description
          "IP Security Protocol (ESP/AH";
        type empty;
      }
      leaf ipv6 {
        description
          "IPV6";
        type empty;
      }
      leaf ipx {
        description
          "Novell IPX";
        type empty;
      }
      leaf irc {
        type empty;
        description
          "Internet Relay Chat";
      }
      container kazaa2 {
        description
          "Kazaa Version 2";
        presence "enable kazaa version 2 matching";
        leaf file-transfer {
          description
            "File transfer stream";
          type string;
        }
      }
      leaf kerberos {
        description
          "Kerberos";
        type empty;
      }
      leaf l2tp {
        description
          "L2F/L2TP tunnel";
        type empty;
      }
      leaf ldap {
        description
          "Lightweight Directory Access Protocol";
        type empty;
      }
      leaf llc2 {
        description
          "llc2";
        type empty;
      }
      leaf mgcp {
        description
          "Media Gateway Control Protocol";
        type empty;
      }
      container napster {
        description
          "Napster Traffic";
        presence "enable napster matching";
        leaf non-std {
          description
            "Non-standard port advertizements";
          type empty;
        }
      }
      leaf netbios {
        description
          "NetBIOS";
        type empty;
      }
      leaf netshow {
        description
          "Microsoft Netshow";
        type empty;
      }
      leaf nfs {
        description
          "Network File System";
        type empty;
      }
      leaf nntp {
        description
          "Network News Transfer Protocol";
        type empty;
      }
      leaf notes {
        description
          "Lotus Notes(R";
        type empty;
      }
      leaf novadigm {
        description
          "Novadigm EDM";
        type empty;
      }
      leaf ntp {
        description
          "Network Time Protocol";
        type empty;
      }
      leaf ospf {
        description
          "Open Shortest Path First";
        type empty;
      }
      leaf pad {
        description
          "PAD links";
        type empty;
      }
      leaf pcanywhere {
        description
          "Symantec pcANYWHERE";
        type empty;
      }
      leaf pop3 {
        description
          "Post Office Protocol";
        type empty;
      }
      leaf pppoe {
        description
          "PPP over Ethernet";
        type empty;
      }
      leaf pptp {
        description
          "Point-to-Point Tunneling Protocol";
        type empty;
      }
      leaf printer {
        description
          "print spooler/lpd";
        type empty;
      }
      leaf qllc {
        description
          "qllc protocol";
        type empty;
      }
      leaf rcmd {
        description
          "BSD r-commands (rsh, rlogin, rexec";
        type empty;
      }
      leaf rip {
        description
          "Routing Information Protocol";
        type empty;
      }
      leaf rsrb {
        description
          "Remote Source-Route Bridging";
        type empty;
      }
      leaf rsvp {
        description
          "Resource Reservation Protocol";
        type empty;
      }
      leaf rtcp {
        description
          "Real Time Control Protocol";
        type empty;
      }
      container rtp {
        description
          "Real Time Protocol";
        presence "enable rtp matching";
        leaf audio {
          description
            "Match voice packets";
          type empty;
        }
        leaf payload-type {
          description
            "Match an explicit PT";
          type string;
        }
        leaf video {
          description
            "Match video packets";
          type empty;
        }
      }
      leaf rtsp {
        description
          "Real Time Streaming Protocol";
        type empty;
      }
      leaf secure-ftp {
        description
          "FTP over TLS/SSL";
        type empty;
      }
      leaf secure-http {
        description
          "Secured HTTP";
        type empty;
      }
      leaf secure-imap {
        description
          "Internet Message Access Protocol over TLS/SSL";
        type empty;
      }
      leaf secure-irc {
        description
          "Internet Relay Chat over TLS/SSL";
        type empty;
      }
      leaf secure-ldap {
        description
          "Lightweight Directory Access Protocol over TLS/SSL";
        type empty;
      }
      leaf secure-nntp {
        description
          "Network News Transfer Protocol over TLS/SSL";
        type empty;
      }
      leaf secure-pop3 {
        description
          "Post Office Protocol over TLS/SSL";
        type empty;
      }
      leaf secure-telnet {
        description
          "Telnet over TLS/SSL";
        type empty;
      }
      leaf sip {
        description
          "Session Initiation Protocol";
        type empty;
      }
      leaf skinny {
        description
          "Skinny Protocol";
        type empty;
      }
      container smtp {
        description
          "Simple Mail Transfer Protocol";
        presence "true";
        leaf extended {
          type empty;
        }
      }
      leaf snapshot {
        description
          "Snapshot routing support";
        type empty;
      }
      leaf snmp {
        description
          "Simple Network Management Protocol";
        type empty;
      }
      leaf socks {
        description
          "SOCKS";
        type empty;
      }
      leaf sqlnet {
        description
          "SQL*NET for Oracle";
        type empty;
      }
      leaf sqlserver {
        description
          "MS SQL Server";
        type empty;
      }
      leaf ssh {
        description
          "Secured Shell";
        type empty;
      }
      leaf streamwork {
        description
          "Xing Technology StreamWorks player";
        type empty;
      }
      leaf stun {
        description
          "Serial Tunnel";
        type empty;
      }
      leaf sunrpc {
        description
          "Sun RPC";
        type empty;
      }
      leaf syslog {
        description
          "System Logging Utility";
        type empty;
      }
      leaf telnet {
        description
          "Telnet";
        type empty;
      }
      leaf tftp {
        description
          "Trivial File Transfer Protocol";
        type empty;
      }
      leaf vdolive {
        description
          "VDOLive streaming video";
        type empty;
      }
      leaf vofr {
        description
          "voice over Frame Relay packets";
        type empty;
      }
      leaf winmx {
        description
          "WinMx file-sharing application";
        type empty;
      }
      leaf xwindows {
        description
          "X-Windows remote access";
        type empty;
      }
      container attribute {
        description
          "Attribute based protocol match";
        container business-relevance {
          description
            "Application business-relevance";
          leaf business-irrelevant {
            description
              "Undesirable business traffic";
            type empty;
          }
          leaf business-relevant {
            description
              "Business critical applications";
            type empty;
          }
          leaf default {
            description
              "Related business applications";
            type empty;
          }
        }
        container traffic-class {
          description
            "SRND class";
          leaf broadcast-video {
            description
              "Broadcast TV, live events, video surveillance";
            type empty;
          }
          leaf bulk-data {
            description
              "Non-interactive data applications";
            type empty;
          }
          leaf multimedia-conferencing {
            description
              "Desktop software multimedia collaboration applications";
            type empty;
          }
          leaf multimedia-streaming {
            description
              "Video-on-Demand (VoD) streaming video";
            type empty;
          }
          leaf network-control {
            description
              "Network control plane traffic";
            type empty;
          }
          leaf ops-admin-mgmt {
            description
              "Network operations, administration, and management traffic";
            type empty;
          }
          leaf real-time-interactive {
            description
              "High-definition interactive video applications";
            type empty;
          }
          leaf signaling {
            description
              "Signaling traffic that supports IP voice and video telephony";
            type empty;
          }
          leaf transactional-data {
            description
              "Interactive data applications";
            type empty;
          }
          leaf voip-telephony {
            description
              "VoIP telephony (bearer-only) traffic";
            type empty;
          }
        }
      }
    }
    leaf-list qos-group {
      // NCS patched for predictable order
      ordered-by user;
      description
        "Qos-group";
      type string;
    }
    container security-group {
      description
        "Security group";
      container destination {
        description
          "Destination security group";
        leaf tag {
          description
            "Security group tag";
          type string;
        }
      }
      container source {
        description
          "Source security group";
        leaf tag {
          description
            "Security group tag";
          type string;
        }
      }
    }
    container source-address {
      description
        "Source address";
      leaf-list mac {
        // NCS patched for predictable order
        ordered-by user;
        description
          "MAC address";
        type string;
      }
    }
    container vlan {
      description
        "VLANs to match";
      leaf-list inner {
        // NCS patched for predictable order
        ordered-by user;
        description
          "Inner tag to match";
        type string;
      }
      leaf-list value {
        // NCS patched for predictable order
        ordered-by user;
        type string;
      }
    }
  }

  grouping ncs_template_class-map-appnav-match-grouping {
    leaf peer {
      description
        "APPNAV Peer Filter";
      // NCS drop when statement
      type string;
    }
  }

  grouping ncs_template_class-map-appnav-not-match-grouping {
    leaf peer {
      description
        "APPNAV Peer Filter";
      // NCS drop when statement
      type string;
    }
  }

  grouping ncs_template_config-class-map-grouping {
    list class-map {
      // NCS patched for predictable order
      ordered-by user;
      description
        "configure qos class map";
      key "name";
      leaf name {
        type string;
      }
      leaf type {
        description
          "type of the class-map";
        type string;
      }
      leaf subscriber {
        type empty;
      }
      leaf protocol {
        // NCS drop when statement
        type string;
      }
      leaf prematch {
        type string;
        // NCS drop mandatory statement
      }
      leaf description {
        description
          "Class-Map description";
        type string;
      }
      container match {
        description
          "classification criteria";
        uses ncs_template_class-map-match-grouping;
        uses ncs_template_class-map-appnav-match-grouping;
        uses ncs_template_class-map-control-filter-grouping;
        container not {
          description
            "Negate this match result";
          uses ncs_template_class-map-match-grouping;
          uses ncs_template_class-map-appnav-not-match-grouping;
        }
      }
      container no-match {
        description
          "no-match filter";
        uses ncs_template_class-map-control-filter-grouping;
      }
    }
  }

  grouping ncs_template_config-parameter-map-grouping {
    container timeout {
      description
        "timeout for the webauth session";
      // NCS drop when statement
      container init-state {
        description
          "init-state timeout";
        presence "true";
        leaf sec {
          description
            "WEBAUTH Timeout in Seconds";
          type string;
        }
      }
      container fin-wait {
        description
          "fin-wait timeout";
        leaf msec {
          description
            "WEBAUTH Timeout in milliseconds";
          type string;
        }
      }
    }
    container watch-list {
      description
        "Watch List of webauth clients";
      // NCS drop when statement
      leaf enabled {
        description
          "Enable Watchlist";
        type empty;
      }
      leaf dynamic-expiry-timeout {
        description
          "dynamic_expiry_timeout";
        type string;
      }
      container add-item {
        description
          "Add item to Watch-list";
        leaf ipv4 {
          description
            "IPv4 Watch List Entry";
          type string;
        }
        leaf ipv6 {
          description
            "IPv6 Watch List Entry";
          type string;
        }
      }
    }
    container aggressive-aging {
      description
        "Aggressive Aging parameters";
      // NCS drop when statement
      container high {
        description
          "Specify the high watermark for aggressive-aging";
        choice absolute-percent {
          case absolute-case {
            container absolute {
              leaf value {
                type string;
              }
              leaf low {
                description
                  "Specify the low watermark for aggressive-aging";
                type string;
              }
            }
          }
          case percent-case {
            container percent {
              description
                "high watermark in percentage of max-incomplete value";
              leaf value {
                type string;
              }
              leaf low_percent {
                description
                  "Specify the low watermark for aggressive-aging in percents";
                type string;
              }
            }
          }
        }
      }
    }
    leaf alert {
      description
        "Turn on/off alert";
      type string;
    }
    leaf application-inspect {
      description
        "Turn on application inspection";
      type string;
    }
    leaf audit-trail {
      description
        "Turn on/off audit trail";
      // NCS drop when statement
      type string;
    }
    leaf dns-timeout {
      description
        "Specify timeout for DNS";
      // NCS drop when statement
      type string;
    }
    container global {
      description
        "cws_tunnel global parameter-map";
      leaf fail-open {
        description
          "Allow traffic to go in clear if CWS Towers are unreachable";
        // NCS drop when statement
        type empty;
      }
      container license {
        description
          "License Key";
        // NCS drop when statement
        container Unencypted {
          description
            "Unencrypted License";
          leaf Hex-string {
            description
              "32 char non encrypted hex key";
            type string;
          }
        }
        container Encrypted {
          description
            "Encrypted License";
          leaf Hex-string {
            description
              "66 char encrypted hex key";
            type string;
          }
        }
      }
      leaf logging {
        description
          "CWS syslogs";
        type empty;
      }
      container primary {
        description
          "Primary tower";
        // NCS drop when statement
        presence "true";
        container tower {
          description
            "Tower configuration for CWS";
          leaf ipv4 {
            description
              "IPv4 address of the tower";
            type string;
          }
          leaf name {
            description
              "Fully Qualified Domain Name of tower";
            type string;
          }
        }
      }
      leaf redirect-list {
        description
          "Set access-list for reverse route from CWS Tower
           Standard IP access-list number <1-199>
           Standard IP access-list number (expanded range) <1300-2699>";
        // NCS drop when statement
        type string;
      }
      container secondary {
        description
          "Secondary tower";
        // NCS drop when statement
        presence "true";
        container tower {
          description
            "Tower configuration for CWS";
          leaf ipv4 {
            description
              "IPv4 address of the tower";
            type string;
          }
          leaf name {
            description
              "Fully Qualified Domain Name of tower";
            type string;
          }
        }
      }
      container whitelist {
        description
          "Disable redirection to CWS
           Access list (standard) <1-199>
           Access list (extended) <1300-2699>
           Access list name";
        presence "true";
        container acl {
          description
            "Access list";
          leaf acl-number {
            type string;
          }
          leaf name {
            description
              "Access list name";
            type string;
          }
        }
        container domain-name {
          description
            "Domain name based Whitelist";
          leaf regex {
            description
              "Domain name regex parameter map";
            type string;
          }
        }
        container download {
          description
            "whitelist download command";
          presence "true";
          leaf interval {
            description
              "Download interval in minutes";
            type string;
          }
        }
      }
    }
    container icmp {
      description
        "Config timeout values for icmp";
      // NCS drop when statement
      leaf idle-time {
        description
          "Specify timeout for icmp";
        type string;
      }
    }
    container lisp {
      description
        "Turn on LISP options";
      leaf inner-packet-inspection {
        description
          "inner-packet-inspection";
        type empty;
      }
    }
    container log {
      description
        "Configure inspect logging parameters";
      leaf dropped-packets {
        description
          "Log dropped packets";
        type empty;
      }
      container flow-export {
        description
          "Configure inspect external logging parameters";
        container template {
          description
            "Configure record template parameters";
          leaf timeout-rate {
            description
              "Rate to resend the template in seconds";
            type string;
          }
        }
        container v9 {
          description
            "Netflow version 9";
          container udp {
            description
              "Use UDP to export records";
            container destination {
              description
                "Specify the flow-export destination";
              leaf dst-ip {
                type string;
              }
              leaf dst-port {
                type string;
              }
            }
          }
        }
      }
    }
    leaf max-destination {
      description
        "config maximum destination";
      // NCS drop when statement
      type string;
    }
    container max-incomplete {
      description
        "Specify maximum number of incomplete connections before clamping";
      leaf high {
        description
          "Specify high-watermark for clamping";
        type string;
      }
      leaf low {
        description
          "Specify low-watermark for clamping";
        type string;
      }
    }
    container one-minute {
      description
        "Specify one-minute-sample watermarks for clamping";
      // NCS drop when statement
      leaf high {
        description
          "Specify high-watermark for clamping";
        type string;
      }
      leaf low {
        description
          "Specify low-watermark for clamping";
        type string;
      }
    }
    container sessions {
      description
        "Maximum number of inspect sessions";
      // NCS drop when statement
      leaf maximum {
        description
          "Maximum sessions";
        type string;
      }
      container queue {
        description
          "queue";
        leaf max-threshold {
          type string;
        }
        leaf min-threshold {
          type string;
        }
      }
    }
    choice tcp-ins {
      container tcp-inspect {
        // NCS drop when statement
        container tcp {
          description
            "Config timeout values for tcp connections";
          // NCS drop when statement
          leaf finwait-time {
            description
              "Specify timeout for TCP connections after a FIN";
            type string;
          }
          leaf idle-time {
            description
              "Specify idle timeout for tcp connections";
            type string;
          }
          container max-incomplete {
            description
              "Specify max half-open connection per host";
            leaf host {
              description
                "Specify max half-open connection per host";
              type string;
            }
          }
          leaf synwait-time {
            description
              "Specify timeout for TCP connections after a SYN and no";
            type string;
          }
        }
      }
      container tcp-inspect-zone {
        // NCS drop when statement
        container tcp {
          description
            "Configure tcp syn-flood per-destination rate";
          container syn-flood {
            description
              "maximum syn packet";
            container rate {
              description
                "maximum syn packet rate";
              leaf per-destination {
                description
                  "per destination
                   maximum rate of TCP SYN packets";
                type string;
              }
            }
          }
        }
      }
    }
    container threat-detection {
      description
        "Configure Threat Detection";
      // NCS drop when statement
      leaf basic-threat {
        description
          "Enable Threat Detection";
        type empty;
      }
      container rate {
        description
          "Configure Threat Detection rate";
        container fw-drop {
          description
            "Configure Threat Detection rate for firewall drop events";
          leaf average-time-frame {
            description
              "Configure Threat Detection average time frame";
            type string;
          }
          leaf average-threshold {
            description
              "Configure Threat Detection average threshold";
            type string;
          }
          leaf burst-threshold {
            description
              " Configure Threat Detection burst threshold";
            type string;
          }
        }
        container inspect-drop {
          description
            "Configure Threat Detection rate for firewall inspection based drop events";
          leaf average-time-frame {
            description
              "Configure Threat Detection average time frame";
            type string;
          }
          leaf average-threshold {
            description
              "Configure Threat Detection average threshold";
            type string;
          }
          leaf burst-threshold {
            description
              " Configure Threat Detection burst threshold";
            type string;
          }
        }
        container syn-attack {
          description
            "Configure Threat Detection rate for syn attack events";
          leaf average-time-frame {
            description
              "Configure Threat Detection average time frame";
            type string;
          }
          leaf average-threshold {
            description
              "Configure Threat Detection average threshold";
            type string;
          }
          leaf burst-threshold {
            description
              " Configure Threat Detection burst threshold";
            type string;
          }
        }
      }
    }
    container udp {
      description
        "Config timeout values for udp flows";
      // NCS drop when statement
      leaf idle-time {
        description
          "Specify idle timeout for udp";
        type string;
      }
    }
    container vrf {
      description
        "vrf binding with parameter map";
      leaf name {
        type string;
      }
      leaf inspect {
        description
          "vrf binding with parameter map";
        type string;
      }
    }
    leaf zone-mismatch {
      description
        "Config zone-mismatch option";
      type string;
    }
  }

  grouping ncs_template_config-service-policy-direction-grouping {
    leaf input {
      description
        "Assign policy-map to the input of an interface";
      type string;
    }
    leaf output {
      description
        "Assign policy-map to the output of an interface";
      type string;
    }
  }

  grouping ncs_template_config-service-policy-grouping {
    container service-policy {
      uses ncs_template_config-service-policy-direction-grouping;
    }
  }

  grouping ncs_template_config-interface-service-policy-grouping {
    container service-policy {
      description
        "Configure QoS Service Policy";
      leaf history {
        description
          "Keep history of QoS metrics";
        type empty;
      }
      uses ncs_template_config-service-policy-direction-grouping;
      container type {
        description
          "Configure CPL Service Policy";
        container control {
          leaf subscriber {
            type string;
          }
        }
        container performance-monitor {
          description
            "Configure media monitor service-policy type";
          leaf direction {
            type string;
          }
          leaf name {
            type string;
          }
        }
        container service-chain {
          description
            "Configure Service-chain Service Policy";
          container input {
            description
              "Assign policy-map to the input of an interface";
            leaf name {
              type string;
            }
          }
          container output {
            description
              "Assign policy-map to the output of an interface";
            leaf name {
              type string;
            }
          }
        }
      }
    }
  }

  grouping ncs_rpc_notif_police-action-transmit-grouping {
    leaf transmit {
      description
        "transmit packet";
      type empty;
    }
  }

  grouping ncs_rpc_notif_police-action-drop-grouping {
    leaf drop {
      description
        "drop packet";
      type empty;
    }
  }

  grouping ncs_rpc_notif_police-conform-action-grouping {
    container conform-set-clp-transmit {
      container conform-action {
        description
          "action when rate is less than conform burst";
        leaf set-clp-transmit {
          description
            "set atm clp and send it";
          type empty;
        }
      }
    }
    container conform-set-cos-transmit {
      container conform-action {
        description
          "action when rate is less than conform burst";
        leaf set-cos-transmit {
          description
            "rewrite packet cos and send it";
          type ios-types:cos_value-type;
        }
      }
    }
    container conform-set-cos-transmit-table {
      container conform-action {
        description
          "action when rate is less than conform burst";
        leaf set-cos-transmit {
          description
            "rewrite packet cos and send it";
          type ios-types:cos_value-type;
        }
        leaf table {
          description
            "Specify table-map";
          type string;
        }
      }
    }
    container conform-set-discard-class-transmit {
      container conform-action {
        description
          "action when rate is less than conform burst";
        leaf set-discard-class-transmit {
          description
            "set discard-class and send it";
          type uint8 {
            range "0..7";
          }
        }
      }
    }
    container conform-set-dscp-transmit {
      container conform-action {
        description
          "action when rate is less than conform burst";
        leaf set-dscp-transmit {
          description
            "set dscp and send it";
          type ios-types:dscp-type;
        }
      }
    }
    container conform-set-dscp-transmit-table {
      container conform-action {
        description
          "action when rate is less than conform burst";
        leaf set-dscp-transmit {
          description
            "set dscp and send it";
          type ios-types:dscp-type;
        }
        leaf table {
          description
            "Specify table-map";
          type string;
        }
      }
    }
    container conform-set-frde-transmit {
      container conform-action {
        description
          "action when rate is less than conform burst";
        leaf set-frde-transmit {
          description
            "set FR DE and send it";
          type empty;
        }
      }
    }
    container conform-set-mpls-exp-imposition-transmit {
      container conform-action {
        description
          "action when rate is less than conform burst";
        leaf set-mpls-exp-imposition-transmit {
          description
            "set exp at tag imposition and send it";
          type ios-types:exp_value-type;
        }
      }
    }
    container conform-set-mpls-exp-imposition-transmit-table {
      container conform-action {
        description
          "action when rate is less than conform burst";
        leaf set-mpls-exp-imposition-transmit {
          description
            "set exp at tag imposition and send it";
          type ios-types:exp_value-type;
        }
        leaf table {
          description
            "Specify table-map";
          type string;
        }
      }
    }
    container conform-set-mpls-exp-topmost-transmit {
      container conform-action {
        description
          "action when rate is less than conform burst";
        leaf set-mpls-exp-topmost-transmit {
          description
            "set exp on topmost label and send it";
          type ios-types:exp_value-type;
        }
      }
    }
    container conform-set-mpls-exp-topmost-transmit-table {
      container conform-action {
        description
          "action when rate is less than conform burst";
        leaf set-mpls-exp-topmost-transmit {
          description
            "set exp on topmost label and send it";
          type ios-types:exp_value-type;
        }
        leaf table {
          description
            "Specify table-map";
          type string;
        }
      }
    }
    container conform-set-prec-transmit {
      container conform-action {
        description
          "action when rate is less than conform burst";
        leaf set-prec-transmit {
          description
            "rewrite packet precedence and send it";
          type ios-types:prec_value-type;
        }
      }
    }
    container conform-set-prec-transmit-table {
      container conform-action {
        description
          "action when rate is less than conform burst";
        leaf set-prec-transmit {
          description
            "rewrite packet precedence and send it";
          type ios-types:prec_value-type;
        }
        leaf table {
          description
            "Specify table-map";
          type string;
        }
      }
    }
    container conform-set-qos-transmit {
      container conform-action {
        description
          "action when rate is less than conform burst";
        leaf set-qos-transmit {
          description
            "set qos-group and send it";
          type ios-types:qos_value-type;
        }
      }
    }
    container conform-set-qos-transmit-table {
      container conform-action {
        description
          "action when rate is less than conform burst";
        leaf set-qos-transmit {
          description
            "set qos-group and send it";
          type ios-types:qos_value-type;
        }
        leaf table {
          description
            "Specify table-map";
          type string;
        }
      }
    }
    container conform-transmit {
      container conform-action {
        description
          "action when rate is less than conform burst";
        uses ncs_rpc_notif_police-action-transmit-grouping;
      }
    }
    container conform-drop {
      container conform-action {
        description
          "action when rate is less than conform burst";
        uses ncs_rpc_notif_police-action-drop-grouping;
      }
    }
  }

  grouping ncs_rpc_notif_police-exceed-action-grouping {
    container exceed-dscp {
      container exceed-action {
        description
          "action when rate is within conform and conform + exceed burst";
        leaf dscp {
          type ios-types:dscp-type;
        }
      }
    }
    container exceed-set-clp-transmit {
      container exceed-action {
        description
          "action when rate is within conform and conform + exceed burst";
        leaf set-clp-transmit {
          description
            "set atm clp and send it";
          type empty;
        }
      }
    }
    container exceed-set-cos-transmit {
      container exceed-action {
        description
          "action when rate is within conform and conform + exceed burst";
        leaf set-cos-transmit {
          description
            "rewrite packet cos and send it";
          type ios-types:cos_value-type;
        }
        leaf table {
          description
            "Specify table-map";
          type string;
        }
      }
    }
    container exceed-set-discard-class-transmit {
      container exceed-action {
        description
          "action when rate is within conform and conform + exceed burst";
        leaf set-discard-class-transmit {
          description
            "set discard-class and send it";
          type uint8 {
            range "0..7";
          }
        }
      }
    }
    container exceed-set-dscp-transmit {
      container exceed-action {
        description
          "action when rate is within conform and conform + exceed burst";
        container set-dscp-transmit {
          container dscp {
            leaf table {
              type enumeration {
                enum "policed-dscp";
              }
            }
          }
        }
      }
    }
    container exceed-set-dscp-transmit-table {
      container exceed-action {
        description
          "action when rate is within conform and conform + exceed burst";
        leaf set-dscp-transmit {
          description
            "set dscp and send it";
          type ios-types:dscp-type;
        }
        leaf table {
          description
            "Specify table-map";
          type string;
        }
      }
    }
    container exceed-set-frde-transmit {
      container exceed-action {
        description
          "action when rate is within conform and conform + exceed burst";
        leaf set-frde-transmit {
          description
            "set FR DE and send it";
          type empty;
        }
      }
    }
    container exceed-set-mpls-exp-imposition-transmit {
      container exceed-action {
        description
          "action when rate is within conform and conform + exceed burst";
        leaf set-mpls-exp-imposition-transmit {
          description
            "set exp at tag imposition and send it";
          type ios-types:exp_value-type;
        }
      }
    }
    container exceed-set-mpls-exp-topmost-transmit {
      container exceed-action {
        description
          "action when rate is within conform and conform + exceed burst";
        leaf set-mpls-exp-topmost-transmit {
          description
            "set exp on topmost label and send it";
          type ios-types:exp_value-type;
        }
      }
    }
    container exceed-set-prec-transmit {
      container exceed-action {
        description
          "action when rate is within conform and conform + exceed burst";
        leaf set-prec-transmit {
          description
            "rewrite packet precedence and send it";
          type ios-types:prec_value-type;
        }
        leaf table {
          description
            "Specify table-map";
          type string;
        }
      }
    }
    container exceed-set-qos-transmit {
      container exceed-action {
        description
          "action when rate is within conform and conform + exceed burst";
        leaf set-qos-transmit {
          description
            "set qos-group and send it";
          type ios-types:qos_value-type;
        }
      }
    }
    container exceed-transmit {
      container exceed-action {
        description
          "action when rate is within conform and conform + exceed burst";
        uses ncs_rpc_notif_police-action-transmit-grouping;
      }
    }
    container exceed-drop {
      container exceed-action {
        description
          "action when rate is within conform and conform + exceed burst";
        uses ncs_rpc_notif_police-action-drop-grouping;
      }
    }
  }

  grouping ncs_rpc_notif_police-violate-action-grouping {
    container violate-set-clp-transmit {
      container violate-action {
        description
          "action when rate is greater than conform + exceed burst";
        leaf set-clp-transmit {
          description
            "set atm clp and send it";
          type empty;
        }
      }
    }
    container violate-set-cos-transmit {
      container violate-action {
        description
          "action when rate is greater than conform + exceed burst";
        leaf set-cos-transmit {
          description
            "rewrite packet cos and send it";
          type ios-types:cos_value-type;
        }
        leaf table {
          description
            "Specify table-map";
          type string;
        }
      }
    }
    container violate-set-discard-class-transmit {
      container violate-action {
        description
          "action when rate is greater than conform + exceed burst";
        leaf set-discard-class-transmit {
          description
            "set discard-class and send it";
          type uint8 {
            range "0..7";
          }
        }
      }
    }
    container violate-set-dscp-transmit {
      container violate-action {
        description
          "action when rate is greater than conform + exceed burst";
        leaf set-dscp-transmit {
          description
            "set dscp and send it";
          type ios-types:dscp-type;
        }
        leaf table {
          description
            "Specify table-map";
          type string;
        }
      }
    }
    container violate-set-frde-transmit {
      container violate-action {
        description
          "action when rate is greater than conform + exceed burst";
        leaf set-frde-transmit {
          description
            "set FR DE and send it";
          type empty;
        }
      }
    }
    container violate-set-mpls-exp-imposition-transmit {
      container violate-action {
        description
          "action when rate is greater than conform + exceed burst";
        leaf set-mpls-exp-imposition-transmit {
          description
            "set exp at tag imposition and send it";
          type ios-types:exp_value-type;
        }
      }
    }
    container violate-set-mpls-exp-topmost-transmit {
      container violate-action {
        description
          "action when rate is greater than conform + exceed burst";
        leaf set-mpls-exp-topmost-transmit {
          description
            "set exp on topmost label and send it";
          type ios-types:exp_value-type;
        }
      }
    }
    container violate-set-prec-transmit {
      container violate-action {
        description
          "action when rate is greater than conform + exceed burst";
        leaf set-prec-transmit {
          description
            "rewrite packet precedence and send it";
          type ios-types:prec_value-type;
        }
        leaf table {
          description
            "Specify table-map";
          type string;
        }
      }
    }
    container violate-set-qos-transmit {
      container violate-action {
        description
          "action when rate is greater than conform + exceed burst";
        leaf set-qos-transmit {
          description
            "set qos-group and send it";
          type ios-types:qos_value-type;
        }
      }
    }
    container violate-transmit {
      container violate-action {
        description
          "action when rate is greater than conform + exceed burst";
        uses ncs_rpc_notif_police-action-transmit-grouping;
      }
    }
    container violate-drop {
      container violate-action {
        description
          "action when rate is greater than conform + exceed burst";
        uses ncs_rpc_notif_police-action-drop-grouping;
      }
    }
  }

  grouping ncs_rpc_notif_police-action-grouping {
    container actions {
      uses ncs_rpc_notif_police-conform-action-grouping;
      uses ncs_rpc_notif_police-exceed-action-grouping;
      uses ncs_rpc_notif_police-violate-action-grouping;
    }
  }

  grouping ncs_rpc_notif_random-detect-grouping {
    leaf min-threshold {
      type uint16 {
        range "1..4096";
      }
    }
    leaf max-threshold {
      type uint16 {
        range "1..4096";
      }
    }
    leaf denominator {
      type uint32 {
        range "1..65535";
      }
    }
  }

  grouping ncs_rpc_notif_config-policy-map-grouping {
    list policy-map {
      description
        "Configure QoS Policy Map";
      key "name";
      leaf name {
        type string;
      }
      leaf type {
        description
          "type of the policy-map";
        type enumeration {
          enum "access-control";
          enum "appnav";
          enum "inspect";
          enum "control";
          enum "packet-service";
          enum "performance-monitor";
          enum "service";
          enum "service-chain";
        }
      }
      leaf subscriber {
        type empty;
      }
      leaf protocol {
        when "../type = 'inspect'" {
          tailf:xpath-root 3;
        }
        type enumeration {
          enum "http";
          enum "im";
          enum "imap";
          enum "p2p";
          enum "pop3";
          enum "smtp";
          enum "sunrpc";
        }
      }
      list event {
        description
          "The event type this control class-map triggers upon";
        key "event-type";
        leaf event-type {
          type enumeration {
            enum "aaa-available";
            enum "absolute-timeout";
            enum "agent-found";
            enum "authentication-failure";
            enum "authentication-success";
            enum "authorization-failure";
            enum "authorization-success";
            enum "identity-update";
            enum "inactivity-timeout";
            enum "remote-authentication-failure";
            enum "remote-authentication-success";
            enum "session-disconnected";
            enum "session-started";
            enum "tag-added";
            enum "tag-removed";
            enum "template-activated";
            enum "template-activation-failed";
            enum "template-deactivated";
            enum "template-deactivation-failed";
            enum "timer-expiry";
            enum "violation";
          }
        }
        leaf match-type {
          type enumeration {
            enum "match-all";
            enum "match-first";
          }
        }
        list class-number {
          description
            "class number, 1 for 1st class, 2 for 2nd...";
          key "number";
          leaf number {
            type uint8 {
              range "1..254";
            }
          }
          leaf class {
            description
              "The class type this control policy-map triggers upon";
            type union {
              type enumeration {
                enum "always";
              }
              type string;
            }
          }
          leaf execution-type {
            type enumeration {
              enum "do-all";
              enum "do-until-failure";
              enum "do-until-success";
            }
          }
          list action-number {
            description
              "action number, 1 for 1st class, 2 for 2nd...";
            key "number";
            leaf number {
              type uint8 {
                range "1..254";
              }
            }
            container terminate {
              description
                "terminate auth method";
              leaf dot1x {
                description
                  "dot1x method";
                type empty;
              }
              leaf mab {
                description
                  "mab method";
                type empty;
              }
              leaf webauth {
                description
                  "webauth method";
                type empty;
              }
            }
            leaf clear-session {
              description
                "clears an active session";
              type empty;
            }
            container resume {
              description
                "resume operation to be specified";
              leaf reauthentication {
                description
                  "resume reauthentication";
                type empty;
              }
            }
            leaf authentication-restart {
              description
                "restarts the auth sequence after the specified number of sec";
              type uint16 {
                range "1..65535";
              }
            }
            container pause {
              description
                "pause operation to be specified";
              leaf reauthentication {
                description
                  "pause reauthentication";
                type empty;
              }
            }
            leaf authorize {
              description
                "authorize session";
              type empty;
            }
            container activate {
              description
                "activate template or policy";
              leaf service-template {
                description
                  "activate service template";
                type string;
              }
            }
            container authenticate {
              description
                "authenticate a session";
              container using {
                description
                  "authenticate a session";
                leaf method {
                  type enumeration {
                    enum "dot1x";
                    enum "mab";
                    enum "webauth";
                  }
                }
                leaf both {
                  description
                    "Enabling Dot1x Authenticator & Supplicant";
                  type empty;
                }
                leaf retries {
                  description
                    "Number of times to retry failed authentications";
                  type uint8 {
                    range "1..5";
                  }
                }
                leaf retry-time {
                  description
                    "Time interval between retries";
                  type uint16 {
                    range "0..65535";
                  }
                }
                leaf priority {
                  description
                    "Method priority";
                  type uint8 {
                    range "1..254";
                  }
                }
              }
            }
          }
        }
      }
      list class {
        description
          "policy criteria";
        key "name";
        leaf name {
          type class-name-type;
        }
        leaf type {
          description
            "type of the class-map";
          type enumeration {
            enum "inspect";
          }
        }
        leaf insert-before {
          description
            "Insert the class before a specified class";
          when "../../type = 'appnav'" {
            tailf:xpath-root 3;
          }
          type string;
        }
        container appnav-policy {
          when "../../type = 'appnav'" {
            tailf:xpath-root 3;
          }
          list distribute {
            description
              "Distribute action";
            key "service-node-group";
            leaf service-node-group {
              description
                "Distribute to service-node-group";
              type string;
            }
            leaf insert-before {
              description
                "Insert before specific node";
              type string;
            }
          }
          leaf monitor-load {
            description
              "Monitor AO";
            when "../distribute" {
              tailf:xpath-root 3;
            }
            type enumeration {
              enum "MS-port-mapper";
              enum "cifs";
              enum "http";
              enum "ica";
              enum "mapi";
              enum "nfs";
              enum "ssl";
              enum "video";
            }
          }
          leaf pass-through {
            description
              "pass-through action";
            type empty;
          }
        }
        container policy {
          when "../../type = 'inspect'" {
            tailf:xpath-root 3;
          }
          leaf action {
            type enumeration {
              enum "cxsc";
              enum "drop";
              enum "inspect";
              enum "pass";
              enum "service-policy";
            }
          }
          leaf log {
            description
              "Send logging message for drop or pass";
            when "../action = 'drop'or ../action = 'pass'" {
              tailf:xpath-root 3;
            }
            type empty;
          }
          leaf parameter-map {
            when "../action = 'inspect' or ../action = 'cxsc'" {
              tailf:xpath-root 3;
            }
            type union {
              type string;
              type enumeration {
                enum "global";
                enum "gtp";
              }
            }
          }
          container dpi {
            when "../action = 'service-policy'" {
              tailf:xpath-root 3;
            }
            leaf type {
              type enumeration {
                enum "gtpv0";
                enum "gtpv1";
                enum "imap";
                enum "pop3";
                enum "smtp";
                enum "sunrpc";
              }
            }
            leaf policy-map {
              type string;
            }
          }
        }
        container pm-policy {
          when "../../type = 'performance-monitor'" {
            tailf:xpath-root 3;
          }
          container flow {
            description
              "Flow subcommands";
            leaf monitor {
              description
                "Apply a Flow Monitor";
              type string;
            }
          }
          container monitor {
            description
              "Monitor related parameters";
            container metric {
              description
                "Monitor metric";
              container rtp {
                description
                  "RTP metrics parameters";
                list clock-rate {
                  description
                    "RTP timestamp field's sampling frequency";
                  key "number";
                  leaf number {
                    type union {
                      type uint8 {
                        range "0..127";
                      }
                      type enumeration {
                        enum "celb";
                        enum "cn";
                        enum "default";
                        enum "dvi4";
                        enum "dvi4-2";
                        enum "dvi4-3";
                        enum "dvi4-4";
                        enum "g722";
                        enum "g723";
                        enum "g728";
                        enum "g729";
                        enum "gsm";
                        enum "h261";
                        enum "h263";
                        enum "jpeg";
                        enum "l16";
                        enum "l16-2";
                        enum "lpc";
                        enum "mp2t";
                        enum "mpa";
                        enum "mpv";
                        enum "nv";
                        enum "pcma";
                        enum "pcmu";
                        enum "qcelp";
                      }
                    }
                  }
                  leaf frequency {
                    type uint32 {
                      range "1000..192000";
                    }
                  }
                }
              }
            }
          }
          list react {
            description
              "Configure threshold crossing actions";
            key "id";
            leaf id {
              type uint16;
            }
            leaf mode {
              type enumeration {
                enum "media-stop";
                enum "mrv";
                enum "rtp-jitter-average";
                enum "transport-packets-lost-rate";
              }
            }
            leaf description {
              description
                "Description for the instance";
              type string;
            }
            container action {
              description
                "Config react action";
              leaf snmp {
                description
                  "SNMP is notified of the event";
                type empty;
              }
              leaf syslog {
                description
                  "The threshold-crossing event is logged to syslog";
                type empty;
              }
            }
            container alarm {
              description
                "Config react alarm";
              leaf severity {
                description
                  "Alarm severity - default level none";
                type enumeration {
                  enum "alert";
                  enum "critical";
                  enum "emergency";
                  enum "error";
                  enum "info";
                }
              }
              container type {
                description
                  "Alarm raised type - for each flow or a group";
                leaf discrete {
                  description
                    "Alert for each flow within the class";
                  type empty;
                }
                container grouped {
                  description
                    "Alert if more than one flow cross the threshold";
                  leaf count {
                    description
                      "Number of flows in the group cross the threshold";
                    type uint16;
                  }
                  leaf percent {
                    description
                      "Percent of flows in the group cross the threshold";
                    type uint8 {
                      range "1..100";
                    }
                  }
                }
              }
            }
            container threshold {
              description
                "Config react threshold";
              container value {
                description
                  "Range of percentage loss that would trigger the alarm";
                leaf ge {
                  description
                    "greater and equal to";
                  type string;
                }
                leaf gt {
                  description
                    "greater than";
                  type string;
                }
                leaf le {
                  description
                    "less and equal to";
                  type string;
                }
                leaf lt {
                  description
                    "less than";
                  type string;
                }
                container range {
                  description
                    "threshold within the range of";
                  leaf low {
                    type string;
                  }
                  leaf high {
                    type string;
                  }
                }
              }
            }
          }
        }
        container inspect-police {
          when "../policy/action = 'inspect'" {
            tailf:xpath-root 3;
          }
          container police {
            description
              "Police";
            leaf rate {
              description
                "Specify police rate";
              type uint32 {
                range "8000..2000000000";
              }
            }
            leaf burst {
              description
                "Specify 'burst' parameter";
              type uint32 {
                range "1000..512000000";
              }
            }
          }
        }
        list action-list {
          key "action-type";
          ordered-by user;
          leaf action-type {
            type policy-action-type;
          }
          choice action-param {
            case bandwidth-case {
              container bandwidth {
                when "../action-type = 'bandwidth'" {
                  tailf:xpath-root 3;
                }
                leaf bits {
                  type uint32 {
                    range "8..2000000";
                  }
                }
                leaf percent {
                  description
                    "% of total Bandwidth";
                  type ios-types:percentage;
                }
                container remaining {
                  description
                    "% of the remaining bandwidth";
                  leaf rem-option {
                    type enumeration {
                      enum "percent";
                      enum "ratio";
                    }
                  }
                  leaf percent {
                    description
                      "% of the remaining bandwidth";
                    when "../rem-option='percent'" {
                      tailf:xpath-root 3;
                    }
                    type ios-types:percentage;
                  }
                  leaf ratio {
                    description
                      "ratio for sharing excess bandwidth";
                    when "../rem-option='ratio'" {
                      tailf:xpath-root 3;
                    }
                    type uint16;
                  }
                  container account {
                    description
                      "Overhead Accounting";
                    when "../rem-option = 'percent' or ../rem-option = 'ratio'" {
                      tailf:xpath-root 3;
                    }
                    leaf user-defined {
                      description
                        "Offset Size";
                      type int32 {
                        range "-1000000..1000000";
                      }
                    }
                  }
                }
              }
            }
            case compression-case {
              container compression {
                when "../action-type = 'compression'" {
                  tailf:xpath-root 3;
                }
                container header {
                  description
                    "configure header compression";
                  presence "configure header compression";
                  leaf ip {
                    description
                      "configure ip header compression";
                    type enumeration {
                      enum "rtp";
                      enum "tcp";
                    }
                  }
                }
              }
            }
            case estimate-case {
              container estimate {
                when "../action-type = 'estimate'" {
                  tailf:xpath-root 3;
                }
                container bandwidth {
                  presence "bandwidth required to service this class";
                  description
                    "bandwidth required to service this class";
                  container delay-one-in {
                    description
                      "specify QoS target delay";
                    leaf doi {
                      type uint32 {
                        range "50..1000000";
                      }
                    }
                    leaf milliseconds {
                      type uint32 {
                        range "8..1000";
                      }
                    }
                  }
                  leaf drop-one-in {
                    description
                      "specify QoS target loss rate";
                    type uint32;
                  }
                }
              }
            }
            case forward-case {
              container forward {
                when "../action-type = 'forward'" {
                  tailf:xpath-root 3;
                }
                leaf service-path {
                  description
                    "Service Path Entries";
                  type uint32 {
                    range "0..16777215";
                  }
                }
                leaf service-index {
                  description
                    "Service Index";
                  type uint8 {
                    range "2..255";
                  }
                }
              }
            }
            case fair-queue-case {
              container fair-queue {
                when "../action-type = 'fair-queue'" {
                  tailf:xpath-root 3;
                }
                leaf dynamic-queues {
                  type uint32 {
                    range "16|32|64|128|256|512|1024|2048|4096";
                  }
                }
                leaf queue-limit {
                  description
                    "per flow queue limit";
                  type uint16 {
                    range "1..32768";
                  }
                }
              }
            }
            case netflow-sampler-case {
              leaf netflow-sampler {
                when "../action-type = 'netflow-sampler'" {
                  tailf:xpath-root 3;
                }
                type string;
              }
            }
            case police-case {
              choice police-choice {
                case police-aggregate-case {
                  container police-aggregate {
                    container police {
                      when "../../action-type = 'police'" {
                        tailf:xpath-root 3;
                      }
                      leaf aggregate {
                        description
                          "Choose aggregate policer for current class";
                        type string;
                      }
                    }
                  }
                }
                case police-policy-map-case {
                  container police-policy-map {
                    container police {
                      when "../../action-type = 'police'" {
                        tailf:xpath-root 3;
                      }
                      leaf cir {
                        description
                          "Committed information rate";
                        type police-bps-type;
                      }
                      leaf bc {
                        description
                          "Conform burst";
                        type police-burst-type;
                      }
                      leaf be {
                        description
                          "Excess burst";
                        when "../bc" {
                          tailf:xpath-root 3;
                        }
                        type police-burst-type;
                      }
                      leaf pir {
                        description
                          "Peak Information Rate";
                        type police-bps-type;
                      }
                      container pir-be {
                        when "../pir" {
                          tailf:xpath-root 3;
                        }
                        leaf be {
                          description
                            "Excess burst";
                          type police-burst-type;
                        }
                      }
                      uses ncs_rpc_notif_police-action-grouping;
                    }
                  }
                }
                case police-cir-percent-case {
                  container police-cir-percent {
                    container police {
                      when "../../action-type = 'police'" {
                        tailf:xpath-root 3;
                      }
                      container cir {
                        description
                          "Committed information rate";
                        container percent {
                          description
                            "% of interface bandwidth for Committed information rate";
                          leaf percentage {
                            type ios-types:percentage;
                          }
                          leaf bc {
                            description
                              "Conform burst";
                            type uint16;
                          }
                          container bc-ms {
                            when "../bc" {
                              tailf:xpath-root 3;
                            }
                            leaf ms {
                              description
                                "Milli seconds";
                              type empty;
                            }
                          }
                          leaf be {
                            when "../bc-ms/ms" {
                              tailf:xpath-root 3;
                            }
                            type uint16;
                          }
                          container be-ms {
                            when "../be" {
                              tailf:xpath-root 3;
                            }
                            leaf ms {
                              description
                                "Milli seconds";
                              type empty;
                            }
                          }
                          container pir {
                            description
                              "Peak Information Rate";
                            leaf percent {
                              description
                                "% of interface bandwidth for Peak Information Rate";
                              type ios-types:percentage;
                            }
                          }
                          container pir-be {
                            when "../pir" {
                              tailf:xpath-root 3;
                            }
                            leaf be {
                              description
                                "Excess burst";
                              type uint16;
                            }
                          }
                          container pir-be-ms {
                            when "../pir-be/be" {
                              tailf:xpath-root 3;
                            }
                            leaf ms {
                              description
                                "Milli seconds";
                              type empty;
                            }
                          }
                          uses ncs_rpc_notif_police-action-grouping;
                        }
                      }
                    }
                  }
                }
                case police-rate-unit-case {
                  container police-rate-unit {
                    container police {
                      when "../../action-type = 'police'" {
                        tailf:xpath-root 3;
                      }
                      container rate {
                        description
                          "Specify police rate";
                        leaf units {
                          type uint64;
                        }
                        leaf xps {
                          type police-pps-bps-type;
                        }
                        container burst {
                          description
                            "Specify 'burst' parameter";
                          leaf burst-value {
                            type uint32;
                          }
                          leaf burst-type {
                            type police-packets-bytes-type;
                          }
                        }
                        container peak-rate {
                          description
                            "Specify peak rate";
                          leaf peak-rate-value {
                            type uint32 {
                              range "1..512000000";
                            }
                          }
                          leaf xps {
                            type police-pps-bps-type;
                          }
                        }
                        container peak-burst {
                          description
                            "Specify 'peak-burst' parameter for peak-rate";
                          leaf burst-value {
                            type uint32;
                          }
                          leaf burst-type {
                            type police-packets-bytes-type;
                          }
                        }
                        uses ncs_rpc_notif_police-action-grouping;
                      }
                    }
                  }
                }
                case police-rate-percent-case {
                  container police-rate-percent {
                    container police {
                      when "../../action-type = 'police'" {
                        tailf:xpath-root 3;
                      }
                      container rate {
                        description
                          "Specify police rate";
                        container percent {
                          description
                            "% of interface bandwidth for rate";
                          leaf percentage {
                            type ios-types:percentage;
                          }
                          leaf burst {
                            description
                              "Specify 'burst' parameter";
                            type uint16;
                          }
                          leaf ms {
                            description
                              "Treat 'burst' value in milliseconds";
                            when "../burst" {
                              tailf:xpath-root 3;
                            }
                            type empty;
                          }
                          container peak-rate {
                            description
                              "Specify peak rate";
                            leaf percent {
                              description
                                "% of interface bandwidth for peak-rate";
                              type ios-types:percentage;
                            }
                          }
                          leaf peak-burst {
                            description
                              "Specify 'peak-burst' parameter for 'peak-rate'";
                            type uint16;
                          }
                          container peak-burst-ms {
                            when "../peak-burst" {
                              tailf:xpath-root 3;
                            }
                            leaf ms {
                              description
                                "Milli seconds";
                              type empty;
                            }
                          }
                          uses ncs_rpc_notif_police-action-grouping;
                        }
                      }
                    }
                  }
                }
                case police-rate-pdp-case {
                  container police-rate-pdp {
                    container police {
                      when "../../action-type = 'police'" {
                        tailf:xpath-root 3;
                      }
                      container rate {
                        description
                          "Specify police rate";
                        container pdp {
                          description
                            "% of interface bandwidth for rate";
                          leaf burst {
                            description
                              "Conform burst";
                            type police-burst-type;
                          }
                          leaf peak-rate {
                            description
                              "Specify peak rate";
                            type enumeration {
                              enum "pdp";
                            }
                          }
                          leaf peak-burst {
                            description
                              "Specify 'peak-burst' parameter for 'peak-rate'";
                            when "../peak-rate" {
                              tailf:xpath-root 3;
                            }
                            type police-burst-type;
                          }
                          uses ncs_rpc_notif_police-action-grouping;
                        }
                      }
                    }
                  }
                }
                case police-target-bitrate-case {
                  container police-target-bitrate {
                    container police {
                      when "../../action-type = 'police'" {
                        tailf:xpath-root 3;
                      }
                      leaf bit-rate {
                        description
                          "Target bit rate (bits per second) (postfix k, m, g optional),decimal point allowed";
                        type uint64 {
                          range "8000..10000000000";
                        }
                      }
                      leaf confirm_burst-byte {
                        description
                          "Burst Byte";
                        type uint64 {
                          range "100..512000000";
                        }
                      }
                      leaf excess_burst-byte {
                        description
                          "Burst Byte";
                        type uint64 {
                          range "100..512000000";
                        }
                      }
                      leaf conform-action {
                        description
                          "action when rate is less than conform burst";
                        type empty;
                      }
                      leaf transmit {
                        description
                          "transmit packet";
                        type empty;
                      }
                      leaf exceed-action {
                        description
                          "action when rate is within conform and conform + exceed burst";
                        type empty;
                      }
                      leaf drop {
                        description
                          "drop packet";
                        type empty;
                      }
                      leaf set-dscp-transmit {
                        description
                          "set dscp and send it";
                        type empty;
                      }
                      leaf dscp {
                        description
                          "Set packet dscp from dscp";
                        type empty;
                      }
                      leaf table {
                        description
                          "Specify table-map";
                        type string;
                      }
                      container actions {
                        uses ncs_rpc_notif_police-conform-action-grouping;
                        uses ncs_rpc_notif_police-exceed-action-grouping;
                        uses ncs_rpc_notif_police-violate-action-grouping;
                      }
                    }
                  }
                }
                case police-flow-case {
                  container police-flow {
                    container police {
                      when "../../action-type = 'police'" {
                        tailf:xpath-root 3;
                      }
                      container flow {
                        description
                          "police each flow";
                        leaf mask {
                          description
                            "flow mask to be used for policing";
                          type enumeration {
                            enum "dest-only";
                            enum "full-flow";
                            enum "src-only";
                          }
                        }
                        leaf bps {
                          type police-bps-type;
                        }
                        leaf burst-normal {
                          type police-burst-type;
                          when "../bps" {
                            tailf:xpath-root 3;
                          }
                        }
                        uses ncs_rpc_notif_police-action-grouping;
                      }
                    }
                  }
                }
                case police-catalyst-case {
                  container police-catalyst {
                    container police {
                      when "../../action-type = 'police'" {
                        tailf:xpath-root 3;
                      }
                      leaf bps-value {
                        type string;
                      }
                      leaf bps {
                        type empty;
                      }
                      leaf byte-value {
                        type string;
                      }
                      leaf byte {
                        type empty;
                      }
                      container actions {
                        uses ncs_rpc_notif_police-conform-action-grouping;
                        uses ncs_rpc_notif_police-exceed-action-grouping;
                        uses ncs_rpc_notif_police-violate-action-grouping;
                      }
                    }
                  }
                }
                case police-switch-case {
                  container police-switch {
                    container police {
                      when "../../action-type = 'police'" {
                        tailf:xpath-root 3;
                      }
                      leaf cir {
                        type uint32 {
                          range "8000..1000000000";
                        }
                      }
                      leaf bc {
                        type uint32 {
                          range "8000..2000000";
                        }
                      }
                      leaf exceed-action {
                        description
                          "action when rate is exceeded";
                        type enumeration {
                          enum "drop";
                          enum "policed-dscp-transmit";
                        }
                      }
                    }
                  }
                }
              }
            }
            case priority-case {
              container priority {
                when "../action-type = 'priority'" {
                  tailf:xpath-root 3;
                }
                leaf level {
                  description
                    "Multi-Level Priority Queue";
                  type uint8 {
                    range "1..2";
                  }
                }
                choice priority-type {
                  leaf kilo-bits {
                    type uint32 {
                      range "8..2000000";
                    }
                  }
                  leaf percent {
                    description
                      "% of total bandwidth";
                    type uint16 {
                      range "1..100";
                    }
                  }
                }
                leaf burst {
                  type uint32 {
                    range "32..64000000";
                  }
                }
              }
            }
            case queue-buffers-case {
              container queue-buffers {
                when "../action-type = 'queue-buffers'" {
                  tailf:xpath-root 3;
                }
                leaf ratio {
                  description
                    "Relative buffer size for queue";
                  type uint8 {
                    range "0..100";
                  }
                }
              }
            }
            case queue-limit-case {
              container queue-limit {
                when "../action-type = 'queue-limit'" {
                  tailf:xpath-root 3;
                }
                leaf queue-limit-value {
                  type uint32 {
                    range "1..8192000";
                  }
                }
                leaf queue-limit-type {
                  type enumeration {
                    enum "bytes";
                    enum "ms";
                    enum "packets";
                    enum "us";
                  }
                }
              }
              container queue-limit-dscp {
                when "../action-type = 'queue-limit'" {
                  tailf:xpath-root 3;
                }
                list dscp {
                  description
                    "parameters for each dscp value";
                  key "dscp-val";
                  leaf dscp-val {
                    type ios-types:dscp-type;
                  }
                  leaf values {
                    description
                      "dscp values";
                    type empty;
                  }
                  leaf dscp-val1 {
                    type ios-types:dscp-type;
                  }
                  leaf percent {
                    description
                      "% of threshold";
                    type uint8 {
                      range "0..100";
                    }
                  }
                }
              }
            }
            case random-detect {
              container random-detect {
                when "../action-type = 'random-detect'" {
                  tailf:xpath-root 3;
                }
                container aggregate {
                  description
                    "aggregate subclasses";
                  presence "true";
                  leaf minimum-thresh {
                    description
                      "minimum threshold for red aggregate";
                    type uint32 {
                      range "0..1000000";
                    }
                  }
                  leaf maximum-thresh {
                    description
                      "maximum threshold for red aggregate";
                    type uint32 {
                      range "0..1000000";
                    }
                  }
                  leaf mark-probability {
                    description
                      "mark-probability for red aggregate";
                    type empty;
                  }
                  leaf denominator {
                    type uint32 {
                      range "0..65535";
                    }
                  }
                }
                container discard-class {
                  description
                    "parameters for each discard-class value";
                  leaf dclass {
                    type uint16 {
                      range "0..7";
                    }
                  }
                  uses ncs_rpc_notif_random-detect-grouping;
                }
                leaf discard-class-based {
                  description
                    "Enable discard-class-based WRED as drop policy";
                  type empty;
                }
                leaf dscp-based {
                  description
                    "Enable dscp-based WRED as drop policy";
                  type empty;
                }
                list dscp {
                  description
                    "parameters for each dscp value";
                  key "dscp-val";
                  leaf dscp-val {
                    type ios-types:dscp-type;
                  }
                  uses ncs_rpc_notif_random-detect-grouping;
                }
                leaf ecn {
                  description
                    "explicit congestion notification";
                  type empty;
                }
                leaf exponential-weighting-constant {
                  description
                    "weight for mean queue depth calculation";
                  type uint16 {
                    range "1..16";
                  }
                }
                leaf prec-based {
                  description
                    "Enable precedence-based WRED as drop policy";
                  type empty;
                }
                container precedence {
                  description
                    "parameters for each precedence value";
                  leaf prec {
                    type precedence-type2;
                  }
                  uses ncs_rpc_notif_random-detect-grouping;
                }
              }
            }
            case service-policy-case {
              leaf service-policy {
                type string;
              }
            }
            case set-case {
              container set {
                when "../action-type = 'set'" {
                  tailf:xpath-root 3;
                }
                leaf atm-clp {
                  description
                    "Set ATM CLP bit to 1";
                  type empty;
                }
                container cos {
                  description
                    "Set IEEE 802.1Q/ISL class of service/user priority";
                  choice cos-type {
                    case a {
                      leaf val {
                        type uint16 {
                          range "0..7";
                        }
                      }
                    }
                    case b {
                      leaf pack {
                        type enumeration {
                          enum "dscp";
                          enum "precedence";
                          enum "cos";
                          enum "qos-group";
                          enum "wlan";
                        }
                      }
                      leaf user-priority {
                        description
                          "Set value from WLAN user-priority";
                        when "../pack = 'wlan'" {
                          tailf:xpath-root 3;
                        }
                        type empty;
                      }
                      leaf table {
                        description
                          "Set codepoint value based on tablemap.";
                        type string;
                      }
                    }
                  }
                }
                leaf discard-class {
                  description
                    "Discard behavior identifier";
                  type uint16 {
                    range "0..7";
                  }
                }
                container dscp {
                  description
                    "Set DSCP in IP(v4) and IPv6 packets";
                  container dscp {
                    description
                      "Set packet dscp from dscp";
                    presence "true";
                    leaf table {
                      description
                        "Set packet dscp from dscp based on table map.";
                      type string;
                    }
                  }
                  leaf tunnel {
                    description
                      "set tunnel packet dscp";
                    type empty;
                  }
                  leaf dscp-val {
                    type ios-types:dscp-type;
                  }
                }
                leaf fr-de {
                  description
                    "Set FR DE bit to 1";
                  type empty;
                }
                container ip {
                  description
                    "Set IP specific values";
                  choice ip-choice {
                    container dscp {
                      description
                        "Set IP DSCP (DiffServ CodePointint)";
                      leaf tunnel {
                        description
                          "set tunnel packet dscp";
                        type empty;
                      }
                      leaf dscp-val {
                        type ios-types:dscp-type;
                      }
                    }
                    container precedence {
                      description
                        "Set IP precedence";
                      presence "Set IP precedence";
                      leaf precedence-val {
                        type ios-types:precedence-type;
                      }
                    }
                  }
                }
                container mpls {
                  description
                    "Set MPLS specific values";
                  container experimental {
                    description
                      "Set Experimental value";
                    container imposition {
                      description
                        "Set Experimental value at tag imposition";
                      leaf exp-value {
                        type uint8 {
                          range "0..7";
                        }
                      }
                    }
                    container topmost {
                      description
                        "Set Experimental value  on topmost label";
                      leaf exp-value {
                        type uint8 {
                          range "0..7";
                        }
                      }
                    }
                  }
                }
                container qos-group {
                  description
                    "Set QoS Group";
                  leaf qos-group-value {
                    type uint8 {
                      range "0..99";
                    }
                  }
                }
              }
            }
            case shape-case {
              container shape {
                when "../action-type = 'shape'" {
                  tailf:xpath-root 3;
                }
                leaf adaptive {
                  description
                    "Enable Traffic Shaping adaptation to BECN";
                  type uint32 {
                    range "8000..154400000";
                  }
                }
                container average {
                  description
                    "configure token bucket: CIR (bps) [Bc (bits) [Be (bits)]], send out Bc only per interval";
                  choice average-choice {
                    case a {
                      leaf bit-rate {
                        type uint64;
                      }
                      leaf bits-per-interval-sustained {
                        type uint32 {
                          range "256..154400000";
                        }
                      }
                      leaf bits-per-interval-excess {
                        when "../bits-per-interval-sustained" {
                          tailf:xpath-root 3;
                        }
                        type uint32 {
                          range "0..154400000";
                        }
                      }
                      container account {
                        description
                          "Overhead Accounting";
                        leaf user-defined {
                          description
                            "Offset Size";
                          type int32 {
                            range "-1000000..1000000";
                          }
                        }
                      }
                    }
                    case b {
                      leaf percent {
                        description
                          "% of interface bandwidth for Committed information rate";
                        type ios-types:percentage;
                      }
                      leaf burst-size-sustained {
                        type uint16 {
                          range "10..2000";
                        }
                      }
                      leaf ms {
                        description
                          "milliseconds";
                        type empty;
                      }
                      container bse {
                        leaf burst-size-excess {
                          type uint16 {
                            range "10..2000";
                          }
                        }
                        leaf ms {
                          description
                            "milliseconds";
                          type empty;
                        }
                      }
                    }
                  }
                }
                leaf fecn-adapt {
                  description
                    "Enable Traffic Shaping reflection of FECN as BECN";
                  type empty;
                }
                container fr-voice-adapt {
                  description
                    "Enable rate adjustment depending on voice presence";
                  presence "Enable rate adjustment depending on voice presence";
                  leaf deactivation {
                    type uint16 {
                      range "1..10000";
                    }
                  }
                }
                leaf max-buffers {
                  description
                    "Set Maximum Buffer Limit";
                  type uint16 {
                    range "1..4096";
                  }
                }
              }
            }
            case trust-case {
              leaf trust {
                when "../action-type = 'trust'" {
                  tailf:xpath-root 3;
                }
                type enumeration {
                  enum "cos";
                  enum "dscp";
                  enum "ip-precedence";
                }
              }
            }
          }
        }
      }
      leaf description {
        description
          "Policy-Map description";
        type string {
          length "1..200";
        }
      }
      leaf sequence-interval {
        description
          "Enable sequence number capability";
        when "../type = 'appnav'" {
          tailf:xpath-root 3;
        }
        type uint16;
      }
    }
  }

  grouping ncs_rpc_notif_class-map-match-result-type-grouping {
    leaf aaa-timeout {
      description
        "aaa timeout type";
      type empty;
    }
    leaf agent-not-found {
      description
        "agent not found type";
      type empty;
    }
    leaf authoritative {
      description
        "failure type";
      type empty;
    }
    leaf method-timeout {
      description
        "method_timeout type";
      type empty;
    }
    leaf none {
      description
        "no type";
      type empty;
    }
    leaf success {
      description
        "success type";
      type empty;
    }
  }

  grouping ncs_rpc_notif_class-map-control-filter-grouping {
    list activated-service-template {
      description
        "match name of service template activated on session";
      key "service-name";
      leaf service-name {
        description
          "Enter service name";
        type string;
      }
    }
    container authorization-status {
      description
        "match the authorization status of the session";
      leaf authorized {
        description
          "authorized";
        type empty;
      }
      leaf unauthorized {
        description
          "unauthorized";
        type empty;
      }
    }
    container authorizing-method-priority {
      description
        "match the priority against the authorizing method's priority";
      leaf eq {
        description
          "equal to";
        type uint8 {
          range "1..254";
        }
      }
      leaf gt {
        description
          "greater than";
        type uint8 {
          range "1..254";
        }
      }
      leaf lt {
        description
          "less than";
        type uint8 {
          range "1..254";
        }
      }
    }
    container method {
      description
        "match the type of authentication method from an event";
      leaf dot1x {
        description
          "dot1x";
        type empty;
      }
      leaf mab {
        description
          "mab";
        type empty;
      }
      leaf webauth {
        description
          "webauth";
        type empty;
      }
    }
    container result-type {
      description
        "match the result type, optionally for a specific method";
      container method {
        description
          "match the result of a particular method";
        container dot1x {
          description
            "dot1x result";
          uses ncs_rpc_notif_class-map-match-result-type-grouping;
        }
        container mab {
          description
            "mab result";
          uses ncs_rpc_notif_class-map-match-result-type-grouping;
        }
        container webauth {
          description
            "webauth result";
          uses ncs_rpc_notif_class-map-match-result-type-grouping;
        }
      }
      uses ncs_rpc_notif_class-map-match-result-type-grouping;
    }
  }

  grouping ncs_rpc_notif_class-map-match-grouping {
    container current-method-priority {
      description
        "match the priority against the current method's priority";
      leaf eq {
        description
          "equal to";
        type uint8 {
          range "1..254";
        }
      }
      leaf gt {
        description
          "greater than";
        type uint8 {
          range "1..254";
        }
      }
      leaf lt {
        description
          "less than";
        type uint8 {
          range "1..254";
        }
      }
    }
    container application {
      description
        "Application to match";
      container application-group {
        description
          "Application Group to match";
        leaf telepresence-group {
          description
            "Telepresence Group";
          type empty;
        }
        leaf vmware-group {
          description
            "VMWARE Group";
          type empty;
        }
        leaf webex-group {
          description
            "WebEx Group";
          type empty;
        }
      }
      container attribute {
        description
          "Application attribute to match";
        leaf media-type {
          description
            "Media type attribute to match";
          type enumeration {
            enum "audio";
            enum "audio-video";
            enum "control";
            enum "data";
            enum "video";
          }
        }
      }
    }
    container access-group {
      description
        "Access group";
      leaf index {
        type uint32 {
          range "1..2699";
        }
      }
      leaf-list name {
        description
          "Named Access List";
        type string;
      }
    }
    leaf any {
      description
        "Any packets";
      type empty;
    }
    leaf-list class-map {
      description
        "Class map";
      type string;
    }
    leaf-list cos {
      description
        "IEEE 802.1Q/ISL class of service/user priority values";
      type uint8 {
        range "0..7";
      }
    }
    container destination-address {
      description
        "Destination address";
      leaf-list mac {
        description
          "MAC address";
        type yang:mac-address;
      }
    }
    leaf-list discard-class {
      description
        "Discard behavior identifier";
      type uint8 {
        range "0..7";
      }
    }
    leaf-list dscp {
      description
        "Match DSCP in IP(v4) and IPv6 packets";
      type ios-types:dscp-type;
    }
    leaf fr-de {
      description
        "Match on Frame-relay DE bit";
      type empty;
    }
    leaf-list fr-dlci {
      description
        "Match on fr-dlci";
      type uint16 {
        range "16..1007";
      }
    }
    container group-object {
      description
        "Match object-group";
      container security {
        description
          "Match object-group security";
        leaf-list source {
          description
            "Match source object-group security";
          type string;
        }
        leaf-list destination {
          description
            "Match destination object-group security";
          type string;
        }
      }
    }
    leaf-list input-interface {
      description
        "Select an input interface to match";
      type string;
    }
    container ip {
      description
        "IP specific values";
      leaf-list dscp {
        description
          "Match IP DSCP (DiffServ CodePoints)";
        type ios-types:dscp-type;
      }
      leaf-list precedence {
        description
          "Match IP precedence";
        type ios-types:precedence-type;
      }
      list rtp {
        description
          "Match RTP port nos";
        key "port1 port2";
        leaf port1 {
          type uint16 {
            range "2000..65535";
          }
        }
        leaf port2 {
          type uint16 {
            range "0..16383";
          }
        }
      }
    }
    leaf non-client-nrt {
      type empty;
    }
    container mpls {
      description
        "Multi Protocol Label Switching specific values";
      container experimental {
        description
          "Match MPLS experimental";
        leaf-list topmost {
          description
            "Match MPLS experimental value on topmost label";
          type uint8 {
            range "0..7";
          }
        }
      }
    }
    container packet {
      description
        "Layer 3 Packet length";
      container length {
        description
          "Layer 3 Packet length";
        leaf max {
          description
            "Maximum length of packet";
          type uint16 {
            range "1..2000";
          }
        }
        leaf min {
          description
            "Minimum length of packet";
          type uint16 {
            range "1..2000";
          }
        }
      }
    }
    leaf-list precedence {
      description
        "Match Precedence in IP(v4) and IPv6 packets";
      type ios-types:precedence-type;
    }
    container protocol {
      description
        "Protocol";
      leaf protocols {
        type enumeration {
          enum "x802-11-iapp";
          enum "ace-svr";
          enum "aol";
          enum "appleqtc";
          enum "biff";
          enum "bittorrent";
          enum "bootpc";
          enum "bootps";
          enum "cddbp";
          enum "cifs";
          enum "cisco-fna";
          enum "cisco-net-mgmt";
          enum "cisco-svcs";
          enum "cisco-sys";
          enum "cisco-tdp";
          enum "cisco-tna";
          enum "citriximaclient";
          enum "clp";
          enum "creativepartnr";
          enum "creativeserver";
          enum "daytime";
          enum "dbase";
          enum "dbcontrol_agent";
          enum "ddns-v3";
          enum "dhcp-failover";
          enum "directconnect";
          enum "discard";
          enum "dnsix";
          enum "echo";
          enum "entrust-svc-hdlr";
          enum "entrust-svcs";
          enum "exec";
          enum "fcip-port";
          enum "ftps";
          enum "gdoi";
          enum "giop";
          enum "gtpv0";
          enum "gtpv1";
          enum "h225ras";
          enum "h323callsigalt";
          enum "hp-alarm-mgr";
          enum "hp-collector";
          enum "hp-managed-node";
          enum "hsrp";
          enum "https";
          enum "ica";
          enum "icabrowser";
          enum "ident";
          enum "igmpv3lite";
          enum "imap3";
          enum "imaps";
          enum "ipass";
          enum "ipsec-msft";
          enum "irc-serv";
          enum "ircs";
          enum "ircu";
          enum "isakmp";
          enum "iscsi";
          enum "iscsi-target";
          enum "kermit";
          enum "ldap-admin";
          enum "ldaps";
          enum "login";
          enum "lotusmtap";
          enum "lotusnote";
          enum "mapi";
          enum "ms-ad-rep";
          enum "ms-exch-nspi";
          enum "ms-frs";
          enum "ms-frsapi";
          enum "ms-rfr";
          enum "msn-messenger";
          enum "netlogon";
          enum "microsoft-ds";
          enum "ms-cluster-net";
          enum "ms-dotnetster";
          enum "ms-sna";
          enum "ms-sql";
          enum "ms-sql-m";
          enum "msexch-routing";
          enum "msnmsgr";
          enum "msrpc";
          enum "mysql";
          enum "n2h2server";
          enum "ncp";
          enum "net8-cman";
          enum "netbios-dgm";
          enum "netbios-ns";
          enum "netbios-ssn";
          enum "netstat";
          enum "oem-agent";
          enum "oracle";
          enum "oracle-em-vp";
          enum "oraclenames";
          enum "orasrv";
          enum "pcanywheredata";
          enum "pcanywherestat";
          enum "pop3s";
          enum "pwdgen";
          enum "qmtp";
          enum "r-winsock";
          enum "radius";
          enum "rdb-dbs-disp";
          enum "realmedia";
          enum "realsecure";
          enum "router";
          enum "rsvp-encap";
          enum "rsvp_tunnel";
          enum "rtc-pm-port";
          enum "rtelnet";
          enum "send";
          enum "shell";
          enum "sip-tls";
          enum "sms";
          enum "smtp";
          enum "snmptrap";
          enum "sql-net";
          enum "sqlserv";
          enum "sqlsrv";
          enum "sshell";
          enum "ssp";
          enum "syslog-conn";
          enum "tacacs";
          enum "tacacs-ds";
          enum "tarantella";
          enum "tcp";
          enum "telnets";
          enum "time";
          enum "timed";
          enum "tr-rsrb";
          enum "ttc";
          enum "udp";
          enum "uucp";
          enum "vqp";
          enum "webster";
          enum "who";
          enum "wins";
          enum "x11";
          enum "xdmcp";
          enum "ymsgr";
          enum "aarp";
          enum "appletalk";
          enum "arp";
          enum "bgp";
          enum "bridge";
          enum "bstun";
          enum "cdp";
        }
      }
      container citrix {
        description
          "Citrix Systems ICA protocol";
        presence "enable citrix system protocol matching";
        leaf ica-tag {
          description
            "Citrix ICA tag 0-high 1-medium 2-low 3-background";
          type string;
        }
      }
      leaf clns {
        description
          "ISO CLNS";
        type empty;
      }
      leaf clns_es {
        description
          "ISO CLNS End System";
        type empty;
      }
      leaf clns_is {
        description
          "ISO CLNS Intermediate System";
        type empty;
      }
      leaf cmns {
        description
          "ISO CMNS";
        type empty;
      }
      leaf compressedtcp {
        description
          "Compressed TCP (VJ";
        type empty;
      }
      leaf cuseeme {
        description
          "CU-SeeMe desktop video conference";
        type empty;
      }
      leaf decnet {
        description
          "DECnet";
        type empty;
      }
      leaf decnet_node {
        description
          "DECnet Node";
        type empty;
      }
      leaf decnet_router-l1 {
        description
          "DECnet Router L1";
        type empty;
      }
      leaf decnet_router-l2 {
        description
          "DECnet Router L2";
        type empty;
      }
      leaf dhcp {
        description
          "Dynamic Host Configuration";
        type empty;
      }
      leaf dlsw {
        type empty;
      }
      leaf dns {
        type empty;
      }
      leaf edonkey {
        type empty;
      }
      leaf egp {
        type empty;
      }
      leaf eigrp {
        type empty;
      }
      leaf exchange {
        type empty;
      }
      container fasttrack {
        description
          "FastTrack Traffic - KaZaA, Morpheus, Grokster";
        presence "enable fasttrack matching";
        leaf file-transfer {
          description
            "File transfer stream";
          type string;
        }
      }
      leaf finger {
        type empty;
      }
      leaf ftp {
        type empty;
      }
      container gnutella {
        description
          "Gnutella Version2 Traffic - BearShare, Shareeza, Morpheus";
        presence "enable gnutella matching";
        leaf file-transfer {
          description
            "File transfer stream";
          type string;
        }
      }
      leaf gopher {
        type empty;
      }
      leaf gre {
        type empty;
      }
      leaf h323 {
        type empty;
      }
      container http {
        description
          "World Wide Web traffic";
        presence "enable http traffic matching";
        leaf c-header-field {
          description
            "Client general Header Field";
          type string;
        }
        leaf host {
          description
            "Server Host Name";
          type string;
        }
        leaf mime {
          description
            "Match MIME Type";
          type string;
        }
        leaf s-header-field {
          description
            "Server general Header Field";
          type string;
        }
        leaf url {
          description
            "Match URL String";
          type string;
        }
      }
      leaf icmp {
        description
          "Internet Control Message";
        type empty;
      }
      leaf imap {
        description
          "Internet Message Access Protocol";
        type empty;
      }
      leaf ip {
        description
          "IP";
        type empty;
      }
      leaf ipinip {
        description
          "IP in IP (encapsulation";
        type empty;
      }
      leaf ipsec {
        description
          "IP Security Protocol (ESP/AH";
        type empty;
      }
      leaf ipv6 {
        description
          "IPV6";
        type empty;
      }
      leaf ipx {
        description
          "Novell IPX";
        type empty;
      }
      leaf irc {
        type empty;
        description
          "Internet Relay Chat";
      }
      container kazaa2 {
        description
          "Kazaa Version 2";
        presence "enable kazaa version 2 matching";
        leaf file-transfer {
          description
            "File transfer stream";
          type string;
        }
      }
      leaf kerberos {
        description
          "Kerberos";
        type empty;
      }
      leaf l2tp {
        description
          "L2F/L2TP tunnel";
        type empty;
      }
      leaf ldap {
        description
          "Lightweight Directory Access Protocol";
        type empty;
      }
      leaf llc2 {
        description
          "llc2";
        type empty;
      }
      leaf mgcp {
        description
          "Media Gateway Control Protocol";
        type empty;
      }
      container napster {
        description
          "Napster Traffic";
        presence "enable napster matching";
        leaf non-std {
          description
            "Non-standard port advertizements";
          type empty;
        }
      }
      leaf netbios {
        description
          "NetBIOS";
        type empty;
      }
      leaf netshow {
        description
          "Microsoft Netshow";
        type empty;
      }
      leaf nfs {
        description
          "Network File System";
        type empty;
      }
      leaf nntp {
        description
          "Network News Transfer Protocol";
        type empty;
      }
      leaf notes {
        description
          "Lotus Notes(R";
        type empty;
      }
      leaf novadigm {
        description
          "Novadigm EDM";
        type empty;
      }
      leaf ntp {
        description
          "Network Time Protocol";
        type empty;
      }
      leaf ospf {
        description
          "Open Shortest Path First";
        type empty;
      }
      leaf pad {
        description
          "PAD links";
        type empty;
      }
      leaf pcanywhere {
        description
          "Symantec pcANYWHERE";
        type empty;
      }
      leaf pop3 {
        description
          "Post Office Protocol";
        type empty;
      }
      leaf pppoe {
        description
          "PPP over Ethernet";
        type empty;
      }
      leaf pptp {
        description
          "Point-to-Point Tunneling Protocol";
        type empty;
      }
      leaf printer {
        description
          "print spooler/lpd";
        type empty;
      }
      leaf qllc {
        description
          "qllc protocol";
        type empty;
      }
      leaf rcmd {
        description
          "BSD r-commands (rsh, rlogin, rexec";
        type empty;
      }
      leaf rip {
        description
          "Routing Information Protocol";
        type empty;
      }
      leaf rsrb {
        description
          "Remote Source-Route Bridging";
        type empty;
      }
      leaf rsvp {
        description
          "Resource Reservation Protocol";
        type empty;
      }
      leaf rtcp {
        description
          "Real Time Control Protocol";
        type empty;
      }
      container rtp {
        description
          "Real Time Protocol";
        presence "enable rtp matching";
        leaf audio {
          description
            "Match voice packets";
          type empty;
        }
        leaf payload-type {
          description
            "Match an explicit PT";
          type string;
        }
        leaf video {
          description
            "Match video packets";
          type empty;
        }
      }
      leaf rtsp {
        description
          "Real Time Streaming Protocol";
        type empty;
      }
      leaf secure-ftp {
        description
          "FTP over TLS/SSL";
        type empty;
      }
      leaf secure-http {
        description
          "Secured HTTP";
        type empty;
      }
      leaf secure-imap {
        description
          "Internet Message Access Protocol over TLS/SSL";
        type empty;
      }
      leaf secure-irc {
        description
          "Internet Relay Chat over TLS/SSL";
        type empty;
      }
      leaf secure-ldap {
        description
          "Lightweight Directory Access Protocol over TLS/SSL";
        type empty;
      }
      leaf secure-nntp {
        description
          "Network News Transfer Protocol over TLS/SSL";
        type empty;
      }
      leaf secure-pop3 {
        description
          "Post Office Protocol over TLS/SSL";
        type empty;
      }
      leaf secure-telnet {
        description
          "Telnet over TLS/SSL";
        type empty;
      }
      leaf sip {
        description
          "Session Initiation Protocol";
        type empty;
      }
      leaf skinny {
        description
          "Skinny Protocol";
        type empty;
      }
      container smtp {
        description
          "Simple Mail Transfer Protocol";
        presence "true";
        leaf extended {
          type empty;
        }
      }
      leaf snapshot {
        description
          "Snapshot routing support";
        type empty;
      }
      leaf snmp {
        description
          "Simple Network Management Protocol";
        type empty;
      }
      leaf socks {
        description
          "SOCKS";
        type empty;
      }
      leaf sqlnet {
        description
          "SQL*NET for Oracle";
        type empty;
      }
      leaf sqlserver {
        description
          "MS SQL Server";
        type empty;
      }
      leaf ssh {
        description
          "Secured Shell";
        type empty;
      }
      leaf streamwork {
        description
          "Xing Technology StreamWorks player";
        type empty;
      }
      leaf stun {
        description
          "Serial Tunnel";
        type empty;
      }
      leaf sunrpc {
        description
          "Sun RPC";
        type empty;
      }
      leaf syslog {
        description
          "System Logging Utility";
        type empty;
      }
      leaf telnet {
        description
          "Telnet";
        type empty;
      }
      leaf tftp {
        description
          "Trivial File Transfer Protocol";
        type empty;
      }
      leaf vdolive {
        description
          "VDOLive streaming video";
        type empty;
      }
      leaf vofr {
        description
          "voice over Frame Relay packets";
        type empty;
      }
      leaf winmx {
        description
          "WinMx file-sharing application";
        type empty;
      }
      leaf xwindows {
        description
          "X-Windows remote access";
        type empty;
      }
      container attribute {
        description
          "Attribute based protocol match";
        container business-relevance {
          description
            "Application business-relevance";
          leaf business-irrelevant {
            description
              "Undesirable business traffic";
            type empty;
          }
          leaf business-relevant {
            description
              "Business critical applications";
            type empty;
          }
          leaf default {
            description
              "Related business applications";
            type empty;
          }
        }
        container traffic-class {
          description
            "SRND class";
          leaf broadcast-video {
            description
              "Broadcast TV, live events, video surveillance";
            type empty;
          }
          leaf bulk-data {
            description
              "Non-interactive data applications";
            type empty;
          }
          leaf multimedia-conferencing {
            description
              "Desktop software multimedia collaboration applications";
            type empty;
          }
          leaf multimedia-streaming {
            description
              "Video-on-Demand (VoD) streaming video";
            type empty;
          }
          leaf network-control {
            description
              "Network control plane traffic";
            type empty;
          }
          leaf ops-admin-mgmt {
            description
              "Network operations, administration, and management traffic";
            type empty;
          }
          leaf real-time-interactive {
            description
              "High-definition interactive video applications";
            type empty;
          }
          leaf signaling {
            description
              "Signaling traffic that supports IP voice and video telephony";
            type empty;
          }
          leaf transactional-data {
            description
              "Interactive data applications";
            type empty;
          }
          leaf voip-telephony {
            description
              "VoIP telephony (bearer-only) traffic";
            type empty;
          }
        }
      }
    }
    leaf-list qos-group {
      description
        "Qos-group";
      type uint16 {
        range "0..99";
      }
    }
    container security-group {
      description
        "Security group";
      container destination {
        description
          "Destination security group";
        leaf tag {
          description
            "Security group tag";
          type uint16;
        }
      }
      container source {
        description
          "Source security group";
        leaf tag {
          description
            "Security group tag";
          type uint16;
        }
      }
    }
    container source-address {
      description
        "Source address";
      leaf-list mac {
        description
          "MAC address";
        type yang:mac-address;
      }
    }
    container vlan {
      description
        "VLANs to match";
      leaf-list inner {
        description
          "Inner tag to match";
        type union {
          type uint16 {
            range "1..4094";
          }
          type string;
        }
      }
      leaf-list value {
        type union {
          type uint16 {
            range "1..4094";
          }
          type string;
        }
      }
    }
  }

  grouping ncs_rpc_notif_class-map-appnav-match-grouping {
    leaf peer {
      description
        "APPNAV Peer Filter";
      when "../../type = 'appnav'" {
        tailf:xpath-root 3;
      }
      type string;
    }
  }

  grouping ncs_rpc_notif_class-map-appnav-not-match-grouping {
    leaf peer {
      description
        "APPNAV Peer Filter";
      when "../../../type = 'appnav'" {
        tailf:xpath-root 3;
      }
      type string;
    }
  }

  grouping ncs_rpc_notif_config-class-map-grouping {
    list class-map {
      description
        "configure qos class map";
      key "name";
      leaf name {
        type string;
      }
      leaf type {
        description
          "type of the class-map";
        type enumeration {
          enum "access-control";
          enum "appnav";
          enum "control";
          enum "inspect";
          enum "multicast-flows";
          enum "stack";
          enum "traffic";
        }
      }
      leaf subscriber {
        type empty;
      }
      leaf protocol {
        when "../type = 'inspect'" {
          tailf:xpath-root 3;
        }
        type enumeration {
          enum "aol";
          enum "edonkey";
          enum "fasttrack";
          enum "gnutella";
          enum "http";
          enum "imap";
          enum "kazaa2";
          enum "msnmsgr";
          enum "pop3";
          enum "smtp";
          enum "sunrpc";
          enum "ymsgr";
        }
      }
      leaf prematch {
        type enumeration {
          enum "match-all";
          enum "match-any";
          enum "match-none";
        }
        mandatory true;
      }
      leaf description {
        description
          "Class-Map description";
        type string;
      }
      container match {
        description
          "classification criteria";
        uses ncs_rpc_notif_class-map-match-grouping;
        uses ncs_rpc_notif_class-map-appnav-match-grouping;
        uses ncs_rpc_notif_class-map-control-filter-grouping;
        container not {
          description
            "Negate this match result";
          uses ncs_rpc_notif_class-map-match-grouping;
          uses ncs_rpc_notif_class-map-appnav-not-match-grouping;
        }
      }
      container no-match {
        description
          "no-match filter";
        uses ncs_rpc_notif_class-map-control-filter-grouping;
      }
    }
  }

  grouping ncs_rpc_notif_config-parameter-map-grouping {
    container timeout {
      description
        "timeout for the webauth session";
      when "/ios:native/ios:parameter-map/ios:type = 'webauth'" {
        tailf:xpath-root 3;
      }
      container init-state {
        description
          "init-state timeout";
        presence "true";
        leaf sec {
          description
            "WEBAUTH Timeout in Seconds";
          type uint32 {
            range "60..3932100";
          }
        }
      }
      container fin-wait {
        description
          "fin-wait timeout";
        leaf msec {
          description
            "WEBAUTH Timeout in milliseconds";
          type uint32 {
            range "1..2147483647";
          }
        }
      }
    }
    container watch-list {
      description
        "Watch List of webauth clients";
      when "/ios:native/ios:parameter-map/ios:type = 'webauth'" {
        tailf:xpath-root 3;
      }
      leaf enabled {
        description
          "Enable Watchlist";
        type empty;
      }
      leaf dynamic-expiry-timeout {
        description
          "dynamic_expiry_timeout";
        type uint32 {
          range "0..2147483";
        }
      }
      container add-item {
        description
          "Add item to Watch-list";
        leaf ipv4 {
          description
            "IPv4 Watch List Entry";
          type inet:ipv4-address;
        }
        leaf ipv6 {
          description
            "IPv6 Watch List Entry";
          type inet:ipv6-address;
        }
      }
    }
    container aggressive-aging {
      description
        "Aggressive Aging parameters";
      when "/ios:native/ios:parameter-map/ios:type = 'inspect-global'" {
        tailf:xpath-root 3;
      }
      container high {
        description
          "Specify the high watermark for aggressive-aging";
        choice absolute-percent {
          case absolute-case {
            container absolute {
              leaf value {
                type uint64 {
                  range "1..4294967295";
                }
              }
              leaf low {
                description
                  "Specify the low watermark for aggressive-aging";
                type uint64 {
                  range "1..4294967295";
                }
              }
            }
          }
          case percent-case {
            container percent {
              description
                "high watermark in percentage of max-incomplete value";
              leaf value {
                type uint8 {
                  range "1..100";
                }
              }
              leaf low_percent {
                description
                  "Specify the low watermark for aggressive-aging in percents";
                type uint8 {
                  range "1..100";
                }
              }
            }
          }
        }
      }
    }
    leaf alert {
      description
        "Turn on/off alert";
      type enumeration {
        enum "off";
        enum "on";
      }
    }
    leaf application-inspect {
      description
        "Turn on application inspection";
      type enumeration {
        enum "all";
        enum "dns";
        enum "exec";
        enum "ftp";
        enum "gtp";
        enum "h323";
        enum "http";
        enum "imap";
        enum "login";
        enum "msrpc";
        enum "netbios";
        enum "pop3";
        enum "rtsp";
        enum "shell";
        enum "sip";
        enum "skinny";
        enum "smtp";
        enum "sunrpc";
        enum "tftp";
      }
    }
    leaf audit-trail {
      description
        "Turn on/off audit trail";
      when "/ios:native/ios:parameter-map/ios:type = 'inspect'" {
        tailf:xpath-root 3;
      }
      type enumeration {
        enum "off";
        enum "on";
      }
    }
    leaf dns-timeout {
      description
        "Specify timeout for DNS";
      when "/ios:native/ios:parameter-map/ios:type = 'inspect'" {
        tailf:xpath-root 3;
      }
      type uint32 {
        range "1..2147483";
      }
    }
    container global {
      description
        "cws_tunnel global parameter-map";
      leaf fail-open {
        description
          "Allow traffic to go in clear if CWS Towers are unreachable";
        when "/ios:native/ios:parameter-map/ios:type = 'cws-tunnel'" {
          tailf:xpath-root 3;
        }
        type empty;
      }
      container license {
        description
          "License Key";
        when "/ios:native/ios:parameter-map/ios:type = 'cws-tunnel'" {
          tailf:xpath-root 3;
        }
        container Unencypted {
          description
            "Unencrypted License";
          leaf Hex-string {
            description
              "32 char non encrypted hex key";
            type string;
          }
        }
        container Encrypted {
          description
            "Encrypted License";
          leaf Hex-string {
            description
              "66 char encrypted hex key";
            type string;
          }
        }
      }
      leaf logging {
        description
          "CWS syslogs";
        type empty;
      }
      container primary {
        description
          "Primary tower";
        when "/ios:native/ios:parameter-map/ios:type = 'cws-tunnel'" {
          tailf:xpath-root 3;
        }
        presence "true";
        container tower {
          description
            "Tower configuration for CWS";
          leaf ipv4 {
            description
              "IPv4 address of the tower";
            type inet:ipv4-address;
          }
          leaf name {
            description
              "Fully Qualified Domain Name of tower";
            type string;
          }
        }
      }
      leaf redirect-list {
        description
          "Set access-list for reverse route from CWS Tower
           Standard IP access-list number <1-199>
           Standard IP access-list number (expanded range) <1300-2699>";
        when "/ios:native/ios:parameter-map/ios:type = 'cws-tunnel'" {
          tailf:xpath-root 3;
        }
        type union {
          type uint16 {
            range "1..199";
          }
          type uint16 {
            range "1300..2699";
          }
        }
      }
      container secondary {
        description
          "Secondary tower";
        when "/ios:native/ios:parameter-map/ios:type = 'cws-tunnel'" {
          tailf:xpath-root 3;
        }
        presence "true";
        container tower {
          description
            "Tower configuration for CWS";
          leaf ipv4 {
            description
              "IPv4 address of the tower";
            type inet:ipv4-address;
          }
          leaf name {
            description
              "Fully Qualified Domain Name of tower";
            type string;
          }
        }
      }
      container whitelist {
        description
          "Disable redirection to CWS
           Access list (standard) <1-199>
           Access list (extended) <1300-2699>
           Access list name";
        presence "true";
        container acl {
          description
            "Access list";
          leaf acl-number {
            type union {
              type uint16 {
                range "1..199";
              }
              type uint16 {
                range "1300..2699";
              }
            }
          }
          leaf name {
            description
              "Access list name";
            type string;
          }
        }
        container domain-name {
          description
            "Domain name based Whitelist";
          leaf regex {
            description
              "Domain name regex parameter map";
            type string;
          }
        }
        container download {
          description
            "whitelist download command";
          presence "true";
          leaf interval {
            description
              "Download interval in minutes";
            type uint16 {
              range "5..10080";
            }
          }
        }
      }
    }
    container icmp {
      description
        "Config timeout values for icmp";
      when "/ios:native/ios:parameter-map/ios:type = 'inspect'" {
        tailf:xpath-root 3;
      }
      leaf idle-time {
        description
          "Specify timeout for icmp";
        type uint32 {
          range "1..2147483";
        }
      }
    }
    container lisp {
      description
        "Turn on LISP options";
      leaf inner-packet-inspection {
        description
          "inner-packet-inspection";
        type empty;
      }
    }
    container log {
      description
        "Configure inspect logging parameters";
      leaf dropped-packets {
        description
          "Log dropped packets";
        type empty;
      }
      container flow-export {
        description
          "Configure inspect external logging parameters";
        container template {
          description
            "Configure record template parameters";
          leaf timeout-rate {
            description
              "Rate to resend the template in seconds";
            type uint32 {
              range "0..65535";
            }
          }
        }
        container v9 {
          description
            "Netflow version 9";
          container udp {
            description
              "Use UDP to export records";
            container destination {
              description
                "Specify the flow-export destination";
              leaf dst-ip {
                type inet:ipv4-address;
              }
              leaf dst-port {
                type uint16;
              }
            }
          }
        }
      }
    }
    leaf max-destination {
      description
        "config maximum destination";
      when "/ios:native/ios:parameter-map/ios:type = 'inspect-zone'" {
        tailf:xpath-root 3;
      }
      type uint32 {
        range "1..4294967295";
      }
    }
    container max-incomplete {
      description
        "Specify maximum number of incomplete connections before clamping";
      leaf high {
        description
          "Specify high-watermark for clamping";
        type uint32 {
          range "1..2147483647";
        }
      }
      leaf low {
        description
          "Specify low-watermark for clamping";
        type uint32 {
          range "1..2147483647";
        }
      }
    }
    container one-minute {
      description
        "Specify one-minute-sample watermarks for clamping";
      when "/ios:native/ios:parameter-map/ios:type = 'inspect'" {
        tailf:xpath-root 3;
      }
      leaf high {
        description
          "Specify high-watermark for clamping";
        type uint32 {
          range "1..2147483647";
        }
      }
      leaf low {
        description
          "Specify low-watermark for clamping";
        type uint32 {
          range "1..2147483647";
        }
      }
    }
    container sessions {
      description
        "Maximum number of inspect sessions";
      when "/ios:native/ios:parameter-map/ios:type = 'inspect'" {
        tailf:xpath-root 3;
      }
      leaf maximum {
        description
          "Maximum sessions";
        type uint32 {
          range "1..2147483647";
        }
      }
      container queue {
        description
          "queue";
        leaf max-threshold {
          type uint16 {
            range "0..65535";
          }
        }
        leaf min-threshold {
          type uint16 {
            range "0..65535";
          }
        }
      }
    }
    choice tcp-ins {
      container tcp-inspect {
        when "/ios:native/ios:parameter-map/ios:type = 'inspect'" {
          tailf:xpath-root 3;
        }
        container tcp {
          description
            "Config timeout values for tcp connections";
          when "/ios:native/ios:parameter-map/ios:type = 'inspect'" {
            tailf:xpath-root 3;
          }
          leaf finwait-time {
            description
              "Specify timeout for TCP connections after a FIN";
            type uint32 {
              range "1..2147483";
            }
          }
          leaf idle-time {
            description
              "Specify idle timeout for tcp connections";
            type uint32 {
              range "1..2147483";
            }
          }
          container max-incomplete {
            description
              "Specify max half-open connection per host";
            leaf host {
              description
                "Specify max half-open connection per host";
              type uint32 {
                range "1..4294967295";
              }
            }
          }
          leaf synwait-time {
            description
              "Specify timeout for TCP connections after a SYN and no";
            type uint32 {
              range "1..2147483";
            }
          }
        }
      }
      container tcp-inspect-zone {
        when "/ios:native/ios:parameter-map/ios:type = 'inspect-zone'" {
          tailf:xpath-root 3;
        }
        container tcp {
          description
            "Configure tcp syn-flood per-destination rate";
          container syn-flood {
            description
              "maximum syn packet";
            container rate {
              description
                "maximum syn packet rate";
              leaf per-destination {
                description
                  "per destination
                   maximum rate of TCP SYN packets";
                type uint32 {
                  range "1..1000000000";
                }
              }
            }
          }
        }
      }
    }
    container threat-detection {
      description
        "Configure Threat Detection";
      when "/ios:native/ios:parameter-map/ios:type = 'inspect-zone'" {
        tailf:xpath-root 3;
      }
      leaf basic-threat {
        description
          "Enable Threat Detection";
        type empty;
      }
      container rate {
        description
          "Configure Threat Detection rate";
        container fw-drop {
          description
            "Configure Threat Detection rate for firewall drop events";
          leaf average-time-frame {
            description
              "Configure Threat Detection average time frame";
            type uint32 {
              range "600..3600";
            }
          }
          leaf average-threshold {
            description
              "Configure Threat Detection average threshold";
            type uint64 {
              range "1..4294967295";
            }
          }
          leaf burst-threshold {
            description
              " Configure Threat Detection burst threshold";
            type uint64 {
              range "1..1000000000";
            }
          }
        }
        container inspect-drop {
          description
            "Configure Threat Detection rate for firewall inspection based drop events";
          leaf average-time-frame {
            description
              "Configure Threat Detection average time frame";
            type uint32 {
              range "600..3600";
            }
          }
          leaf average-threshold {
            description
              "Configure Threat Detection average threshold";
            type uint64 {
              range "1..4294967295";
            }
          }
          leaf burst-threshold {
            description
              " Configure Threat Detection burst threshold";
            type uint64 {
              range "1..1000000000";
            }
          }
        }
        container syn-attack {
          description
            "Configure Threat Detection rate for syn attack events";
          leaf average-time-frame {
            description
              "Configure Threat Detection average time frame";
            type uint32 {
              range "600..3600";
            }
          }
          leaf average-threshold {
            description
              "Configure Threat Detection average threshold";
            type uint64 {
              range "1..4294967295";
            }
          }
          leaf burst-threshold {
            description
              " Configure Threat Detection burst threshold";
            type uint64 {
              range "1..1000000000";
            }
          }
        }
      }
    }
    container udp {
      description
        "Config timeout values for udp flows";
      when "/ios:native/ios:parameter-map/ios:type = 'inspect'" {
        tailf:xpath-root 3;
      }
      leaf idle-time {
        description
          "Specify idle timeout for udp";
        type uint32 {
          range "1..2147483";
        }
      }
    }
    container vrf {
      description
        "vrf binding with parameter map";
      leaf name {
        type string;
      }
      leaf inspect {
        description
          "vrf binding with parameter map";
        type string;
      }
    }
    leaf zone-mismatch {
      description
        "Config zone-mismatch option";
      type enumeration {
        enum "drop";
      }
    }
  }

  grouping ncs_rpc_notif_config-service-policy-direction-grouping {
    leaf input {
      description
        "Assign policy-map to the input of an interface";
      type string;
    }
    leaf output {
      description
        "Assign policy-map to the output of an interface";
      type string;
    }
  }

  grouping ncs_rpc_notif_config-service-policy-grouping {
    container service-policy {
      uses ncs_rpc_notif_config-service-policy-direction-grouping;
    }
  }

  grouping ncs_rpc_notif_config-interface-service-policy-grouping {
    container service-policy {
      description
        "Configure QoS Service Policy";
      leaf history {
        description
          "Keep history of QoS metrics";
        type empty;
      }
      uses ncs_rpc_notif_config-service-policy-direction-grouping;
      container type {
        description
          "Configure CPL Service Policy";
        container control {
          leaf subscriber {
            type string;
          }
        }
        container performance-monitor {
          description
            "Configure media monitor service-policy type";
          leaf direction {
            type enumeration {
              enum "input";
              enum "output";
            }
          }
          leaf name {
            type string;
          }
        }
        container service-chain {
          description
            "Configure Service-chain Service Policy";
          container input {
            description
              "Assign policy-map to the input of an interface";
            leaf name {
              type string;
            }
          }
          container output {
            description
              "Assign policy-map to the output of an interface";
            leaf name {
              type string;
            }
          }
        }
      }
    }
  }

  grouping live_ncs_police-action-transmit-grouping {
    leaf transmit {
      description
        "transmit packet";
      type empty;
    }
  }

  grouping live_ncs_police-action-drop-grouping {
    leaf drop {
      description
        "drop packet";
      type empty;
    }
  }

  grouping live_ncs_police-conform-action-grouping {
    container conform-set-clp-transmit {
      container conform-action {
        description
          "action when rate is less than conform burst";
        leaf set-clp-transmit {
          description
            "set atm clp and send it";
          type empty;
        }
      }
    }
    container conform-set-cos-transmit {
      container conform-action {
        description
          "action when rate is less than conform burst";
        leaf set-cos-transmit {
          description
            "rewrite packet cos and send it";
          type ios-types:cos_value-type;
        }
      }
    }
    container conform-set-cos-transmit-table {
      container conform-action {
        description
          "action when rate is less than conform burst";
        leaf set-cos-transmit {
          description
            "rewrite packet cos and send it";
          type ios-types:cos_value-type;
        }
        leaf table {
          description
            "Specify table-map";
          type leafref {
            path "/ncs:devices/ncs:device/ncs:live-status/ios:native/ios:table-map/ios:name" {
              tailf:xpath-root 3;
            }
          }
        }
      }
    }
    container conform-set-discard-class-transmit {
      container conform-action {
        description
          "action when rate is less than conform burst";
        leaf set-discard-class-transmit {
          description
            "set discard-class and send it";
          type uint8 {
            range "0..7";
          }
        }
      }
    }
    container conform-set-dscp-transmit {
      container conform-action {
        description
          "action when rate is less than conform burst";
        leaf set-dscp-transmit {
          description
            "set dscp and send it";
          type ios-types:dscp-type;
        }
      }
    }
    container conform-set-dscp-transmit-table {
      container conform-action {
        description
          "action when rate is less than conform burst";
        leaf set-dscp-transmit {
          description
            "set dscp and send it";
          type ios-types:dscp-type;
        }
        leaf table {
          description
            "Specify table-map";
          type leafref {
            path "/ncs:devices/ncs:device/ncs:live-status/ios:native/ios:table-map/ios:name" {
              tailf:xpath-root 3;
            }
          }
        }
      }
    }
    container conform-set-frde-transmit {
      container conform-action {
        description
          "action when rate is less than conform burst";
        leaf set-frde-transmit {
          description
            "set FR DE and send it";
          type empty;
        }
      }
    }
    container conform-set-mpls-exp-imposition-transmit {
      container conform-action {
        description
          "action when rate is less than conform burst";
        leaf set-mpls-exp-imposition-transmit {
          description
            "set exp at tag imposition and send it";
          type ios-types:exp_value-type;
        }
      }
    }
    container conform-set-mpls-exp-imposition-transmit-table {
      container conform-action {
        description
          "action when rate is less than conform burst";
        leaf set-mpls-exp-imposition-transmit {
          description
            "set exp at tag imposition and send it";
          type ios-types:exp_value-type;
        }
        leaf table {
          description
            "Specify table-map";
          type leafref {
            path "/ncs:devices/ncs:device/ncs:live-status/ios:native/ios:table-map/ios:name" {
              tailf:xpath-root 3;
            }
          }
        }
      }
    }
    container conform-set-mpls-exp-topmost-transmit {
      container conform-action {
        description
          "action when rate is less than conform burst";
        leaf set-mpls-exp-topmost-transmit {
          description
            "set exp on topmost label and send it";
          type ios-types:exp_value-type;
        }
      }
    }
    container conform-set-mpls-exp-topmost-transmit-table {
      container conform-action {
        description
          "action when rate is less than conform burst";
        leaf set-mpls-exp-topmost-transmit {
          description
            "set exp on topmost label and send it";
          type ios-types:exp_value-type;
        }
        leaf table {
          description
            "Specify table-map";
          type leafref {
            path "/ncs:devices/ncs:device/ncs:live-status/ios:native/ios:table-map/ios:name" {
              tailf:xpath-root 3;
            }
          }
        }
      }
    }
    container conform-set-prec-transmit {
      container conform-action {
        description
          "action when rate is less than conform burst";
        leaf set-prec-transmit {
          description
            "rewrite packet precedence and send it";
          type ios-types:prec_value-type;
        }
      }
    }
    container conform-set-prec-transmit-table {
      container conform-action {
        description
          "action when rate is less than conform burst";
        leaf set-prec-transmit {
          description
            "rewrite packet precedence and send it";
          type ios-types:prec_value-type;
        }
        leaf table {
          description
            "Specify table-map";
          type leafref {
            path "/ncs:devices/ncs:device/ncs:live-status/ios:native/ios:table-map/ios:name" {
              tailf:xpath-root 3;
            }
          }
        }
      }
    }
    container conform-set-qos-transmit {
      container conform-action {
        description
          "action when rate is less than conform burst";
        leaf set-qos-transmit {
          description
            "set qos-group and send it";
          type ios-types:qos_value-type;
        }
      }
    }
    container conform-set-qos-transmit-table {
      container conform-action {
        description
          "action when rate is less than conform burst";
        leaf set-qos-transmit {
          description
            "set qos-group and send it";
          type ios-types:qos_value-type;
        }
        leaf table {
          description
            "Specify table-map";
          type leafref {
            path "/ncs:devices/ncs:device/ncs:live-status/ios:native/ios:table-map/ios:name" {
              tailf:xpath-root 3;
            }
          }
        }
      }
    }
    container conform-transmit {
      container conform-action {
        description
          "action when rate is less than conform burst";
        uses live_ncs_police-action-transmit-grouping;
      }
    }
    container conform-drop {
      container conform-action {
        description
          "action when rate is less than conform burst";
        uses live_ncs_police-action-drop-grouping;
      }
    }
  }

  grouping live_ncs_police-exceed-action-grouping {
    container exceed-dscp {
      container exceed-action {
        description
          "action when rate is within conform and conform + exceed burst";
        leaf dscp {
          type ios-types:dscp-type;
        }
      }
    }
    container exceed-set-clp-transmit {
      container exceed-action {
        description
          "action when rate is within conform and conform + exceed burst";
        leaf set-clp-transmit {
          description
            "set atm clp and send it";
          type empty;
        }
      }
    }
    container exceed-set-cos-transmit {
      container exceed-action {
        description
          "action when rate is within conform and conform + exceed burst";
        leaf set-cos-transmit {
          description
            "rewrite packet cos and send it";
          type ios-types:cos_value-type;
        }
        leaf table {
          description
            "Specify table-map";
          type leafref {
            path "/ncs:devices/ncs:device/ncs:live-status/ios:native/ios:table-map/ios:name" {
              tailf:xpath-root 3;
            }
          }
        }
      }
    }
    container exceed-set-discard-class-transmit {
      container exceed-action {
        description
          "action when rate is within conform and conform + exceed burst";
        leaf set-discard-class-transmit {
          description
            "set discard-class and send it";
          type uint8 {
            range "0..7";
          }
        }
      }
    }
    container exceed-set-dscp-transmit {
      container exceed-action {
        description
          "action when rate is within conform and conform + exceed burst";
        container set-dscp-transmit {
          container dscp {
            leaf table {
              type enumeration {
                enum "policed-dscp";
              }
            }
          }
        }
      }
    }
    container exceed-set-dscp-transmit-table {
      container exceed-action {
        description
          "action when rate is within conform and conform + exceed burst";
        leaf set-dscp-transmit {
          description
            "set dscp and send it";
          type ios-types:dscp-type;
        }
        leaf table {
          description
            "Specify table-map";
          type leafref {
            path "/ncs:devices/ncs:device/ncs:live-status/ios:native/ios:table-map/ios:name" {
              tailf:xpath-root 3;
            }
          }
        }
      }
    }
    container exceed-set-frde-transmit {
      container exceed-action {
        description
          "action when rate is within conform and conform + exceed burst";
        leaf set-frde-transmit {
          description
            "set FR DE and send it";
          type empty;
        }
      }
    }
    container exceed-set-mpls-exp-imposition-transmit {
      container exceed-action {
        description
          "action when rate is within conform and conform + exceed burst";
        leaf set-mpls-exp-imposition-transmit {
          description
            "set exp at tag imposition and send it";
          type ios-types:exp_value-type;
        }
      }
    }
    container exceed-set-mpls-exp-topmost-transmit {
      container exceed-action {
        description
          "action when rate is within conform and conform + exceed burst";
        leaf set-mpls-exp-topmost-transmit {
          description
            "set exp on topmost label and send it";
          type ios-types:exp_value-type;
        }
      }
    }
    container exceed-set-prec-transmit {
      container exceed-action {
        description
          "action when rate is within conform and conform + exceed burst";
        leaf set-prec-transmit {
          description
            "rewrite packet precedence and send it";
          type ios-types:prec_value-type;
        }
        leaf table {
          description
            "Specify table-map";
          type leafref {
            path "/ncs:devices/ncs:device/ncs:live-status/ios:native/ios:table-map/ios:name" {
              tailf:xpath-root 3;
            }
          }
        }
      }
    }
    container exceed-set-qos-transmit {
      container exceed-action {
        description
          "action when rate is within conform and conform + exceed burst";
        leaf set-qos-transmit {
          description
            "set qos-group and send it";
          type ios-types:qos_value-type;
        }
      }
    }
    container exceed-transmit {
      container exceed-action {
        description
          "action when rate is within conform and conform + exceed burst";
        uses live_ncs_police-action-transmit-grouping;
      }
    }
    container exceed-drop {
      container exceed-action {
        description
          "action when rate is within conform and conform + exceed burst";
        uses live_ncs_police-action-drop-grouping;
      }
    }
  }

  grouping live_ncs_police-violate-action-grouping {
    container violate-set-clp-transmit {
      container violate-action {
        description
          "action when rate is greater than conform + exceed burst";
        leaf set-clp-transmit {
          description
            "set atm clp and send it";
          type empty;
        }
      }
    }
    container violate-set-cos-transmit {
      container violate-action {
        description
          "action when rate is greater than conform + exceed burst";
        leaf set-cos-transmit {
          description
            "rewrite packet cos and send it";
          type ios-types:cos_value-type;
        }
        leaf table {
          description
            "Specify table-map";
          type leafref {
            path "/ncs:devices/ncs:device/ncs:live-status/ios:native/ios:table-map/ios:name" {
              tailf:xpath-root 3;
            }
          }
        }
      }
    }
    container violate-set-discard-class-transmit {
      container violate-action {
        description
          "action when rate is greater than conform + exceed burst";
        leaf set-discard-class-transmit {
          description
            "set discard-class and send it";
          type uint8 {
            range "0..7";
          }
        }
      }
    }
    container violate-set-dscp-transmit {
      container violate-action {
        description
          "action when rate is greater than conform + exceed burst";
        leaf set-dscp-transmit {
          description
            "set dscp and send it";
          type ios-types:dscp-type;
        }
        leaf table {
          description
            "Specify table-map";
          type leafref {
            path "/ncs:devices/ncs:device/ncs:live-status/ios:native/ios:table-map/ios:name" {
              tailf:xpath-root 3;
            }
          }
        }
      }
    }
    container violate-set-frde-transmit {
      container violate-action {
        description
          "action when rate is greater than conform + exceed burst";
        leaf set-frde-transmit {
          description
            "set FR DE and send it";
          type empty;
        }
      }
    }
    container violate-set-mpls-exp-imposition-transmit {
      container violate-action {
        description
          "action when rate is greater than conform + exceed burst";
        leaf set-mpls-exp-imposition-transmit {
          description
            "set exp at tag imposition and send it";
          type ios-types:exp_value-type;
        }
      }
    }
    container violate-set-mpls-exp-topmost-transmit {
      container violate-action {
        description
          "action when rate is greater than conform + exceed burst";
        leaf set-mpls-exp-topmost-transmit {
          description
            "set exp on topmost label and send it";
          type ios-types:exp_value-type;
        }
      }
    }
    container violate-set-prec-transmit {
      container violate-action {
        description
          "action when rate is greater than conform + exceed burst";
        leaf set-prec-transmit {
          description
            "rewrite packet precedence and send it";
          type ios-types:prec_value-type;
        }
        leaf table {
          description
            "Specify table-map";
          type leafref {
            path "/ncs:devices/ncs:device/ncs:live-status/ios:native/ios:table-map/ios:name" {
              tailf:xpath-root 3;
            }
          }
        }
      }
    }
    container violate-set-qos-transmit {
      container violate-action {
        description
          "action when rate is greater than conform + exceed burst";
        leaf set-qos-transmit {
          description
            "set qos-group and send it";
          type ios-types:qos_value-type;
        }
      }
    }
    container violate-transmit {
      container violate-action {
        description
          "action when rate is greater than conform + exceed burst";
        uses live_ncs_police-action-transmit-grouping;
      }
    }
    container violate-drop {
      container violate-action {
        description
          "action when rate is greater than conform + exceed burst";
        uses live_ncs_police-action-drop-grouping;
      }
    }
  }

  grouping live_ncs_police-action-grouping {
    container actions {
      uses live_ncs_police-conform-action-grouping;
      uses live_ncs_police-exceed-action-grouping;
      uses live_ncs_police-violate-action-grouping;
    }
  }

  grouping live_ncs_random-detect-grouping {
    leaf min-threshold {
      type uint16 {
        range "1..4096";
      }
    }
    leaf max-threshold {
      type uint16 {
        range "1..4096";
      }
    }
    leaf denominator {
      type uint32 {
        range "1..65535";
      }
    }
  }

  grouping live_ncs_config-policy-map-grouping {
    list policy-map {
      description
        "Configure QoS Policy Map";
      key "name";
      leaf name {
        type string;
      }
      leaf type {
        description
          "type of the policy-map";
        type enumeration {
          enum "access-control";
          enum "appnav";
          enum "inspect";
          enum "control";
          enum "packet-service";
          enum "performance-monitor";
          enum "service";
          enum "service-chain";
        }
      }
      leaf subscriber {
        type empty;
      }
      leaf protocol {
        // NCS drop when statement
        type enumeration {
          enum "http";
          enum "im";
          enum "imap";
          enum "p2p";
          enum "pop3";
          enum "smtp";
          enum "sunrpc";
        }
      }
      list event {
        description
          "The event type this control class-map triggers upon";
        key "event-type";
        leaf event-type {
          type enumeration {
            enum "aaa-available";
            enum "absolute-timeout";
            enum "agent-found";
            enum "authentication-failure";
            enum "authentication-success";
            enum "authorization-failure";
            enum "authorization-success";
            enum "identity-update";
            enum "inactivity-timeout";
            enum "remote-authentication-failure";
            enum "remote-authentication-success";
            enum "session-disconnected";
            enum "session-started";
            enum "tag-added";
            enum "tag-removed";
            enum "template-activated";
            enum "template-activation-failed";
            enum "template-deactivated";
            enum "template-deactivation-failed";
            enum "timer-expiry";
            enum "violation";
          }
        }
        leaf match-type {
          type enumeration {
            enum "match-all";
            enum "match-first";
          }
        }
        list class-number {
          description
            "class number, 1 for 1st class, 2 for 2nd...";
          key "number";
          leaf number {
            type uint8 {
              range "1..254";
            }
          }
          leaf class {
            description
              "The class type this control policy-map triggers upon";
            type union {
              type enumeration {
                enum "always";
              }
              type string;
            }
          }
          leaf execution-type {
            type enumeration {
              enum "do-all";
              enum "do-until-failure";
              enum "do-until-success";
            }
          }
          list action-number {
            description
              "action number, 1 for 1st class, 2 for 2nd...";
            key "number";
            leaf number {
              type uint8 {
                range "1..254";
              }
            }
            container terminate {
              description
                "terminate auth method";
              leaf dot1x {
                description
                  "dot1x method";
                type empty;
              }
              leaf mab {
                description
                  "mab method";
                type empty;
              }
              leaf webauth {
                description
                  "webauth method";
                type empty;
              }
            }
            leaf clear-session {
              description
                "clears an active session";
              type empty;
            }
            container resume {
              description
                "resume operation to be specified";
              leaf reauthentication {
                description
                  "resume reauthentication";
                type empty;
              }
            }
            leaf authentication-restart {
              description
                "restarts the auth sequence after the specified number of sec";
              type uint16 {
                range "1..65535";
              }
            }
            container pause {
              description
                "pause operation to be specified";
              leaf reauthentication {
                description
                  "pause reauthentication";
                type empty;
              }
            }
            leaf authorize {
              description
                "authorize session";
              type empty;
            }
            container activate {
              description
                "activate template or policy";
              leaf service-template {
                description
                  "activate service template";
                type string;
              }
            }
            container authenticate {
              description
                "authenticate a session";
              container using {
                description
                  "authenticate a session";
                leaf method {
                  type enumeration {
                    enum "dot1x";
                    enum "mab";
                    enum "webauth";
                  }
                }
                leaf both {
                  description
                    "Enabling Dot1x Authenticator & Supplicant";
                  type empty;
                }
                leaf retries {
                  description
                    "Number of times to retry failed authentications";
                  type uint8 {
                    range "1..5";
                  }
                }
                leaf retry-time {
                  description
                    "Time interval between retries";
                  type uint16 {
                    range "0..65535";
                  }
                }
                leaf priority {
                  description
                    "Method priority";
                  type uint8 {
                    range "1..254";
                  }
                }
              }
            }
          }
        }
      }
      list class {
        description
          "policy criteria";
        key "name";
        leaf name {
          type class-name-type;
        }
        leaf type {
          description
            "type of the class-map";
          type enumeration {
            enum "inspect";
          }
        }
        leaf insert-before {
          description
            "Insert the class before a specified class";
          // NCS drop when statement
          type string;
        }
        container appnav-policy {
          // NCS drop when statement
          list distribute {
            description
              "Distribute action";
            key "service-node-group";
            leaf service-node-group {
              description
                "Distribute to service-node-group";
              type string;
            }
            leaf insert-before {
              description
                "Insert before specific node";
              type string;
            }
          }
          leaf monitor-load {
            description
              "Monitor AO";
            // NCS drop when statement
            type enumeration {
              enum "MS-port-mapper";
              enum "cifs";
              enum "http";
              enum "ica";
              enum "mapi";
              enum "nfs";
              enum "ssl";
              enum "video";
            }
          }
          leaf pass-through {
            description
              "pass-through action";
            type empty;
          }
        }
        container policy {
          // NCS drop when statement
          leaf action {
            type enumeration {
              enum "cxsc";
              enum "drop";
              enum "inspect";
              enum "pass";
              enum "service-policy";
            }
          }
          leaf log {
            description
              "Send logging message for drop or pass";
            // NCS drop when statement
            type empty;
          }
          leaf parameter-map {
            // NCS drop when statement
            type union {
              type string;
              type enumeration {
                enum "global";
                enum "gtp";
              }
            }
          }
          container dpi {
            // NCS drop when statement
            leaf type {
              type enumeration {
                enum "gtpv0";
                enum "gtpv1";
                enum "imap";
                enum "pop3";
                enum "smtp";
                enum "sunrpc";
              }
            }
            leaf policy-map {
              type string;
            }
          }
        }
        container pm-policy {
          // NCS drop when statement
          container flow {
            description
              "Flow subcommands";
            leaf monitor {
              description
                "Apply a Flow Monitor";
              type string;
            }
          }
          container monitor {
            description
              "Monitor related parameters";
            container metric {
              description
                "Monitor metric";
              container rtp {
                description
                  "RTP metrics parameters";
                list clock-rate {
                  description
                    "RTP timestamp field's sampling frequency";
                  key "number";
                  leaf number {
                    type union {
                      type uint8 {
                        range "0..127";
                      }
                      type enumeration {
                        enum "celb";
                        enum "cn";
                        enum "default";
                        enum "dvi4";
                        enum "dvi4-2";
                        enum "dvi4-3";
                        enum "dvi4-4";
                        enum "g722";
                        enum "g723";
                        enum "g728";
                        enum "g729";
                        enum "gsm";
                        enum "h261";
                        enum "h263";
                        enum "jpeg";
                        enum "l16";
                        enum "l16-2";
                        enum "lpc";
                        enum "mp2t";
                        enum "mpa";
                        enum "mpv";
                        enum "nv";
                        enum "pcma";
                        enum "pcmu";
                        enum "qcelp";
                      }
                    }
                  }
                  leaf frequency {
                    type uint32 {
                      range "1000..192000";
                    }
                  }
                }
              }
            }
          }
          list react {
            description
              "Configure threshold crossing actions";
            key "id";
            leaf id {
              type uint16;
            }
            leaf mode {
              type enumeration {
                enum "media-stop";
                enum "mrv";
                enum "rtp-jitter-average";
                enum "transport-packets-lost-rate";
              }
            }
            leaf description {
              description
                "Description for the instance";
              type string;
            }
            container action {
              description
                "Config react action";
              leaf snmp {
                description
                  "SNMP is notified of the event";
                type empty;
              }
              leaf syslog {
                description
                  "The threshold-crossing event is logged to syslog";
                type empty;
              }
            }
            container alarm {
              description
                "Config react alarm";
              leaf severity {
                description
                  "Alarm severity - default level none";
                type enumeration {
                  enum "alert";
                  enum "critical";
                  enum "emergency";
                  enum "error";
                  enum "info";
                }
              }
              container type {
                description
                  "Alarm raised type - for each flow or a group";
                leaf discrete {
                  description
                    "Alert for each flow within the class";
                  type empty;
                }
                container grouped {
                  description
                    "Alert if more than one flow cross the threshold";
                  leaf count {
                    description
                      "Number of flows in the group cross the threshold";
                    type uint16;
                  }
                  leaf percent {
                    description
                      "Percent of flows in the group cross the threshold";
                    type uint8 {
                      range "1..100";
                    }
                  }
                }
              }
            }
            container threshold {
              description
                "Config react threshold";
              container value {
                description
                  "Range of percentage loss that would trigger the alarm";
                leaf ge {
                  description
                    "greater and equal to";
                  type string;
                }
                leaf gt {
                  description
                    "greater than";
                  type string;
                }
                leaf le {
                  description
                    "less and equal to";
                  type string;
                }
                leaf lt {
                  description
                    "less than";
                  type string;
                }
                container range {
                  description
                    "threshold within the range of";
                  leaf low {
                    type string;
                  }
                  leaf high {
                    type string;
                  }
                }
              }
            }
          }
        }
        container inspect-police {
          // NCS drop when statement
          container police {
            description
              "Police";
            leaf rate {
              description
                "Specify police rate";
              type uint32 {
                range "8000..2000000000";
              }
            }
            leaf burst {
              description
                "Specify 'burst' parameter";
              type uint32 {
                range "1000..512000000";
              }
            }
          }
        }
        list action-list {
          key "action-type";
          ordered-by user;
          leaf action-type {
            type policy-action-type;
          }
          choice action-param {
            case bandwidth-case {
              container bandwidth {
                // NCS drop when statement
                leaf bits {
                  type uint32 {
                    range "8..2000000";
                  }
                }
                leaf percent {
                  description
                    "% of total Bandwidth";
                  type ios-types:percentage;
                }
                container remaining {
                  description
                    "% of the remaining bandwidth";
                  leaf rem-option {
                    type enumeration {
                      enum "percent";
                      enum "ratio";
                    }
                  }
                  leaf percent {
                    description
                      "% of the remaining bandwidth";
                    // NCS drop when statement
                    type ios-types:percentage;
                  }
                  leaf ratio {
                    description
                      "ratio for sharing excess bandwidth";
                    // NCS drop when statement
                    type uint16;
                  }
                  container account {
                    description
                      "Overhead Accounting";
                    // NCS drop when statement
                    leaf user-defined {
                      description
                        "Offset Size";
                      type int32 {
                        range "-1000000..1000000";
                      }
                    }
                  }
                }
              }
            }
            case compression-case {
              container compression {
                // NCS drop when statement
                container header {
                  description
                    "configure header compression";
                  presence "configure header compression";
                  leaf ip {
                    description
                      "configure ip header compression";
                    type enumeration {
                      enum "rtp";
                      enum "tcp";
                    }
                  }
                }
              }
            }
            case estimate-case {
              container estimate {
                // NCS drop when statement
                container bandwidth {
                  presence "bandwidth required to service this class";
                  description
                    "bandwidth required to service this class";
                  container delay-one-in {
                    description
                      "specify QoS target delay";
                    leaf doi {
                      type uint32 {
                        range "50..1000000";
                      }
                    }
                    leaf milliseconds {
                      type uint32 {
                        range "8..1000";
                      }
                    }
                  }
                  leaf drop-one-in {
                    description
                      "specify QoS target loss rate";
                    type uint32;
                  }
                }
              }
            }
            case forward-case {
              container forward {
                // NCS drop when statement
                leaf service-path {
                  description
                    "Service Path Entries";
                  type uint32 {
                    range "0..16777215";
                  }
                }
                leaf service-index {
                  description
                    "Service Index";
                  type uint8 {
                    range "2..255";
                  }
                }
              }
            }
            case fair-queue-case {
              container fair-queue {
                // NCS drop when statement
                leaf dynamic-queues {
                  type uint32 {
                    range "16|32|64|128|256|512|1024|2048|4096";
                  }
                }
                leaf queue-limit {
                  description
                    "per flow queue limit";
                  type uint16 {
                    range "1..32768";
                  }
                }
              }
            }
            case netflow-sampler-case {
              leaf netflow-sampler {
                // NCS drop when statement
                type string;
              }
            }
            case police-case {
              choice police-choice {
                case police-aggregate-case {
                  container police-aggregate {
                    container police {
                      // NCS drop when statement
                      leaf aggregate {
                        description
                          "Choose aggregate policer for current class";
                        type string;
                      }
                    }
                  }
                }
                case police-policy-map-case {
                  container police-policy-map {
                    container police {
                      // NCS drop when statement
                      leaf cir {
                        description
                          "Committed information rate";
                        type police-bps-type;
                      }
                      leaf bc {
                        description
                          "Conform burst";
                        type police-burst-type;
                      }
                      leaf be {
                        description
                          "Excess burst";
                        // NCS drop when statement
                        type police-burst-type;
                      }
                      leaf pir {
                        description
                          "Peak Information Rate";
                        type police-bps-type;
                      }
                      container pir-be {
                        // NCS drop when statement
                        leaf be {
                          description
                            "Excess burst";
                          type police-burst-type;
                        }
                      }
                      uses live_ncs_police-action-grouping;
                    }
                  }
                }
                case police-cir-percent-case {
                  container police-cir-percent {
                    container police {
                      // NCS drop when statement
                      container cir {
                        description
                          "Committed information rate";
                        container percent {
                          description
                            "% of interface bandwidth for Committed information rate";
                          leaf percentage {
                            type ios-types:percentage;
                          }
                          leaf bc {
                            description
                              "Conform burst";
                            type uint16;
                          }
                          container bc-ms {
                            // NCS drop when statement
                            leaf ms {
                              description
                                "Milli seconds";
                              type empty;
                            }
                          }
                          leaf be {
                            // NCS drop when statement
                            type uint16;
                          }
                          container be-ms {
                            // NCS drop when statement
                            leaf ms {
                              description
                                "Milli seconds";
                              type empty;
                            }
                          }
                          container pir {
                            description
                              "Peak Information Rate";
                            leaf percent {
                              description
                                "% of interface bandwidth for Peak Information Rate";
                              type ios-types:percentage;
                            }
                          }
                          container pir-be {
                            // NCS drop when statement
                            leaf be {
                              description
                                "Excess burst";
                              type uint16;
                            }
                          }
                          container pir-be-ms {
                            // NCS drop when statement
                            leaf ms {
                              description
                                "Milli seconds";
                              type empty;
                            }
                          }
                          uses live_ncs_police-action-grouping;
                        }
                      }
                    }
                  }
                }
                case police-rate-unit-case {
                  container police-rate-unit {
                    container police {
                      // NCS drop when statement
                      container rate {
                        description
                          "Specify police rate";
                        leaf units {
                          type uint64;
                        }
                        leaf xps {
                          type police-pps-bps-type;
                        }
                        container burst {
                          description
                            "Specify 'burst' parameter";
                          leaf burst-value {
                            type uint32;
                          }
                          leaf burst-type {
                            type police-packets-bytes-type;
                          }
                        }
                        container peak-rate {
                          description
                            "Specify peak rate";
                          leaf peak-rate-value {
                            type uint32 {
                              range "1..512000000";
                            }
                          }
                          leaf xps {
                            type police-pps-bps-type;
                          }
                        }
                        container peak-burst {
                          description
                            "Specify 'peak-burst' parameter for peak-rate";
                          leaf burst-value {
                            type uint32;
                          }
                          leaf burst-type {
                            type police-packets-bytes-type;
                          }
                        }
                        uses live_ncs_police-action-grouping;
                      }
                    }
                  }
                }
                case police-rate-percent-case {
                  container police-rate-percent {
                    container police {
                      // NCS drop when statement
                      container rate {
                        description
                          "Specify police rate";
                        container percent {
                          description
                            "% of interface bandwidth for rate";
                          leaf percentage {
                            type ios-types:percentage;
                          }
                          leaf burst {
                            description
                              "Specify 'burst' parameter";
                            type uint16;
                          }
                          leaf ms {
                            description
                              "Treat 'burst' value in milliseconds";
                            // NCS drop when statement
                            type empty;
                          }
                          container peak-rate {
                            description
                              "Specify peak rate";
                            leaf percent {
                              description
                                "% of interface bandwidth for peak-rate";
                              type ios-types:percentage;
                            }
                          }
                          leaf peak-burst {
                            description
                              "Specify 'peak-burst' parameter for 'peak-rate'";
                            type uint16;
                          }
                          container peak-burst-ms {
                            // NCS drop when statement
                            leaf ms {
                              description
                                "Milli seconds";
                              type empty;
                            }
                          }
                          uses live_ncs_police-action-grouping;
                        }
                      }
                    }
                  }
                }
                case police-rate-pdp-case {
                  container police-rate-pdp {
                    container police {
                      // NCS drop when statement
                      container rate {
                        description
                          "Specify police rate";
                        container pdp {
                          description
                            "% of interface bandwidth for rate";
                          leaf burst {
                            description
                              "Conform burst";
                            type police-burst-type;
                          }
                          leaf peak-rate {
                            description
                              "Specify peak rate";
                            type enumeration {
                              enum "pdp";
                            }
                          }
                          leaf peak-burst {
                            description
                              "Specify 'peak-burst' parameter for 'peak-rate'";
                            // NCS drop when statement
                            type police-burst-type;
                          }
                          uses live_ncs_police-action-grouping;
                        }
                      }
                    }
                  }
                }
                case police-target-bitrate-case {
                  container police-target-bitrate {
                    container police {
                      // NCS drop when statement
                      leaf bit-rate {
                        description
                          "Target bit rate (bits per second) (postfix k, m, g optional),decimal point allowed";
                        type uint64 {
                          range "8000..10000000000";
                        }
                      }
                      leaf confirm_burst-byte {
                        description
                          "Burst Byte";
                        type uint64 {
                          range "100..512000000";
                        }
                      }
                      leaf excess_burst-byte {
                        description
                          "Burst Byte";
                        type uint64 {
                          range "100..512000000";
                        }
                      }
                      leaf conform-action {
                        description
                          "action when rate is less than conform burst";
                        type empty;
                      }
                      leaf transmit {
                        description
                          "transmit packet";
                        type empty;
                      }
                      leaf exceed-action {
                        description
                          "action when rate is within conform and conform + exceed burst";
                        type empty;
                      }
                      leaf drop {
                        description
                          "drop packet";
                        type empty;
                      }
                      leaf set-dscp-transmit {
                        description
                          "set dscp and send it";
                        type empty;
                      }
                      leaf dscp {
                        description
                          "Set packet dscp from dscp";
                        type empty;
                      }
                      leaf table {
                        description
                          "Specify table-map";
                        type string;
                      }
                      container actions {
                        uses live_ncs_police-conform-action-grouping;
                        uses live_ncs_police-exceed-action-grouping;
                        uses live_ncs_police-violate-action-grouping;
                      }
                    }
                  }
                }
                case police-flow-case {
                  container police-flow {
                    container police {
                      // NCS drop when statement
                      container flow {
                        description
                          "police each flow";
                        leaf mask {
                          description
                            "flow mask to be used for policing";
                          type enumeration {
                            enum "dest-only";
                            enum "full-flow";
                            enum "src-only";
                          }
                        }
                        leaf bps {
                          type police-bps-type;
                        }
                        leaf burst-normal {
                          type police-burst-type;
                          // NCS drop when statement
                        }
                        uses live_ncs_police-action-grouping;
                      }
                    }
                  }
                }
                case police-catalyst-case {
                  container police-catalyst {
                    container police {
                      // NCS drop when statement
                      leaf bps-value {
                        type string;
                      }
                      leaf bps {
                        type empty;
                      }
                      leaf byte-value {
                        type string;
                      }
                      leaf byte {
                        type empty;
                      }
                      container actions {
                        uses live_ncs_police-conform-action-grouping;
                        uses live_ncs_police-exceed-action-grouping;
                        uses live_ncs_police-violate-action-grouping;
                      }
                    }
                  }
                }
                case police-switch-case {
                  container police-switch {
                    container police {
                      // NCS drop when statement
                      leaf cir {
                        type uint32 {
                          range "8000..1000000000";
                        }
                      }
                      leaf bc {
                        type uint32 {
                          range "8000..2000000";
                        }
                      }
                      leaf exceed-action {
                        description
                          "action when rate is exceeded";
                        type enumeration {
                          enum "drop";
                          enum "policed-dscp-transmit";
                        }
                      }
                    }
                  }
                }
              }
            }
            case priority-case {
              container priority {
                // NCS drop when statement
                leaf level {
                  description
                    "Multi-Level Priority Queue";
                  type uint8 {
                    range "1..2";
                  }
                }
                choice priority-type {
                  leaf kilo-bits {
                    type uint32 {
                      range "8..2000000";
                    }
                  }
                  leaf percent {
                    description
                      "% of total bandwidth";
                    type uint16 {
                      range "1..100";
                    }
                  }
                }
                leaf burst {
                  type uint32 {
                    range "32..64000000";
                  }
                }
              }
            }
            case queue-buffers-case {
              container queue-buffers {
                // NCS drop when statement
                leaf ratio {
                  description
                    "Relative buffer size for queue";
                  type uint8 {
                    range "0..100";
                  }
                }
              }
            }
            case queue-limit-case {
              container queue-limit {
                // NCS drop when statement
                leaf queue-limit-value {
                  type uint32 {
                    range "1..8192000";
                  }
                }
                leaf queue-limit-type {
                  type enumeration {
                    enum "bytes";
                    enum "ms";
                    enum "packets";
                    enum "us";
                  }
                }
              }
              container queue-limit-dscp {
                // NCS drop when statement
                list dscp {
                  description
                    "parameters for each dscp value";
                  key "dscp-val";
                  leaf dscp-val {
                    type ios-types:dscp-type;
                  }
                  leaf values {
                    description
                      "dscp values";
                    type empty;
                  }
                  leaf dscp-val1 {
                    type ios-types:dscp-type;
                  }
                  leaf percent {
                    description
                      "% of threshold";
                    type uint8 {
                      range "0..100";
                    }
                  }
                }
              }
            }
            case random-detect {
              container random-detect {
                // NCS drop when statement
                container aggregate {
                  description
                    "aggregate subclasses";
                  presence "true";
                  leaf minimum-thresh {
                    description
                      "minimum threshold for red aggregate";
                    type uint32 {
                      range "0..1000000";
                    }
                  }
                  leaf maximum-thresh {
                    description
                      "maximum threshold for red aggregate";
                    type uint32 {
                      range "0..1000000";
                    }
                  }
                  leaf mark-probability {
                    description
                      "mark-probability for red aggregate";
                    type empty;
                  }
                  leaf denominator {
                    type uint32 {
                      range "0..65535";
                    }
                  }
                }
                container discard-class {
                  description
                    "parameters for each discard-class value";
                  leaf dclass {
                    type uint16 {
                      range "0..7";
                    }
                  }
                  uses live_ncs_random-detect-grouping;
                }
                leaf discard-class-based {
                  description
                    "Enable discard-class-based WRED as drop policy";
                  type empty;
                }
                leaf dscp-based {
                  description
                    "Enable dscp-based WRED as drop policy";
                  type empty;
                }
                list dscp {
                  description
                    "parameters for each dscp value";
                  key "dscp-val";
                  leaf dscp-val {
                    type ios-types:dscp-type;
                  }
                  uses live_ncs_random-detect-grouping;
                }
                leaf ecn {
                  description
                    "explicit congestion notification";
                  type empty;
                }
                leaf exponential-weighting-constant {
                  description
                    "weight for mean queue depth calculation";
                  type uint16 {
                    range "1..16";
                  }
                }
                leaf prec-based {
                  description
                    "Enable precedence-based WRED as drop policy";
                  type empty;
                }
                container precedence {
                  description
                    "parameters for each precedence value";
                  leaf prec {
                    type precedence-type2;
                  }
                  uses live_ncs_random-detect-grouping;
                }
              }
            }
            case service-policy-case {
              leaf service-policy {
                type string;
              }
            }
            case set-case {
              container set {
                // NCS drop when statement
                leaf atm-clp {
                  description
                    "Set ATM CLP bit to 1";
                  type empty;
                }
                container cos {
                  description
                    "Set IEEE 802.1Q/ISL class of service/user priority";
                  choice cos-type {
                    case a {
                      leaf val {
                        type uint16 {
                          range "0..7";
                        }
                      }
                    }
                    case b {
                      leaf pack {
                        type enumeration {
                          enum "dscp";
                          enum "precedence";
                          enum "cos";
                          enum "qos-group";
                          enum "wlan";
                        }
                      }
                      leaf user-priority {
                        description
                          "Set value from WLAN user-priority";
                        // NCS drop when statement
                        type empty;
                      }
                      leaf table {
                        description
                          "Set codepoint value based on tablemap.";
                        type string;
                      }
                    }
                  }
                }
                leaf discard-class {
                  description
                    "Discard behavior identifier";
                  type uint16 {
                    range "0..7";
                  }
                }
                container dscp {
                  description
                    "Set DSCP in IP(v4) and IPv6 packets";
                  container dscp {
                    description
                      "Set packet dscp from dscp";
                    presence "true";
                    leaf table {
                      description
                        "Set packet dscp from dscp based on table map.";
                      type string;
                    }
                  }
                  leaf tunnel {
                    description
                      "set tunnel packet dscp";
                    type empty;
                  }
                  leaf dscp-val {
                    type ios-types:dscp-type;
                  }
                }
                leaf fr-de {
                  description
                    "Set FR DE bit to 1";
                  type empty;
                }
                container ip {
                  description
                    "Set IP specific values";
                  choice ip-choice {
                    container dscp {
                      description
                        "Set IP DSCP (DiffServ CodePointint)";
                      leaf tunnel {
                        description
                          "set tunnel packet dscp";
                        type empty;
                      }
                      leaf dscp-val {
                        type ios-types:dscp-type;
                      }
                    }
                    container precedence {
                      description
                        "Set IP precedence";
                      presence "Set IP precedence";
                      leaf precedence-val {
                        type ios-types:precedence-type;
                      }
                    }
                  }
                }
                container mpls {
                  description
                    "Set MPLS specific values";
                  container experimental {
                    description
                      "Set Experimental value";
                    container imposition {
                      description
                        "Set Experimental value at tag imposition";
                      leaf exp-value {
                        type uint8 {
                          range "0..7";
                        }
                      }
                    }
                    container topmost {
                      description
                        "Set Experimental value  on topmost label";
                      leaf exp-value {
                        type uint8 {
                          range "0..7";
                        }
                      }
                    }
                  }
                }
                container qos-group {
                  description
                    "Set QoS Group";
                  leaf qos-group-value {
                    type uint8 {
                      range "0..99";
                    }
                  }
                }
              }
            }
            case shape-case {
              container shape {
                // NCS drop when statement
                leaf adaptive {
                  description
                    "Enable Traffic Shaping adaptation to BECN";
                  type uint32 {
                    range "8000..154400000";
                  }
                }
                container average {
                  description
                    "configure token bucket: CIR (bps) [Bc (bits) [Be (bits)]], send out Bc only per interval";
                  choice average-choice {
                    case a {
                      leaf bit-rate {
                        type uint64;
                      }
                      leaf bits-per-interval-sustained {
                        type uint32 {
                          range "256..154400000";
                        }
                      }
                      leaf bits-per-interval-excess {
                        // NCS drop when statement
                        type uint32 {
                          range "0..154400000";
                        }
                      }
                      container account {
                        description
                          "Overhead Accounting";
                        leaf user-defined {
                          description
                            "Offset Size";
                          type int32 {
                            range "-1000000..1000000";
                          }
                        }
                      }
                    }
                    case b {
                      leaf percent {
                        description
                          "% of interface bandwidth for Committed information rate";
                        type ios-types:percentage;
                      }
                      leaf burst-size-sustained {
                        type uint16 {
                          range "10..2000";
                        }
                      }
                      leaf ms {
                        description
                          "milliseconds";
                        type empty;
                      }
                      container bse {
                        leaf burst-size-excess {
                          type uint16 {
                            range "10..2000";
                          }
                        }
                        leaf ms {
                          description
                            "milliseconds";
                          type empty;
                        }
                      }
                    }
                  }
                }
                leaf fecn-adapt {
                  description
                    "Enable Traffic Shaping reflection of FECN as BECN";
                  type empty;
                }
                container fr-voice-adapt {
                  description
                    "Enable rate adjustment depending on voice presence";
                  presence "Enable rate adjustment depending on voice presence";
                  leaf deactivation {
                    type uint16 {
                      range "1..10000";
                    }
                  }
                }
                leaf max-buffers {
                  description
                    "Set Maximum Buffer Limit";
                  type uint16 {
                    range "1..4096";
                  }
                }
              }
            }
            case trust-case {
              leaf trust {
                // NCS drop when statement
                type enumeration {
                  enum "cos";
                  enum "dscp";
                  enum "ip-precedence";
                }
              }
            }
          }
        }
      }
      leaf description {
        description
          "Policy-Map description";
        type string {
          length "1..200";
        }
      }
      leaf sequence-interval {
        description
          "Enable sequence number capability";
        // NCS drop when statement
        type uint16;
      }
    }
  }

  grouping live_ncs_class-map-match-result-type-grouping {
    leaf aaa-timeout {
      description
        "aaa timeout type";
      type empty;
    }
    leaf agent-not-found {
      description
        "agent not found type";
      type empty;
    }
    leaf authoritative {
      description
        "failure type";
      type empty;
    }
    leaf method-timeout {
      description
        "method_timeout type";
      type empty;
    }
    leaf none {
      description
        "no type";
      type empty;
    }
    leaf success {
      description
        "success type";
      type empty;
    }
  }

  grouping live_ncs_class-map-control-filter-grouping {
    list activated-service-template {
      description
        "match name of service template activated on session";
      key "service-name";
      leaf service-name {
        description
          "Enter service name";
        type string;
      }
    }
    container authorization-status {
      description
        "match the authorization status of the session";
      leaf authorized {
        description
          "authorized";
        type empty;
      }
      leaf unauthorized {
        description
          "unauthorized";
        type empty;
      }
    }
    container authorizing-method-priority {
      description
        "match the priority against the authorizing method's priority";
      leaf eq {
        description
          "equal to";
        type uint8 {
          range "1..254";
        }
      }
      leaf gt {
        description
          "greater than";
        type uint8 {
          range "1..254";
        }
      }
      leaf lt {
        description
          "less than";
        type uint8 {
          range "1..254";
        }
      }
    }
    container method {
      description
        "match the type of authentication method from an event";
      leaf dot1x {
        description
          "dot1x";
        type empty;
      }
      leaf mab {
        description
          "mab";
        type empty;
      }
      leaf webauth {
        description
          "webauth";
        type empty;
      }
    }
    container result-type {
      description
        "match the result type, optionally for a specific method";
      container method {
        description
          "match the result of a particular method";
        container dot1x {
          description
            "dot1x result";
          uses live_ncs_class-map-match-result-type-grouping;
        }
        container mab {
          description
            "mab result";
          uses live_ncs_class-map-match-result-type-grouping;
        }
        container webauth {
          description
            "webauth result";
          uses live_ncs_class-map-match-result-type-grouping;
        }
      }
      uses live_ncs_class-map-match-result-type-grouping;
    }
  }

  grouping live_ncs_class-map-match-grouping {
    container current-method-priority {
      description
        "match the priority against the current method's priority";
      leaf eq {
        description
          "equal to";
        type uint8 {
          range "1..254";
        }
      }
      leaf gt {
        description
          "greater than";
        type uint8 {
          range "1..254";
        }
      }
      leaf lt {
        description
          "less than";
        type uint8 {
          range "1..254";
        }
      }
    }
    container application {
      description
        "Application to match";
      container application-group {
        description
          "Application Group to match";
        leaf telepresence-group {
          description
            "Telepresence Group";
          type empty;
        }
        leaf vmware-group {
          description
            "VMWARE Group";
          type empty;
        }
        leaf webex-group {
          description
            "WebEx Group";
          type empty;
        }
      }
      container attribute {
        description
          "Application attribute to match";
        leaf media-type {
          description
            "Media type attribute to match";
          type enumeration {
            enum "audio";
            enum "audio-video";
            enum "control";
            enum "data";
            enum "video";
          }
        }
      }
    }
    container access-group {
      description
        "Access group";
      leaf index {
        type uint32 {
          range "1..2699";
        }
      }
      leaf-list name {
        description
          "Named Access List";
        type string;
      }
    }
    leaf any {
      description
        "Any packets";
      type empty;
    }
    leaf-list class-map {
      description
        "Class map";
      type string;
    }
    leaf-list cos {
      description
        "IEEE 802.1Q/ISL class of service/user priority values";
      type uint8 {
        range "0..7";
      }
    }
    container destination-address {
      description
        "Destination address";
      leaf-list mac {
        description
          "MAC address";
        type yang:mac-address;
      }
    }
    leaf-list discard-class {
      description
        "Discard behavior identifier";
      type uint8 {
        range "0..7";
      }
    }
    leaf-list dscp {
      description
        "Match DSCP in IP(v4) and IPv6 packets";
      type ios-types:dscp-type;
    }
    leaf fr-de {
      description
        "Match on Frame-relay DE bit";
      type empty;
    }
    leaf-list fr-dlci {
      description
        "Match on fr-dlci";
      type uint16 {
        range "16..1007";
      }
    }
    container group-object {
      description
        "Match object-group";
      container security {
        description
          "Match object-group security";
        leaf-list source {
          description
            "Match source object-group security";
          type string;
        }
        leaf-list destination {
          description
            "Match destination object-group security";
          type string;
        }
      }
    }
    leaf-list input-interface {
      description
        "Select an input interface to match";
      type string;
    }
    container ip {
      description
        "IP specific values";
      leaf-list dscp {
        description
          "Match IP DSCP (DiffServ CodePoints)";
        type ios-types:dscp-type;
      }
      leaf-list precedence {
        description
          "Match IP precedence";
        type ios-types:precedence-type;
      }
      list rtp {
        description
          "Match RTP port nos";
        key "port1 port2";
        leaf port1 {
          type uint16 {
            range "2000..65535";
          }
        }
        leaf port2 {
          type uint16 {
            range "0..16383";
          }
        }
      }
    }
    leaf non-client-nrt {
      type empty;
    }
    container mpls {
      description
        "Multi Protocol Label Switching specific values";
      container experimental {
        description
          "Match MPLS experimental";
        leaf-list topmost {
          description
            "Match MPLS experimental value on topmost label";
          type uint8 {
            range "0..7";
          }
        }
      }
    }
    container packet {
      description
        "Layer 3 Packet length";
      container length {
        description
          "Layer 3 Packet length";
        leaf max {
          description
            "Maximum length of packet";
          type uint16 {
            range "1..2000";
          }
        }
        leaf min {
          description
            "Minimum length of packet";
          type uint16 {
            range "1..2000";
          }
        }
      }
    }
    leaf-list precedence {
      description
        "Match Precedence in IP(v4) and IPv6 packets";
      type ios-types:precedence-type;
    }
    container protocol {
      description
        "Protocol";
      leaf protocols {
        type enumeration {
          enum "x802-11-iapp";
          enum "ace-svr";
          enum "aol";
          enum "appleqtc";
          enum "biff";
          enum "bittorrent";
          enum "bootpc";
          enum "bootps";
          enum "cddbp";
          enum "cifs";
          enum "cisco-fna";
          enum "cisco-net-mgmt";
          enum "cisco-svcs";
          enum "cisco-sys";
          enum "cisco-tdp";
          enum "cisco-tna";
          enum "citriximaclient";
          enum "clp";
          enum "creativepartnr";
          enum "creativeserver";
          enum "daytime";
          enum "dbase";
          enum "dbcontrol_agent";
          enum "ddns-v3";
          enum "dhcp-failover";
          enum "directconnect";
          enum "discard";
          enum "dnsix";
          enum "echo";
          enum "entrust-svc-hdlr";
          enum "entrust-svcs";
          enum "exec";
          enum "fcip-port";
          enum "ftps";
          enum "gdoi";
          enum "giop";
          enum "gtpv0";
          enum "gtpv1";
          enum "h225ras";
          enum "h323callsigalt";
          enum "hp-alarm-mgr";
          enum "hp-collector";
          enum "hp-managed-node";
          enum "hsrp";
          enum "https";
          enum "ica";
          enum "icabrowser";
          enum "ident";
          enum "igmpv3lite";
          enum "imap3";
          enum "imaps";
          enum "ipass";
          enum "ipsec-msft";
          enum "irc-serv";
          enum "ircs";
          enum "ircu";
          enum "isakmp";
          enum "iscsi";
          enum "iscsi-target";
          enum "kermit";
          enum "ldap-admin";
          enum "ldaps";
          enum "login";
          enum "lotusmtap";
          enum "lotusnote";
          enum "mapi";
          enum "ms-ad-rep";
          enum "ms-exch-nspi";
          enum "ms-frs";
          enum "ms-frsapi";
          enum "ms-rfr";
          enum "msn-messenger";
          enum "netlogon";
          enum "microsoft-ds";
          enum "ms-cluster-net";
          enum "ms-dotnetster";
          enum "ms-sna";
          enum "ms-sql";
          enum "ms-sql-m";
          enum "msexch-routing";
          enum "msnmsgr";
          enum "msrpc";
          enum "mysql";
          enum "n2h2server";
          enum "ncp";
          enum "net8-cman";
          enum "netbios-dgm";
          enum "netbios-ns";
          enum "netbios-ssn";
          enum "netstat";
          enum "oem-agent";
          enum "oracle";
          enum "oracle-em-vp";
          enum "oraclenames";
          enum "orasrv";
          enum "pcanywheredata";
          enum "pcanywherestat";
          enum "pop3s";
          enum "pwdgen";
          enum "qmtp";
          enum "r-winsock";
          enum "radius";
          enum "rdb-dbs-disp";
          enum "realmedia";
          enum "realsecure";
          enum "router";
          enum "rsvp-encap";
          enum "rsvp_tunnel";
          enum "rtc-pm-port";
          enum "rtelnet";
          enum "send";
          enum "shell";
          enum "sip-tls";
          enum "sms";
          enum "smtp";
          enum "snmptrap";
          enum "sql-net";
          enum "sqlserv";
          enum "sqlsrv";
          enum "sshell";
          enum "ssp";
          enum "syslog-conn";
          enum "tacacs";
          enum "tacacs-ds";
          enum "tarantella";
          enum "tcp";
          enum "telnets";
          enum "time";
          enum "timed";
          enum "tr-rsrb";
          enum "ttc";
          enum "udp";
          enum "uucp";
          enum "vqp";
          enum "webster";
          enum "who";
          enum "wins";
          enum "x11";
          enum "xdmcp";
          enum "ymsgr";
          enum "aarp";
          enum "appletalk";
          enum "arp";
          enum "bgp";
          enum "bridge";
          enum "bstun";
          enum "cdp";
        }
      }
      container citrix {
        description
          "Citrix Systems ICA protocol";
        presence "enable citrix system protocol matching";
        leaf ica-tag {
          description
            "Citrix ICA tag 0-high 1-medium 2-low 3-background";
          type string;
        }
      }
      leaf clns {
        description
          "ISO CLNS";
        type empty;
      }
      leaf clns_es {
        description
          "ISO CLNS End System";
        type empty;
      }
      leaf clns_is {
        description
          "ISO CLNS Intermediate System";
        type empty;
      }
      leaf cmns {
        description
          "ISO CMNS";
        type empty;
      }
      leaf compressedtcp {
        description
          "Compressed TCP (VJ";
        type empty;
      }
      leaf cuseeme {
        description
          "CU-SeeMe desktop video conference";
        type empty;
      }
      leaf decnet {
        description
          "DECnet";
        type empty;
      }
      leaf decnet_node {
        description
          "DECnet Node";
        type empty;
      }
      leaf decnet_router-l1 {
        description
          "DECnet Router L1";
        type empty;
      }
      leaf decnet_router-l2 {
        description
          "DECnet Router L2";
        type empty;
      }
      leaf dhcp {
        description
          "Dynamic Host Configuration";
        type empty;
      }
      leaf dlsw {
        type empty;
      }
      leaf dns {
        type empty;
      }
      leaf edonkey {
        type empty;
      }
      leaf egp {
        type empty;
      }
      leaf eigrp {
        type empty;
      }
      leaf exchange {
        type empty;
      }
      container fasttrack {
        description
          "FastTrack Traffic - KaZaA, Morpheus, Grokster";
        presence "enable fasttrack matching";
        leaf file-transfer {
          description
            "File transfer stream";
          type string;
        }
      }
      leaf finger {
        type empty;
      }
      leaf ftp {
        type empty;
      }
      container gnutella {
        description
          "Gnutella Version2 Traffic - BearShare, Shareeza, Morpheus";
        presence "enable gnutella matching";
        leaf file-transfer {
          description
            "File transfer stream";
          type string;
        }
      }
      leaf gopher {
        type empty;
      }
      leaf gre {
        type empty;
      }
      leaf h323 {
        type empty;
      }
      container http {
        description
          "World Wide Web traffic";
        presence "enable http traffic matching";
        leaf c-header-field {
          description
            "Client general Header Field";
          type string;
        }
        leaf host {
          description
            "Server Host Name";
          type string;
        }
        leaf mime {
          description
            "Match MIME Type";
          type string;
        }
        leaf s-header-field {
          description
            "Server general Header Field";
          type string;
        }
        leaf url {
          description
            "Match URL String";
          type string;
        }
      }
      leaf icmp {
        description
          "Internet Control Message";
        type empty;
      }
      leaf imap {
        description
          "Internet Message Access Protocol";
        type empty;
      }
      leaf ip {
        description
          "IP";
        type empty;
      }
      leaf ipinip {
        description
          "IP in IP (encapsulation";
        type empty;
      }
      leaf ipsec {
        description
          "IP Security Protocol (ESP/AH";
        type empty;
      }
      leaf ipv6 {
        description
          "IPV6";
        type empty;
      }
      leaf ipx {
        description
          "Novell IPX";
        type empty;
      }
      leaf irc {
        type empty;
        description
          "Internet Relay Chat";
      }
      container kazaa2 {
        description
          "Kazaa Version 2";
        presence "enable kazaa version 2 matching";
        leaf file-transfer {
          description
            "File transfer stream";
          type string;
        }
      }
      leaf kerberos {
        description
          "Kerberos";
        type empty;
      }
      leaf l2tp {
        description
          "L2F/L2TP tunnel";
        type empty;
      }
      leaf ldap {
        description
          "Lightweight Directory Access Protocol";
        type empty;
      }
      leaf llc2 {
        description
          "llc2";
        type empty;
      }
      leaf mgcp {
        description
          "Media Gateway Control Protocol";
        type empty;
      }
      container napster {
        description
          "Napster Traffic";
        presence "enable napster matching";
        leaf non-std {
          description
            "Non-standard port advertizements";
          type empty;
        }
      }
      leaf netbios {
        description
          "NetBIOS";
        type empty;
      }
      leaf netshow {
        description
          "Microsoft Netshow";
        type empty;
      }
      leaf nfs {
        description
          "Network File System";
        type empty;
      }
      leaf nntp {
        description
          "Network News Transfer Protocol";
        type empty;
      }
      leaf notes {
        description
          "Lotus Notes(R";
        type empty;
      }
      leaf novadigm {
        description
          "Novadigm EDM";
        type empty;
      }
      leaf ntp {
        description
          "Network Time Protocol";
        type empty;
      }
      leaf ospf {
        description
          "Open Shortest Path First";
        type empty;
      }
      leaf pad {
        description
          "PAD links";
        type empty;
      }
      leaf pcanywhere {
        description
          "Symantec pcANYWHERE";
        type empty;
      }
      leaf pop3 {
        description
          "Post Office Protocol";
        type empty;
      }
      leaf pppoe {
        description
          "PPP over Ethernet";
        type empty;
      }
      leaf pptp {
        description
          "Point-to-Point Tunneling Protocol";
        type empty;
      }
      leaf printer {
        description
          "print spooler/lpd";
        type empty;
      }
      leaf qllc {
        description
          "qllc protocol";
        type empty;
      }
      leaf rcmd {
        description
          "BSD r-commands (rsh, rlogin, rexec";
        type empty;
      }
      leaf rip {
        description
          "Routing Information Protocol";
        type empty;
      }
      leaf rsrb {
        description
          "Remote Source-Route Bridging";
        type empty;
      }
      leaf rsvp {
        description
          "Resource Reservation Protocol";
        type empty;
      }
      leaf rtcp {
        description
          "Real Time Control Protocol";
        type empty;
      }
      container rtp {
        description
          "Real Time Protocol";
        presence "enable rtp matching";
        leaf audio {
          description
            "Match voice packets";
          type empty;
        }
        leaf payload-type {
          description
            "Match an explicit PT";
          type string;
        }
        leaf video {
          description
            "Match video packets";
          type empty;
        }
      }
      leaf rtsp {
        description
          "Real Time Streaming Protocol";
        type empty;
      }
      leaf secure-ftp {
        description
          "FTP over TLS/SSL";
        type empty;
      }
      leaf secure-http {
        description
          "Secured HTTP";
        type empty;
      }
      leaf secure-imap {
        description
          "Internet Message Access Protocol over TLS/SSL";
        type empty;
      }
      leaf secure-irc {
        description
          "Internet Relay Chat over TLS/SSL";
        type empty;
      }
      leaf secure-ldap {
        description
          "Lightweight Directory Access Protocol over TLS/SSL";
        type empty;
      }
      leaf secure-nntp {
        description
          "Network News Transfer Protocol over TLS/SSL";
        type empty;
      }
      leaf secure-pop3 {
        description
          "Post Office Protocol over TLS/SSL";
        type empty;
      }
      leaf secure-telnet {
        description
          "Telnet over TLS/SSL";
        type empty;
      }
      leaf sip {
        description
          "Session Initiation Protocol";
        type empty;
      }
      leaf skinny {
        description
          "Skinny Protocol";
        type empty;
      }
      container smtp {
        description
          "Simple Mail Transfer Protocol";
        presence "true";
        leaf extended {
          type empty;
        }
      }
      leaf snapshot {
        description
          "Snapshot routing support";
        type empty;
      }
      leaf snmp {
        description
          "Simple Network Management Protocol";
        type empty;
      }
      leaf socks {
        description
          "SOCKS";
        type empty;
      }
      leaf sqlnet {
        description
          "SQL*NET for Oracle";
        type empty;
      }
      leaf sqlserver {
        description
          "MS SQL Server";
        type empty;
      }
      leaf ssh {
        description
          "Secured Shell";
        type empty;
      }
      leaf streamwork {
        description
          "Xing Technology StreamWorks player";
        type empty;
      }
      leaf stun {
        description
          "Serial Tunnel";
        type empty;
      }
      leaf sunrpc {
        description
          "Sun RPC";
        type empty;
      }
      leaf syslog {
        description
          "System Logging Utility";
        type empty;
      }
      leaf telnet {
        description
          "Telnet";
        type empty;
      }
      leaf tftp {
        description
          "Trivial File Transfer Protocol";
        type empty;
      }
      leaf vdolive {
        description
          "VDOLive streaming video";
        type empty;
      }
      leaf vofr {
        description
          "voice over Frame Relay packets";
        type empty;
      }
      leaf winmx {
        description
          "WinMx file-sharing application";
        type empty;
      }
      leaf xwindows {
        description
          "X-Windows remote access";
        type empty;
      }
      container attribute {
        description
          "Attribute based protocol match";
        container business-relevance {
          description
            "Application business-relevance";
          leaf business-irrelevant {
            description
              "Undesirable business traffic";
            type empty;
          }
          leaf business-relevant {
            description
              "Business critical applications";
            type empty;
          }
          leaf default {
            description
              "Related business applications";
            type empty;
          }
        }
        container traffic-class {
          description
            "SRND class";
          leaf broadcast-video {
            description
              "Broadcast TV, live events, video surveillance";
            type empty;
          }
          leaf bulk-data {
            description
              "Non-interactive data applications";
            type empty;
          }
          leaf multimedia-conferencing {
            description
              "Desktop software multimedia collaboration applications";
            type empty;
          }
          leaf multimedia-streaming {
            description
              "Video-on-Demand (VoD) streaming video";
            type empty;
          }
          leaf network-control {
            description
              "Network control plane traffic";
            type empty;
          }
          leaf ops-admin-mgmt {
            description
              "Network operations, administration, and management traffic";
            type empty;
          }
          leaf real-time-interactive {
            description
              "High-definition interactive video applications";
            type empty;
          }
          leaf signaling {
            description
              "Signaling traffic that supports IP voice and video telephony";
            type empty;
          }
          leaf transactional-data {
            description
              "Interactive data applications";
            type empty;
          }
          leaf voip-telephony {
            description
              "VoIP telephony (bearer-only) traffic";
            type empty;
          }
        }
      }
    }
    leaf-list qos-group {
      description
        "Qos-group";
      type uint16 {
        range "0..99";
      }
    }
    container security-group {
      description
        "Security group";
      container destination {
        description
          "Destination security group";
        leaf tag {
          description
            "Security group tag";
          type uint16;
        }
      }
      container source {
        description
          "Source security group";
        leaf tag {
          description
            "Security group tag";
          type uint16;
        }
      }
    }
    container source-address {
      description
        "Source address";
      leaf-list mac {
        description
          "MAC address";
        type yang:mac-address;
      }
    }
    container vlan {
      description
        "VLANs to match";
      leaf-list inner {
        description
          "Inner tag to match";
        type union {
          type uint16 {
            range "1..4094";
          }
          type string;
        }
      }
      leaf-list value {
        type union {
          type uint16 {
            range "1..4094";
          }
          type string;
        }
      }
    }
  }

  grouping live_ncs_class-map-appnav-match-grouping {
    leaf peer {
      description
        "APPNAV Peer Filter";
      // NCS drop when statement
      type string;
    }
  }

  grouping live_ncs_class-map-appnav-not-match-grouping {
    leaf peer {
      description
        "APPNAV Peer Filter";
      // NCS drop when statement
      type string;
    }
  }

  grouping live_ncs_config-class-map-grouping {
    list class-map {
      description
        "configure qos class map";
      key "name";
      leaf name {
        type string;
      }
      leaf type {
        description
          "type of the class-map";
        type enumeration {
          enum "access-control";
          enum "appnav";
          enum "control";
          enum "inspect";
          enum "multicast-flows";
          enum "stack";
          enum "traffic";
        }
      }
      leaf subscriber {
        type empty;
      }
      leaf protocol {
        // NCS drop when statement
        type enumeration {
          enum "aol";
          enum "edonkey";
          enum "fasttrack";
          enum "gnutella";
          enum "http";
          enum "imap";
          enum "kazaa2";
          enum "msnmsgr";
          enum "pop3";
          enum "smtp";
          enum "sunrpc";
          enum "ymsgr";
        }
      }
      leaf prematch {
        type enumeration {
          enum "match-all";
          enum "match-any";
          enum "match-none";
        }
        // NCS drop mandatory statement
      }
      leaf description {
        description
          "Class-Map description";
        type string;
      }
      container match {
        description
          "classification criteria";
        uses live_ncs_class-map-match-grouping;
        uses live_ncs_class-map-appnav-match-grouping;
        uses live_ncs_class-map-control-filter-grouping;
        container not {
          description
            "Negate this match result";
          uses live_ncs_class-map-match-grouping;
          uses live_ncs_class-map-appnav-not-match-grouping;
        }
      }
      container no-match {
        description
          "no-match filter";
        uses live_ncs_class-map-control-filter-grouping;
      }
    }
  }

  grouping live_ncs_config-parameter-map-grouping {
    container timeout {
      description
        "timeout for the webauth session";
      // NCS drop when statement
      container init-state {
        description
          "init-state timeout";
        presence "true";
        leaf sec {
          description
            "WEBAUTH Timeout in Seconds";
          type uint32 {
            range "60..3932100";
          }
        }
      }
      container fin-wait {
        description
          "fin-wait timeout";
        leaf msec {
          description
            "WEBAUTH Timeout in milliseconds";
          type uint32 {
            range "1..2147483647";
          }
        }
      }
    }
    container watch-list {
      description
        "Watch List of webauth clients";
      // NCS drop when statement
      leaf enabled {
        description
          "Enable Watchlist";
        type empty;
      }
      leaf dynamic-expiry-timeout {
        description
          "dynamic_expiry_timeout";
        type uint32 {
          range "0..2147483";
        }
      }
      container add-item {
        description
          "Add item to Watch-list";
        leaf ipv4 {
          description
            "IPv4 Watch List Entry";
          type inet:ipv4-address;
        }
        leaf ipv6 {
          description
            "IPv6 Watch List Entry";
          type inet:ipv6-address;
        }
      }
    }
    container aggressive-aging {
      description
        "Aggressive Aging parameters";
      // NCS drop when statement
      container high {
        description
          "Specify the high watermark for aggressive-aging";
        choice absolute-percent {
          case absolute-case {
            container absolute {
              leaf value {
                type uint64 {
                  range "1..4294967295";
                }
              }
              leaf low {
                description
                  "Specify the low watermark for aggressive-aging";
                type uint64 {
                  range "1..4294967295";
                }
              }
            }
          }
          case percent-case {
            container percent {
              description
                "high watermark in percentage of max-incomplete value";
              leaf value {
                type uint8 {
                  range "1..100";
                }
              }
              leaf low_percent {
                description
                  "Specify the low watermark for aggressive-aging in percents";
                type uint8 {
                  range "1..100";
                }
              }
            }
          }
        }
      }
    }
    leaf alert {
      description
        "Turn on/off alert";
      type enumeration {
        enum "off";
        enum "on";
      }
    }
    leaf application-inspect {
      description
        "Turn on application inspection";
      type enumeration {
        enum "all";
        enum "dns";
        enum "exec";
        enum "ftp";
        enum "gtp";
        enum "h323";
        enum "http";
        enum "imap";
        enum "login";
        enum "msrpc";
        enum "netbios";
        enum "pop3";
        enum "rtsp";
        enum "shell";
        enum "sip";
        enum "skinny";
        enum "smtp";
        enum "sunrpc";
        enum "tftp";
      }
    }
    leaf audit-trail {
      description
        "Turn on/off audit trail";
      // NCS drop when statement
      type enumeration {
        enum "off";
        enum "on";
      }
    }
    leaf dns-timeout {
      description
        "Specify timeout for DNS";
      // NCS drop when statement
      type uint32 {
        range "1..2147483";
      }
    }
    container global {
      description
        "cws_tunnel global parameter-map";
      leaf fail-open {
        description
          "Allow traffic to go in clear if CWS Towers are unreachable";
        // NCS drop when statement
        type empty;
      }
      container license {
        description
          "License Key";
        // NCS drop when statement
        container Unencypted {
          description
            "Unencrypted License";
          leaf Hex-string {
            description
              "32 char non encrypted hex key";
            type string;
          }
        }
        container Encrypted {
          description
            "Encrypted License";
          leaf Hex-string {
            description
              "66 char encrypted hex key";
            type string;
          }
        }
      }
      leaf logging {
        description
          "CWS syslogs";
        type empty;
      }
      container primary {
        description
          "Primary tower";
        // NCS drop when statement
        presence "true";
        container tower {
          description
            "Tower configuration for CWS";
          leaf ipv4 {
            description
              "IPv4 address of the tower";
            type inet:ipv4-address;
          }
          leaf name {
            description
              "Fully Qualified Domain Name of tower";
            type string;
          }
        }
      }
      leaf redirect-list {
        description
          "Set access-list for reverse route from CWS Tower
           Standard IP access-list number <1-199>
           Standard IP access-list number (expanded range) <1300-2699>";
        // NCS drop when statement
        type union {
          type uint16 {
            range "1..199";
          }
          type uint16 {
            range "1300..2699";
          }
        }
      }
      container secondary {
        description
          "Secondary tower";
        // NCS drop when statement
        presence "true";
        container tower {
          description
            "Tower configuration for CWS";
          leaf ipv4 {
            description
              "IPv4 address of the tower";
            type inet:ipv4-address;
          }
          leaf name {
            description
              "Fully Qualified Domain Name of tower";
            type string;
          }
        }
      }
      container whitelist {
        description
          "Disable redirection to CWS
           Access list (standard) <1-199>
           Access list (extended) <1300-2699>
           Access list name";
        presence "true";
        container acl {
          description
            "Access list";
          leaf acl-number {
            type union {
              type uint16 {
                range "1..199";
              }
              type uint16 {
                range "1300..2699";
              }
            }
          }
          leaf name {
            description
              "Access list name";
            type string;
          }
        }
        container domain-name {
          description
            "Domain name based Whitelist";
          leaf regex {
            description
              "Domain name regex parameter map";
            type string;
          }
        }
        container download {
          description
            "whitelist download command";
          presence "true";
          leaf interval {
            description
              "Download interval in minutes";
            type uint16 {
              range "5..10080";
            }
          }
        }
      }
    }
    container icmp {
      description
        "Config timeout values for icmp";
      // NCS drop when statement
      leaf idle-time {
        description
          "Specify timeout for icmp";
        type uint32 {
          range "1..2147483";
        }
      }
    }
    container lisp {
      description
        "Turn on LISP options";
      leaf inner-packet-inspection {
        description
          "inner-packet-inspection";
        type empty;
      }
    }
    container log {
      description
        "Configure inspect logging parameters";
      leaf dropped-packets {
        description
          "Log dropped packets";
        type empty;
      }
      container flow-export {
        description
          "Configure inspect external logging parameters";
        container template {
          description
            "Configure record template parameters";
          leaf timeout-rate {
            description
              "Rate to resend the template in seconds";
            type uint32 {
              range "0..65535";
            }
          }
        }
        container v9 {
          description
            "Netflow version 9";
          container udp {
            description
              "Use UDP to export records";
            container destination {
              description
                "Specify the flow-export destination";
              leaf dst-ip {
                type inet:ipv4-address;
              }
              leaf dst-port {
                type uint16;
              }
            }
          }
        }
      }
    }
    leaf max-destination {
      description
        "config maximum destination";
      // NCS drop when statement
      type uint32 {
        range "1..4294967295";
      }
    }
    container max-incomplete {
      description
        "Specify maximum number of incomplete connections before clamping";
      leaf high {
        description
          "Specify high-watermark for clamping";
        type uint32 {
          range "1..2147483647";
        }
      }
      leaf low {
        description
          "Specify low-watermark for clamping";
        type uint32 {
          range "1..2147483647";
        }
      }
    }
    container one-minute {
      description
        "Specify one-minute-sample watermarks for clamping";
      // NCS drop when statement
      leaf high {
        description
          "Specify high-watermark for clamping";
        type uint32 {
          range "1..2147483647";
        }
      }
      leaf low {
        description
          "Specify low-watermark for clamping";
        type uint32 {
          range "1..2147483647";
        }
      }
    }
    container sessions {
      description
        "Maximum number of inspect sessions";
      // NCS drop when statement
      leaf maximum {
        description
          "Maximum sessions";
        type uint32 {
          range "1..2147483647";
        }
      }
      container queue {
        description
          "queue";
        leaf max-threshold {
          type uint16 {
            range "0..65535";
          }
        }
        leaf min-threshold {
          type uint16 {
            range "0..65535";
          }
        }
      }
    }
    choice tcp-ins {
      container tcp-inspect {
        // NCS drop when statement
        container tcp {
          description
            "Config timeout values for tcp connections";
          // NCS drop when statement
          leaf finwait-time {
            description
              "Specify timeout for TCP connections after a FIN";
            type uint32 {
              range "1..2147483";
            }
          }
          leaf idle-time {
            description
              "Specify idle timeout for tcp connections";
            type uint32 {
              range "1..2147483";
            }
          }
          container max-incomplete {
            description
              "Specify max half-open connection per host";
            leaf host {
              description
                "Specify max half-open connection per host";
              type uint32 {
                range "1..4294967295";
              }
            }
          }
          leaf synwait-time {
            description
              "Specify timeout for TCP connections after a SYN and no";
            type uint32 {
              range "1..2147483";
            }
          }
        }
      }
      container tcp-inspect-zone {
        // NCS drop when statement
        container tcp {
          description
            "Configure tcp syn-flood per-destination rate";
          container syn-flood {
            description
              "maximum syn packet";
            container rate {
              description
                "maximum syn packet rate";
              leaf per-destination {
                description
                  "per destination
                   maximum rate of TCP SYN packets";
                type uint32 {
                  range "1..1000000000";
                }
              }
            }
          }
        }
      }
    }
    container threat-detection {
      description
        "Configure Threat Detection";
      // NCS drop when statement
      leaf basic-threat {
        description
          "Enable Threat Detection";
        type empty;
      }
      container rate {
        description
          "Configure Threat Detection rate";
        container fw-drop {
          description
            "Configure Threat Detection rate for firewall drop events";
          leaf average-time-frame {
            description
              "Configure Threat Detection average time frame";
            type uint32 {
              range "600..3600";
            }
          }
          leaf average-threshold {
            description
              "Configure Threat Detection average threshold";
            type uint64 {
              range "1..4294967295";
            }
          }
          leaf burst-threshold {
            description
              " Configure Threat Detection burst threshold";
            type uint64 {
              range "1..1000000000";
            }
          }
        }
        container inspect-drop {
          description
            "Configure Threat Detection rate for firewall inspection based drop events";
          leaf average-time-frame {
            description
              "Configure Threat Detection average time frame";
            type uint32 {
              range "600..3600";
            }
          }
          leaf average-threshold {
            description
              "Configure Threat Detection average threshold";
            type uint64 {
              range "1..4294967295";
            }
          }
          leaf burst-threshold {
            description
              " Configure Threat Detection burst threshold";
            type uint64 {
              range "1..1000000000";
            }
          }
        }
        container syn-attack {
          description
            "Configure Threat Detection rate for syn attack events";
          leaf average-time-frame {
            description
              "Configure Threat Detection average time frame";
            type uint32 {
              range "600..3600";
            }
          }
          leaf average-threshold {
            description
              "Configure Threat Detection average threshold";
            type uint64 {
              range "1..4294967295";
            }
          }
          leaf burst-threshold {
            description
              " Configure Threat Detection burst threshold";
            type uint64 {
              range "1..1000000000";
            }
          }
        }
      }
    }
    container udp {
      description
        "Config timeout values for udp flows";
      // NCS drop when statement
      leaf idle-time {
        description
          "Specify idle timeout for udp";
        type uint32 {
          range "1..2147483";
        }
      }
    }
    container vrf {
      description
        "vrf binding with parameter map";
      leaf name {
        type string;
      }
      leaf inspect {
        description
          "vrf binding with parameter map";
        type string;
      }
    }
    leaf zone-mismatch {
      description
        "Config zone-mismatch option";
      type enumeration {
        enum "drop";
      }
    }
  }

  grouping live_ncs_config-service-policy-direction-grouping {
    leaf input {
      description
        "Assign policy-map to the input of an interface";
      type string;
    }
    leaf output {
      description
        "Assign policy-map to the output of an interface";
      type string;
    }
  }

  grouping live_ncs_config-service-policy-grouping {
    container service-policy {
      uses live_ncs_config-service-policy-direction-grouping;
    }
  }

  grouping live_ncs_config-interface-service-policy-grouping {
    container service-policy {
      description
        "Configure QoS Service Policy";
      leaf history {
        description
          "Keep history of QoS metrics";
        type empty;
      }
      uses live_ncs_config-service-policy-direction-grouping;
      container type {
        description
          "Configure CPL Service Policy";
        container control {
          leaf subscriber {
            type string;
          }
        }
        container performance-monitor {
          description
            "Configure media monitor service-policy type";
          leaf direction {
            type enumeration {
              enum "input";
              enum "output";
            }
          }
          leaf name {
            type string;
          }
        }
        container service-chain {
          description
            "Configure Service-chain Service Policy";
          container input {
            description
              "Assign policy-map to the input of an interface";
            leaf name {
              type string;
            }
          }
          container output {
            description
              "Assign policy-map to the output of an interface";
            leaf name {
              type string;
            }
          }
        }
      }
    }
  }

  grouping police-action-transmit-grouping {
    leaf transmit {
      description
        "transmit packet";
      type empty;
    }
  }

  grouping police-action-drop-grouping {
    leaf drop {
      description
        "drop packet";
      type empty;
    }
  }

  grouping police-conform-action-grouping {
    container conform-set-clp-transmit {
      container conform-action {
        description
          "action when rate is less than conform burst";
        leaf set-clp-transmit {
          description
            "set atm clp and send it";
          type empty;
        }
      }
    }
    container conform-set-cos-transmit {
      container conform-action {
        description
          "action when rate is less than conform burst";
        leaf set-cos-transmit {
          description
            "rewrite packet cos and send it";
          type ios-types:cos_value-type;
        }
      }
    }
    container conform-set-cos-transmit-table {
      container conform-action {
        description
          "action when rate is less than conform burst";
        leaf set-cos-transmit {
          description
            "rewrite packet cos and send it";
          type ios-types:cos_value-type;
        }
        leaf table {
          description
            "Specify table-map";
          type leafref {
            path "/ncs:devices/ncs:device/ncs:config/ios:native/ios:table-map/ios:name" {
              tailf:xpath-root 3;
            }
          }
        }
      }
    }
    container conform-set-discard-class-transmit {
      container conform-action {
        description
          "action when rate is less than conform burst";
        leaf set-discard-class-transmit {
          description
            "set discard-class and send it";
          type uint8 {
            range "0..7";
          }
        }
      }
    }
    container conform-set-dscp-transmit {
      container conform-action {
        description
          "action when rate is less than conform burst";
        leaf set-dscp-transmit {
          description
            "set dscp and send it";
          type ios-types:dscp-type;
        }
      }
    }
    container conform-set-dscp-transmit-table {
      container conform-action {
        description
          "action when rate is less than conform burst";
        leaf set-dscp-transmit {
          description
            "set dscp and send it";
          type ios-types:dscp-type;
        }
        leaf table {
          description
            "Specify table-map";
          type leafref {
            path "/ncs:devices/ncs:device/ncs:config/ios:native/ios:table-map/ios:name" {
              tailf:xpath-root 3;
            }
          }
        }
      }
    }
    container conform-set-frde-transmit {
      container conform-action {
        description
          "action when rate is less than conform burst";
        leaf set-frde-transmit {
          description
            "set FR DE and send it";
          type empty;
        }
      }
    }
    container conform-set-mpls-exp-imposition-transmit {
      container conform-action {
        description
          "action when rate is less than conform burst";
        leaf set-mpls-exp-imposition-transmit {
          description
            "set exp at tag imposition and send it";
          type ios-types:exp_value-type;
        }
      }
    }
    container conform-set-mpls-exp-imposition-transmit-table {
      container conform-action {
        description
          "action when rate is less than conform burst";
        leaf set-mpls-exp-imposition-transmit {
          description
            "set exp at tag imposition and send it";
          type ios-types:exp_value-type;
        }
        leaf table {
          description
            "Specify table-map";
          type leafref {
            path "/ncs:devices/ncs:device/ncs:config/ios:native/ios:table-map/ios:name" {
              tailf:xpath-root 3;
            }
          }
        }
      }
    }
    container conform-set-mpls-exp-topmost-transmit {
      container conform-action {
        description
          "action when rate is less than conform burst";
        leaf set-mpls-exp-topmost-transmit {
          description
            "set exp on topmost label and send it";
          type ios-types:exp_value-type;
        }
      }
    }
    container conform-set-mpls-exp-topmost-transmit-table {
      container conform-action {
        description
          "action when rate is less than conform burst";
        leaf set-mpls-exp-topmost-transmit {
          description
            "set exp on topmost label and send it";
          type ios-types:exp_value-type;
        }
        leaf table {
          description
            "Specify table-map";
          type leafref {
            path "/ncs:devices/ncs:device/ncs:config/ios:native/ios:table-map/ios:name" {
              tailf:xpath-root 3;
            }
          }
        }
      }
    }
    container conform-set-prec-transmit {
      container conform-action {
        description
          "action when rate is less than conform burst";
        leaf set-prec-transmit {
          description
            "rewrite packet precedence and send it";
          type ios-types:prec_value-type;
        }
      }
    }
    container conform-set-prec-transmit-table {
      container conform-action {
        description
          "action when rate is less than conform burst";
        leaf set-prec-transmit {
          description
            "rewrite packet precedence and send it";
          type ios-types:prec_value-type;
        }
        leaf table {
          description
            "Specify table-map";
          type leafref {
            path "/ncs:devices/ncs:device/ncs:config/ios:native/ios:table-map/ios:name" {
              tailf:xpath-root 3;
            }
          }
        }
      }
    }
    container conform-set-qos-transmit {
      container conform-action {
        description
          "action when rate is less than conform burst";
        leaf set-qos-transmit {
          description
            "set qos-group and send it";
          type ios-types:qos_value-type;
        }
      }
    }
    container conform-set-qos-transmit-table {
      container conform-action {
        description
          "action when rate is less than conform burst";
        leaf set-qos-transmit {
          description
            "set qos-group and send it";
          type ios-types:qos_value-type;
        }
        leaf table {
          description
            "Specify table-map";
          type leafref {
            path "/ncs:devices/ncs:device/ncs:config/ios:native/ios:table-map/ios:name" {
              tailf:xpath-root 3;
            }
          }
        }
      }
    }
    container conform-transmit {
      container conform-action {
        description
          "action when rate is less than conform burst";
        uses police-action-transmit-grouping;
      }
    }
    container conform-drop {
      container conform-action {
        description
          "action when rate is less than conform burst";
        uses police-action-drop-grouping;
      }
    }
  }

  grouping police-exceed-action-grouping {
    container exceed-dscp {
      container exceed-action {
        description
          "action when rate is within conform and conform + exceed burst";
        leaf dscp {
          type ios-types:dscp-type;
        }
      }
    }
    container exceed-set-clp-transmit {
      container exceed-action {
        description
          "action when rate is within conform and conform + exceed burst";
        leaf set-clp-transmit {
          description
            "set atm clp and send it";
          type empty;
        }
      }
    }
    container exceed-set-cos-transmit {
      container exceed-action {
        description
          "action when rate is within conform and conform + exceed burst";
        leaf set-cos-transmit {
          description
            "rewrite packet cos and send it";
          type ios-types:cos_value-type;
        }
        leaf table {
          description
            "Specify table-map";
          type leafref {
            path "/ncs:devices/ncs:device/ncs:config/ios:native/ios:table-map/ios:name" {
              tailf:xpath-root 3;
            }
          }
        }
      }
    }
    container exceed-set-discard-class-transmit {
      container exceed-action {
        description
          "action when rate is within conform and conform + exceed burst";
        leaf set-discard-class-transmit {
          description
            "set discard-class and send it";
          type uint8 {
            range "0..7";
          }
        }
      }
    }
    container exceed-set-dscp-transmit {
      container exceed-action {
        description
          "action when rate is within conform and conform + exceed burst";
        container set-dscp-transmit {
          container dscp {
            leaf table {
              type enumeration {
                enum "policed-dscp";
              }
            }
          }
        }
      }
    }
    container exceed-set-dscp-transmit-table {
      container exceed-action {
        description
          "action when rate is within conform and conform + exceed burst";
        leaf set-dscp-transmit {
          description
            "set dscp and send it";
          type ios-types:dscp-type;
        }
        leaf table {
          description
            "Specify table-map";
          type leafref {
            path "/ncs:devices/ncs:device/ncs:config/ios:native/ios:table-map/ios:name" {
              tailf:xpath-root 3;
            }
          }
        }
      }
    }
    container exceed-set-frde-transmit {
      container exceed-action {
        description
          "action when rate is within conform and conform + exceed burst";
        leaf set-frde-transmit {
          description
            "set FR DE and send it";
          type empty;
        }
      }
    }
    container exceed-set-mpls-exp-imposition-transmit {
      container exceed-action {
        description
          "action when rate is within conform and conform + exceed burst";
        leaf set-mpls-exp-imposition-transmit {
          description
            "set exp at tag imposition and send it";
          type ios-types:exp_value-type;
        }
      }
    }
    container exceed-set-mpls-exp-topmost-transmit {
      container exceed-action {
        description
          "action when rate is within conform and conform + exceed burst";
        leaf set-mpls-exp-topmost-transmit {
          description
            "set exp on topmost label and send it";
          type ios-types:exp_value-type;
        }
      }
    }
    container exceed-set-prec-transmit {
      container exceed-action {
        description
          "action when rate is within conform and conform + exceed burst";
        leaf set-prec-transmit {
          description
            "rewrite packet precedence and send it";
          type ios-types:prec_value-type;
        }
        leaf table {
          description
            "Specify table-map";
          type leafref {
            path "/ncs:devices/ncs:device/ncs:config/ios:native/ios:table-map/ios:name" {
              tailf:xpath-root 3;
            }
          }
        }
      }
    }
    container exceed-set-qos-transmit {
      container exceed-action {
        description
          "action when rate is within conform and conform + exceed burst";
        leaf set-qos-transmit {
          description
            "set qos-group and send it";
          type ios-types:qos_value-type;
        }
      }
    }
    container exceed-transmit {
      container exceed-action {
        description
          "action when rate is within conform and conform + exceed burst";
        uses police-action-transmit-grouping;
      }
    }
    container exceed-drop {
      container exceed-action {
        description
          "action when rate is within conform and conform + exceed burst";
        uses police-action-drop-grouping;
      }
    }
  }

  grouping police-violate-action-grouping {
    container violate-set-clp-transmit {
      container violate-action {
        description
          "action when rate is greater than conform + exceed burst";
        leaf set-clp-transmit {
          description
            "set atm clp and send it";
          type empty;
        }
      }
    }
    container violate-set-cos-transmit {
      container violate-action {
        description
          "action when rate is greater than conform + exceed burst";
        leaf set-cos-transmit {
          description
            "rewrite packet cos and send it";
          type ios-types:cos_value-type;
        }
        leaf table {
          description
            "Specify table-map";
          type leafref {
            path "/ncs:devices/ncs:device/ncs:config/ios:native/ios:table-map/ios:name" {
              tailf:xpath-root 3;
            }
          }
        }
      }
    }
    container violate-set-discard-class-transmit {
      container violate-action {
        description
          "action when rate is greater than conform + exceed burst";
        leaf set-discard-class-transmit {
          description
            "set discard-class and send it";
          type uint8 {
            range "0..7";
          }
        }
      }
    }
    container violate-set-dscp-transmit {
      container violate-action {
        description
          "action when rate is greater than conform + exceed burst";
        leaf set-dscp-transmit {
          description
            "set dscp and send it";
          type ios-types:dscp-type;
        }
        leaf table {
          description
            "Specify table-map";
          type leafref {
            path "/ncs:devices/ncs:device/ncs:config/ios:native/ios:table-map/ios:name" {
              tailf:xpath-root 3;
            }
          }
        }
      }
    }
    container violate-set-frde-transmit {
      container violate-action {
        description
          "action when rate is greater than conform + exceed burst";
        leaf set-frde-transmit {
          description
            "set FR DE and send it";
          type empty;
        }
      }
    }
    container violate-set-mpls-exp-imposition-transmit {
      container violate-action {
        description
          "action when rate is greater than conform + exceed burst";
        leaf set-mpls-exp-imposition-transmit {
          description
            "set exp at tag imposition and send it";
          type ios-types:exp_value-type;
        }
      }
    }
    container violate-set-mpls-exp-topmost-transmit {
      container violate-action {
        description
          "action when rate is greater than conform + exceed burst";
        leaf set-mpls-exp-topmost-transmit {
          description
            "set exp on topmost label and send it";
          type ios-types:exp_value-type;
        }
      }
    }
    container violate-set-prec-transmit {
      container violate-action {
        description
          "action when rate is greater than conform + exceed burst";
        leaf set-prec-transmit {
          description
            "rewrite packet precedence and send it";
          type ios-types:prec_value-type;
        }
        leaf table {
          description
            "Specify table-map";
          type leafref {
            path "/ncs:devices/ncs:device/ncs:config/ios:native/ios:table-map/ios:name" {
              tailf:xpath-root 3;
            }
          }
        }
      }
    }
    container violate-set-qos-transmit {
      container violate-action {
        description
          "action when rate is greater than conform + exceed burst";
        leaf set-qos-transmit {
          description
            "set qos-group and send it";
          type ios-types:qos_value-type;
        }
      }
    }
    container violate-transmit {
      container violate-action {
        description
          "action when rate is greater than conform + exceed burst";
        uses police-action-transmit-grouping;
      }
    }
    container violate-drop {
      container violate-action {
        description
          "action when rate is greater than conform + exceed burst";
        uses police-action-drop-grouping;
      }
    }
  }

  grouping police-action-grouping {
    container actions {
      uses police-conform-action-grouping;
      uses police-exceed-action-grouping;
      uses police-violate-action-grouping;
    }
  }

  grouping random-detect-grouping {
    leaf min-threshold {
      type uint16 {
        range "1..4096";
      }
    }
    leaf max-threshold {
      type uint16 {
        range "1..4096";
      }
    }
    leaf denominator {
      type uint32 {
        range "1..65535";
      }
    }
  }

  grouping config-policy-map-grouping {
    list policy-map {
      description
        "Configure QoS Policy Map";
      key "name";
      leaf name {
        type string;
      }
      leaf type {
        description
          "type of the policy-map";
        type enumeration {
          enum "access-control";
          enum "appnav";
          enum "inspect";
          enum "control";
          enum "packet-service";
          enum "performance-monitor";
          enum "service";
          enum "service-chain";
        }
      }
      leaf subscriber {
        type empty;
      }
      leaf protocol {
        when "../type = 'inspect'" {
          tailf:xpath-root 3;
        }
        type enumeration {
          enum "http";
          enum "im";
          enum "imap";
          enum "p2p";
          enum "pop3";
          enum "smtp";
          enum "sunrpc";
        }
      }
      list event {
        description
          "The event type this control class-map triggers upon";
        key "event-type";
        leaf event-type {
          type enumeration {
            enum "aaa-available";
            enum "absolute-timeout";
            enum "agent-found";
            enum "authentication-failure";
            enum "authentication-success";
            enum "authorization-failure";
            enum "authorization-success";
            enum "identity-update";
            enum "inactivity-timeout";
            enum "remote-authentication-failure";
            enum "remote-authentication-success";
            enum "session-disconnected";
            enum "session-started";
            enum "tag-added";
            enum "tag-removed";
            enum "template-activated";
            enum "template-activation-failed";
            enum "template-deactivated";
            enum "template-deactivation-failed";
            enum "timer-expiry";
            enum "violation";
          }
        }
        leaf match-type {
          type enumeration {
            enum "match-all";
            enum "match-first";
          }
        }
        list class-number {
          description
            "class number, 1 for 1st class, 2 for 2nd...";
          key "number";
          leaf number {
            type uint8 {
              range "1..254";
            }
          }
          leaf class {
            description
              "The class type this control policy-map triggers upon";
            type union {
              type enumeration {
                enum "always";
              }
              type string;
            }
          }
          leaf execution-type {
            type enumeration {
              enum "do-all";
              enum "do-until-failure";
              enum "do-until-success";
            }
          }
          list action-number {
            description
              "action number, 1 for 1st class, 2 for 2nd...";
            key "number";
            leaf number {
              type uint8 {
                range "1..254";
              }
            }
            container terminate {
              description
                "terminate auth method";
              leaf dot1x {
                description
                  "dot1x method";
                type empty;
              }
              leaf mab {
                description
                  "mab method";
                type empty;
              }
              leaf webauth {
                description
                  "webauth method";
                type empty;
              }
            }
            leaf clear-session {
              description
                "clears an active session";
              type empty;
            }
            container resume {
              description
                "resume operation to be specified";
              leaf reauthentication {
                description
                  "resume reauthentication";
                type empty;
              }
            }
            leaf authentication-restart {
              description
                "restarts the auth sequence after the specified number of sec";
              type uint16 {
                range "1..65535";
              }
            }
            container pause {
              description
                "pause operation to be specified";
              leaf reauthentication {
                description
                  "pause reauthentication";
                type empty;
              }
            }
            leaf authorize {
              description
                "authorize session";
              type empty;
            }
            container activate {
              description
                "activate template or policy";
              leaf service-template {
                description
                  "activate service template";
                type string;
              }
            }
            container authenticate {
              description
                "authenticate a session";
              container using {
                description
                  "authenticate a session";
                leaf method {
                  type enumeration {
                    enum "dot1x";
                    enum "mab";
                    enum "webauth";
                  }
                }
                leaf both {
                  description
                    "Enabling Dot1x Authenticator & Supplicant";
                  type empty;
                }
                leaf retries {
                  description
                    "Number of times to retry failed authentications";
                  type uint8 {
                    range "1..5";
                  }
                }
                leaf retry-time {
                  description
                    "Time interval between retries";
                  type uint16 {
                    range "0..65535";
                  }
                }
                leaf priority {
                  description
                    "Method priority";
                  type uint8 {
                    range "1..254";
                  }
                }
              }
            }
          }
        }
      }
      list class {
        description
          "policy criteria";
        key "name";
        leaf name {
          type class-name-type;
        }
        leaf type {
          description
            "type of the class-map";
          type enumeration {
            enum "inspect";
          }
        }
        leaf insert-before {
          description
            "Insert the class before a specified class";
          when "../../type = 'appnav'" {
            tailf:xpath-root 3;
          }
          type string;
        }
        container appnav-policy {
          when "../../type = 'appnav'" {
            tailf:xpath-root 3;
          }
          list distribute {
            description
              "Distribute action";
            key "service-node-group";
            leaf service-node-group {
              description
                "Distribute to service-node-group";
              type string;
            }
            leaf insert-before {
              description
                "Insert before specific node";
              type string;
            }
          }
          leaf monitor-load {
            description
              "Monitor AO";
            when "../distribute" {
              tailf:xpath-root 3;
            }
            type enumeration {
              enum "MS-port-mapper";
              enum "cifs";
              enum "http";
              enum "ica";
              enum "mapi";
              enum "nfs";
              enum "ssl";
              enum "video";
            }
          }
          leaf pass-through {
            description
              "pass-through action";
            type empty;
          }
        }
        container policy {
          when "../../type = 'inspect'" {
            tailf:xpath-root 3;
          }
          leaf action {
            type enumeration {
              enum "cxsc";
              enum "drop";
              enum "inspect";
              enum "pass";
              enum "service-policy";
            }
          }
          leaf log {
            description
              "Send logging message for drop or pass";
            when "../action = 'drop'or ../action = 'pass'" {
              tailf:xpath-root 3;
            }
            type empty;
          }
          leaf parameter-map {
            when "../action = 'inspect' or ../action = 'cxsc'" {
              tailf:xpath-root 3;
            }
            type union {
              type string;
              type enumeration {
                enum "global";
                enum "gtp";
              }
            }
          }
          container dpi {
            when "../action = 'service-policy'" {
              tailf:xpath-root 3;
            }
            leaf type {
              type enumeration {
                enum "gtpv0";
                enum "gtpv1";
                enum "imap";
                enum "pop3";
                enum "smtp";
                enum "sunrpc";
              }
            }
            leaf policy-map {
              type string;
            }
          }
        }
        container pm-policy {
          when "../../type = 'performance-monitor'" {
            tailf:xpath-root 3;
          }
          container flow {
            description
              "Flow subcommands";
            leaf monitor {
              description
                "Apply a Flow Monitor";
              type string;
            }
          }
          container monitor {
            description
              "Monitor related parameters";
            container metric {
              description
                "Monitor metric";
              container rtp {
                description
                  "RTP metrics parameters";
                list clock-rate {
                  description
                    "RTP timestamp field's sampling frequency";
                  key "number";
                  leaf number {
                    type union {
                      type uint8 {
                        range "0..127";
                      }
                      type enumeration {
                        enum "celb";
                        enum "cn";
                        enum "default";
                        enum "dvi4";
                        enum "dvi4-2";
                        enum "dvi4-3";
                        enum "dvi4-4";
                        enum "g722";
                        enum "g723";
                        enum "g728";
                        enum "g729";
                        enum "gsm";
                        enum "h261";
                        enum "h263";
                        enum "jpeg";
                        enum "l16";
                        enum "l16-2";
                        enum "lpc";
                        enum "mp2t";
                        enum "mpa";
                        enum "mpv";
                        enum "nv";
                        enum "pcma";
                        enum "pcmu";
                        enum "qcelp";
                      }
                    }
                  }
                  leaf frequency {
                    type uint32 {
                      range "1000..192000";
                    }
                  }
                }
              }
            }
          }
          list react {
            description
              "Configure threshold crossing actions";
            key "id";
            leaf id {
              type uint16;
            }
            leaf mode {
              type enumeration {
                enum "media-stop";
                enum "mrv";
                enum "rtp-jitter-average";
                enum "transport-packets-lost-rate";
              }
            }
            leaf description {
              description
                "Description for the instance";
              type string;
            }
            container action {
              description
                "Config react action";
              leaf snmp {
                description
                  "SNMP is notified of the event";
                type empty;
              }
              leaf syslog {
                description
                  "The threshold-crossing event is logged to syslog";
                type empty;
              }
            }
            container alarm {
              description
                "Config react alarm";
              leaf severity {
                description
                  "Alarm severity - default level none";
                type enumeration {
                  enum "alert";
                  enum "critical";
                  enum "emergency";
                  enum "error";
                  enum "info";
                }
              }
              container type {
                description
                  "Alarm raised type - for each flow or a group";
                leaf discrete {
                  description
                    "Alert for each flow within the class";
                  type empty;
                }
                container grouped {
                  description
                    "Alert if more than one flow cross the threshold";
                  leaf count {
                    description
                      "Number of flows in the group cross the threshold";
                    type uint16;
                  }
                  leaf percent {
                    description
                      "Percent of flows in the group cross the threshold";
                    type uint8 {
                      range "1..100";
                    }
                  }
                }
              }
            }
            container threshold {
              description
                "Config react threshold";
              container value {
                description
                  "Range of percentage loss that would trigger the alarm";
                leaf ge {
                  description
                    "greater and equal to";
                  type string;
                }
                leaf gt {
                  description
                    "greater than";
                  type string;
                }
                leaf le {
                  description
                    "less and equal to";
                  type string;
                }
                leaf lt {
                  description
                    "less than";
                  type string;
                }
                container range {
                  description
                    "threshold within the range of";
                  leaf low {
                    type string;
                  }
                  leaf high {
                    type string;
                  }
                }
              }
            }
          }
        }
        container inspect-police {
          when "../policy/action = 'inspect'" {
            tailf:xpath-root 3;
          }
          container police {
            description
              "Police";
            leaf rate {
              description
                "Specify police rate";
              type uint32 {
                range "8000..2000000000";
              }
            }
            leaf burst {
              description
                "Specify 'burst' parameter";
              type uint32 {
                range "1000..512000000";
              }
            }
          }
        }
        list action-list {
          key "action-type";
          ordered-by user;
          leaf action-type {
            type policy-action-type;
          }
          choice action-param {
            case bandwidth-case {
              container bandwidth {
                when "../action-type = 'bandwidth'" {
                  tailf:xpath-root 3;
                }
                leaf bits {
                  type uint32 {
                    range "8..2000000";
                  }
                }
                leaf percent {
                  description
                    "% of total Bandwidth";
                  type ios-types:percentage;
                }
                container remaining {
                  description
                    "% of the remaining bandwidth";
                  leaf rem-option {
                    type enumeration {
                      enum "percent";
                      enum "ratio";
                    }
                  }
                  leaf percent {
                    description
                      "% of the remaining bandwidth";
                    when "../rem-option='percent'" {
                      tailf:xpath-root 3;
                    }
                    type ios-types:percentage;
                  }
                  leaf ratio {
                    description
                      "ratio for sharing excess bandwidth";
                    when "../rem-option='ratio'" {
                      tailf:xpath-root 3;
                    }
                    type uint16;
                  }
                  container account {
                    description
                      "Overhead Accounting";
                    when "../rem-option = 'percent' or ../rem-option = 'ratio'" {
                      tailf:xpath-root 3;
                    }
                    leaf user-defined {
                      description
                        "Offset Size";
                      type int32 {
                        range "-1000000..1000000";
                      }
                    }
                  }
                }
              }
            }
            case compression-case {
              container compression {
                when "../action-type = 'compression'" {
                  tailf:xpath-root 3;
                }
                container header {
                  description
                    "configure header compression";
                  presence "configure header compression";
                  leaf ip {
                    description
                      "configure ip header compression";
                    type enumeration {
                      enum "rtp";
                      enum "tcp";
                    }
                  }
                }
              }
            }
            case estimate-case {
              container estimate {
                when "../action-type = 'estimate'" {
                  tailf:xpath-root 3;
                }
                container bandwidth {
                  presence "bandwidth required to service this class";
                  description
                    "bandwidth required to service this class";
                  container delay-one-in {
                    description
                      "specify QoS target delay";
                    leaf doi {
                      type uint32 {
                        range "50..1000000";
                      }
                    }
                    leaf milliseconds {
                      type uint32 {
                        range "8..1000";
                      }
                    }
                  }
                  leaf drop-one-in {
                    description
                      "specify QoS target loss rate";
                    type uint32;
                  }
                }
              }
            }
            case forward-case {
              container forward {
                when "../action-type = 'forward'" {
                  tailf:xpath-root 3;
                }
                leaf service-path {
                  description
                    "Service Path Entries";
                  type uint32 {
                    range "0..16777215";
                  }
                }
                leaf service-index {
                  description
                    "Service Index";
                  type uint8 {
                    range "2..255";
                  }
                }
              }
            }
            case fair-queue-case {
              container fair-queue {
                when "../action-type = 'fair-queue'" {
                  tailf:xpath-root 3;
                }
                leaf dynamic-queues {
                  type uint32 {
                    range "16|32|64|128|256|512|1024|2048|4096";
                  }
                }
                leaf queue-limit {
                  description
                    "per flow queue limit";
                  type uint16 {
                    range "1..32768";
                  }
                }
              }
            }
            case netflow-sampler-case {
              leaf netflow-sampler {
                when "../action-type = 'netflow-sampler'" {
                  tailf:xpath-root 3;
                }
                type string;
              }
            }
            case police-case {
              choice police-choice {
                case police-aggregate-case {
                  container police-aggregate {
                    container police {
                      when "../../action-type = 'police'" {
                        tailf:xpath-root 3;
                      }
                      leaf aggregate {
                        description
                          "Choose aggregate policer for current class";
                        type string;
                      }
                    }
                  }
                }
                case police-policy-map-case {
                  container police-policy-map {
                    container police {
                      when "../../action-type = 'police'" {
                        tailf:xpath-root 3;
                      }
                      leaf cir {
                        description
                          "Committed information rate";
                        type police-bps-type;
                      }
                      leaf bc {
                        description
                          "Conform burst";
                        type police-burst-type;
                      }
                      leaf be {
                        description
                          "Excess burst";
                        when "../bc" {
                          tailf:xpath-root 3;
                        }
                        type police-burst-type;
                      }
                      leaf pir {
                        description
                          "Peak Information Rate";
                        type police-bps-type;
                      }
                      container pir-be {
                        when "../pir" {
                          tailf:xpath-root 3;
                        }
                        leaf be {
                          description
                            "Excess burst";
                          type police-burst-type;
                        }
                      }
                      uses police-action-grouping;
                    }
                  }
                }
                case police-cir-percent-case {
                  container police-cir-percent {
                    container police {
                      when "../../action-type = 'police'" {
                        tailf:xpath-root 3;
                      }
                      container cir {
                        description
                          "Committed information rate";
                        container percent {
                          description
                            "% of interface bandwidth for Committed information rate";
                          leaf percentage {
                            type ios-types:percentage;
                          }
                          leaf bc {
                            description
                              "Conform burst";
                            type uint16;
                          }
                          container bc-ms {
                            when "../bc" {
                              tailf:xpath-root 3;
                            }
                            leaf ms {
                              description
                                "Milli seconds";
                              type empty;
                            }
                          }
                          leaf be {
                            when "../bc-ms/ms" {
                              tailf:xpath-root 3;
                            }
                            type uint16;
                          }
                          container be-ms {
                            when "../be" {
                              tailf:xpath-root 3;
                            }
                            leaf ms {
                              description
                                "Milli seconds";
                              type empty;
                            }
                          }
                          container pir {
                            description
                              "Peak Information Rate";
                            leaf percent {
                              description
                                "% of interface bandwidth for Peak Information Rate";
                              type ios-types:percentage;
                            }
                          }
                          container pir-be {
                            when "../pir" {
                              tailf:xpath-root 3;
                            }
                            leaf be {
                              description
                                "Excess burst";
                              type uint16;
                            }
                          }
                          container pir-be-ms {
                            when "../pir-be/be" {
                              tailf:xpath-root 3;
                            }
                            leaf ms {
                              description
                                "Milli seconds";
                              type empty;
                            }
                          }
                          uses police-action-grouping;
                        }
                      }
                    }
                  }
                }
                case police-rate-unit-case {
                  container police-rate-unit {
                    container police {
                      when "../../action-type = 'police'" {
                        tailf:xpath-root 3;
                      }
                      container rate {
                        description
                          "Specify police rate";
                        leaf units {
                          type uint64;
                        }
                        leaf xps {
                          type police-pps-bps-type;
                        }
                        container burst {
                          description
                            "Specify 'burst' parameter";
                          leaf burst-value {
                            type uint32;
                          }
                          leaf burst-type {
                            type police-packets-bytes-type;
                          }
                        }
                        container peak-rate {
                          description
                            "Specify peak rate";
                          leaf peak-rate-value {
                            type uint32 {
                              range "1..512000000";
                            }
                          }
                          leaf xps {
                            type police-pps-bps-type;
                          }
                        }
                        container peak-burst {
                          description
                            "Specify 'peak-burst' parameter for peak-rate";
                          leaf burst-value {
                            type uint32;
                          }
                          leaf burst-type {
                            type police-packets-bytes-type;
                          }
                        }
                        uses police-action-grouping;
                      }
                    }
                  }
                }
                case police-rate-percent-case {
                  container police-rate-percent {
                    container police {
                      when "../../action-type = 'police'" {
                        tailf:xpath-root 3;
                      }
                      container rate {
                        description
                          "Specify police rate";
                        container percent {
                          description
                            "% of interface bandwidth for rate";
                          leaf percentage {
                            type ios-types:percentage;
                          }
                          leaf burst {
                            description
                              "Specify 'burst' parameter";
                            type uint16;
                          }
                          leaf ms {
                            description
                              "Treat 'burst' value in milliseconds";
                            when "../burst" {
                              tailf:xpath-root 3;
                            }
                            type empty;
                          }
                          container peak-rate {
                            description
                              "Specify peak rate";
                            leaf percent {
                              description
                                "% of interface bandwidth for peak-rate";
                              type ios-types:percentage;
                            }
                          }
                          leaf peak-burst {
                            description
                              "Specify 'peak-burst' parameter for 'peak-rate'";
                            type uint16;
                          }
                          container peak-burst-ms {
                            when "../peak-burst" {
                              tailf:xpath-root 3;
                            }
                            leaf ms {
                              description
                                "Milli seconds";
                              type empty;
                            }
                          }
                          uses police-action-grouping;
                        }
                      }
                    }
                  }
                }
                case police-rate-pdp-case {
                  container police-rate-pdp {
                    container police {
                      when "../../action-type = 'police'" {
                        tailf:xpath-root 3;
                      }
                      container rate {
                        description
                          "Specify police rate";
                        container pdp {
                          description
                            "% of interface bandwidth for rate";
                          leaf burst {
                            description
                              "Conform burst";
                            type police-burst-type;
                          }
                          leaf peak-rate {
                            description
                              "Specify peak rate";
                            type enumeration {
                              enum "pdp";
                            }
                          }
                          leaf peak-burst {
                            description
                              "Specify 'peak-burst' parameter for 'peak-rate'";
                            when "../peak-rate" {
                              tailf:xpath-root 3;
                            }
                            type police-burst-type;
                          }
                          uses police-action-grouping;
                        }
                      }
                    }
                  }
                }
                case police-target-bitrate-case {
                  container police-target-bitrate {
                    container police {
                      when "../../action-type = 'police'" {
                        tailf:xpath-root 3;
                      }
                      leaf bit-rate {
                        description
                          "Target bit rate (bits per second) (postfix k, m, g optional),decimal point allowed";
                        type uint64 {
                          range "8000..10000000000";
                        }
                      }
                      leaf confirm_burst-byte {
                        description
                          "Burst Byte";
                        type uint64 {
                          range "100..512000000";
                        }
                      }
                      leaf excess_burst-byte {
                        description
                          "Burst Byte";
                        type uint64 {
                          range "100..512000000";
                        }
                      }
                      leaf conform-action {
                        description
                          "action when rate is less than conform burst";
                        type empty;
                      }
                      leaf transmit {
                        description
                          "transmit packet";
                        type empty;
                      }
                      leaf exceed-action {
                        description
                          "action when rate is within conform and conform + exceed burst";
                        type empty;
                      }
                      leaf drop {
                        description
                          "drop packet";
                        type empty;
                      }
                      leaf set-dscp-transmit {
                        description
                          "set dscp and send it";
                        type empty;
                      }
                      leaf dscp {
                        description
                          "Set packet dscp from dscp";
                        type empty;
                      }
                      leaf table {
                        description
                          "Specify table-map";
                        type string;
                      }
                      container actions {
                        uses police-conform-action-grouping;
                        uses police-exceed-action-grouping;
                        uses police-violate-action-grouping;
                      }
                    }
                  }
                }
                case police-flow-case {
                  container police-flow {
                    container police {
                      when "../../action-type = 'police'" {
                        tailf:xpath-root 3;
                      }
                      container flow {
                        description
                          "police each flow";
                        leaf mask {
                          description
                            "flow mask to be used for policing";
                          type enumeration {
                            enum "dest-only";
                            enum "full-flow";
                            enum "src-only";
                          }
                        }
                        leaf bps {
                          type police-bps-type;
                        }
                        leaf burst-normal {
                          type police-burst-type;
                          when "../bps" {
                            tailf:xpath-root 3;
                          }
                        }
                        uses police-action-grouping;
                      }
                    }
                  }
                }
                case police-catalyst-case {
                  container police-catalyst {
                    container police {
                      when "../../action-type = 'police'" {
                        tailf:xpath-root 3;
                      }
                      leaf bps-value {
                        type string;
                      }
                      leaf bps {
                        type empty;
                      }
                      leaf byte-value {
                        type string;
                      }
                      leaf byte {
                        type empty;
                      }
                      container actions {
                        uses police-conform-action-grouping;
                        uses police-exceed-action-grouping;
                        uses police-violate-action-grouping;
                      }
                    }
                  }
                }
                case police-switch-case {
                  container police-switch {
                    container police {
                      when "../../action-type = 'police'" {
                        tailf:xpath-root 3;
                      }
                      leaf cir {
                        type uint32 {
                          range "8000..1000000000";
                        }
                      }
                      leaf bc {
                        type uint32 {
                          range "8000..2000000";
                        }
                      }
                      leaf exceed-action {
                        description
                          "action when rate is exceeded";
                        type enumeration {
                          enum "drop";
                          enum "policed-dscp-transmit";
                        }
                      }
                    }
                  }
                }
              }
            }
            case priority-case {
              container priority {
                when "../action-type = 'priority'" {
                  tailf:xpath-root 3;
                }
                leaf level {
                  description
                    "Multi-Level Priority Queue";
                  type uint8 {
                    range "1..2";
                  }
                }
                choice priority-type {
                  leaf kilo-bits {
                    type uint32 {
                      range "8..2000000";
                    }
                  }
                  leaf percent {
                    description
                      "% of total bandwidth";
                    type uint16 {
                      range "1..100";
                    }
                  }
                }
                leaf burst {
                  type uint32 {
                    range "32..64000000";
                  }
                }
              }
            }
            case queue-buffers-case {
              container queue-buffers {
                when "../action-type = 'queue-buffers'" {
                  tailf:xpath-root 3;
                }
                leaf ratio {
                  description
                    "Relative buffer size for queue";
                  type uint8 {
                    range "0..100";
                  }
                }
              }
            }
            case queue-limit-case {
              container queue-limit {
                when "../action-type = 'queue-limit'" {
                  tailf:xpath-root 3;
                }
                leaf queue-limit-value {
                  type uint32 {
                    range "1..8192000";
                  }
                }
                leaf queue-limit-type {
                  type enumeration {
                    enum "bytes";
                    enum "ms";
                    enum "packets";
                    enum "us";
                  }
                }
              }
              container queue-limit-dscp {
                when "../action-type = 'queue-limit'" {
                  tailf:xpath-root 3;
                }
                list dscp {
                  description
                    "parameters for each dscp value";
                  key "dscp-val";
                  leaf dscp-val {
                    type ios-types:dscp-type;
                  }
                  leaf values {
                    description
                      "dscp values";
                    type empty;
                  }
                  leaf dscp-val1 {
                    type ios-types:dscp-type;
                  }
                  leaf percent {
                    description
                      "% of threshold";
                    type uint8 {
                      range "0..100";
                    }
                  }
                }
              }
            }
            case random-detect {
              container random-detect {
                when "../action-type = 'random-detect'" {
                  tailf:xpath-root 3;
                }
                container aggregate {
                  description
                    "aggregate subclasses";
                  presence "true";
                  leaf minimum-thresh {
                    description
                      "minimum threshold for red aggregate";
                    type uint32 {
                      range "0..1000000";
                    }
                  }
                  leaf maximum-thresh {
                    description
                      "maximum threshold for red aggregate";
                    type uint32 {
                      range "0..1000000";
                    }
                  }
                  leaf mark-probability {
                    description
                      "mark-probability for red aggregate";
                    type empty;
                  }
                  leaf denominator {
                    type uint32 {
                      range "0..65535";
                    }
                  }
                }
                container discard-class {
                  description
                    "parameters for each discard-class value";
                  leaf dclass {
                    type uint16 {
                      range "0..7";
                    }
                  }
                  uses random-detect-grouping;
                }
                leaf discard-class-based {
                  description
                    "Enable discard-class-based WRED as drop policy";
                  type empty;
                }
                leaf dscp-based {
                  description
                    "Enable dscp-based WRED as drop policy";
                  type empty;
                }
                list dscp {
                  description
                    "parameters for each dscp value";
                  key "dscp-val";
                  leaf dscp-val {
                    type ios-types:dscp-type;
                  }
                  uses random-detect-grouping;
                }
                leaf ecn {
                  description
                    "explicit congestion notification";
                  type empty;
                }
                leaf exponential-weighting-constant {
                  description
                    "weight for mean queue depth calculation";
                  type uint16 {
                    range "1..16";
                  }
                }
                leaf prec-based {
                  description
                    "Enable precedence-based WRED as drop policy";
                  type empty;
                }
                container precedence {
                  description
                    "parameters for each precedence value";
                  leaf prec {
                    type precedence-type2;
                  }
                  uses random-detect-grouping;
                }
              }
            }
            case service-policy-case {
              leaf service-policy {
                type string;
              }
            }
            case set-case {
              container set {
                when "../action-type = 'set'" {
                  tailf:xpath-root 3;
                }
                leaf atm-clp {
                  description
                    "Set ATM CLP bit to 1";
                  type empty;
                }
                container cos {
                  description
                    "Set IEEE 802.1Q/ISL class of service/user priority";
                  choice cos-type {
                    case a {
                      leaf val {
                        type uint16 {
                          range "0..7";
                        }
                      }
                    }
                    case b {
                      leaf pack {
                        type enumeration {
                          enum "dscp";
                          enum "precedence";
                          enum "cos";
                          enum "qos-group";
                          enum "wlan";
                        }
                      }
                      leaf user-priority {
                        description
                          "Set value from WLAN user-priority";
                        when "../pack = 'wlan'" {
                          tailf:xpath-root 3;
                        }
                        type empty;
                      }
                      leaf table {
                        description
                          "Set codepoint value based on tablemap.";
                        type string;
                      }
                    }
                  }
                }
                leaf discard-class {
                  description
                    "Discard behavior identifier";
                  type uint16 {
                    range "0..7";
                  }
                }
                container dscp {
                  description
                    "Set DSCP in IP(v4) and IPv6 packets";
                  container dscp {
                    description
                      "Set packet dscp from dscp";
                    presence "true";
                    leaf table {
                      description
                        "Set packet dscp from dscp based on table map.";
                      type string;
                    }
                  }
                  leaf tunnel {
                    description
                      "set tunnel packet dscp";
                    type empty;
                  }
                  leaf dscp-val {
                    type ios-types:dscp-type;
                  }
                }
                leaf fr-de {
                  description
                    "Set FR DE bit to 1";
                  type empty;
                }
                container ip {
                  description
                    "Set IP specific values";
                  choice ip-choice {
                    container dscp {
                      description
                        "Set IP DSCP (DiffServ CodePointint)";
                      leaf tunnel {
                        description
                          "set tunnel packet dscp";
                        type empty;
                      }
                      leaf dscp-val {
                        type ios-types:dscp-type;
                      }
                    }
                    container precedence {
                      description
                        "Set IP precedence";
                      presence "Set IP precedence";
                      leaf precedence-val {
                        type ios-types:precedence-type;
                      }
                    }
                  }
                }
                container mpls {
                  description
                    "Set MPLS specific values";
                  container experimental {
                    description
                      "Set Experimental value";
                    container imposition {
                      description
                        "Set Experimental value at tag imposition";
                      leaf exp-value {
                        type uint8 {
                          range "0..7";
                        }
                      }
                    }
                    container topmost {
                      description
                        "Set Experimental value  on topmost label";
                      leaf exp-value {
                        type uint8 {
                          range "0..7";
                        }
                      }
                    }
                  }
                }
                container qos-group {
                  description
                    "Set QoS Group";
                  leaf qos-group-value {
                    type uint8 {
                      range "0..99";
                    }
                  }
                }
              }
            }
            case shape-case {
              container shape {
                when "../action-type = 'shape'" {
                  tailf:xpath-root 3;
                }
                leaf adaptive {
                  description
                    "Enable Traffic Shaping adaptation to BECN";
                  type uint32 {
                    range "8000..154400000";
                  }
                }
                container average {
                  description
                    "configure token bucket: CIR (bps) [Bc (bits) [Be (bits)]], send out Bc only per interval";
                  choice average-choice {
                    case a {
                      leaf bit-rate {
                        type uint64;
                      }
                      leaf bits-per-interval-sustained {
                        type uint32 {
                          range "256..154400000";
                        }
                      }
                      leaf bits-per-interval-excess {
                        when "../bits-per-interval-sustained" {
                          tailf:xpath-root 3;
                        }
                        type uint32 {
                          range "0..154400000";
                        }
                      }
                      container account {
                        description
                          "Overhead Accounting";
                        leaf user-defined {
                          description
                            "Offset Size";
                          type int32 {
                            range "-1000000..1000000";
                          }
                        }
                      }
                    }
                    case b {
                      leaf percent {
                        description
                          "% of interface bandwidth for Committed information rate";
                        type ios-types:percentage;
                      }
                      leaf burst-size-sustained {
                        type uint16 {
                          range "10..2000";
                        }
                      }
                      leaf ms {
                        description
                          "milliseconds";
                        type empty;
                      }
                      container bse {
                        leaf burst-size-excess {
                          type uint16 {
                            range "10..2000";
                          }
                        }
                        leaf ms {
                          description
                            "milliseconds";
                          type empty;
                        }
                      }
                    }
                  }
                }
                leaf fecn-adapt {
                  description
                    "Enable Traffic Shaping reflection of FECN as BECN";
                  type empty;
                }
                container fr-voice-adapt {
                  description
                    "Enable rate adjustment depending on voice presence";
                  presence "Enable rate adjustment depending on voice presence";
                  leaf deactivation {
                    type uint16 {
                      range "1..10000";
                    }
                  }
                }
                leaf max-buffers {
                  description
                    "Set Maximum Buffer Limit";
                  type uint16 {
                    range "1..4096";
                  }
                }
              }
            }
            case trust-case {
              leaf trust {
                when "../action-type = 'trust'" {
                  tailf:xpath-root 3;
                }
                type enumeration {
                  enum "cos";
                  enum "dscp";
                  enum "ip-precedence";
                }
              }
            }
          }
        }
      }
      leaf description {
        description
          "Policy-Map description";
        type string {
          length "1..200";
        }
      }
      leaf sequence-interval {
        description
          "Enable sequence number capability";
        when "../type = 'appnav'" {
          tailf:xpath-root 3;
        }
        type uint16;
      }
    }
  }

  grouping class-map-match-result-type-grouping {
    leaf aaa-timeout {
      description
        "aaa timeout type";
      type empty;
    }
    leaf agent-not-found {
      description
        "agent not found type";
      type empty;
    }
    leaf authoritative {
      description
        "failure type";
      type empty;
    }
    leaf method-timeout {
      description
        "method_timeout type";
      type empty;
    }
    leaf none {
      description
        "no type";
      type empty;
    }
    leaf success {
      description
        "success type";
      type empty;
    }
  }

  grouping class-map-control-filter-grouping {
    list activated-service-template {
      description
        "match name of service template activated on session";
      key "service-name";
      leaf service-name {
        description
          "Enter service name";
        type string;
      }
    }
    container authorization-status {
      description
        "match the authorization status of the session";
      leaf authorized {
        description
          "authorized";
        type empty;
      }
      leaf unauthorized {
        description
          "unauthorized";
        type empty;
      }
    }
    container authorizing-method-priority {
      description
        "match the priority against the authorizing method's priority";
      leaf eq {
        description
          "equal to";
        type uint8 {
          range "1..254";
        }
      }
      leaf gt {
        description
          "greater than";
        type uint8 {
          range "1..254";
        }
      }
      leaf lt {
        description
          "less than";
        type uint8 {
          range "1..254";
        }
      }
    }
    container method {
      description
        "match the type of authentication method from an event";
      leaf dot1x {
        description
          "dot1x";
        type empty;
      }
      leaf mab {
        description
          "mab";
        type empty;
      }
      leaf webauth {
        description
          "webauth";
        type empty;
      }
    }
    container result-type {
      description
        "match the result type, optionally for a specific method";
      container method {
        description
          "match the result of a particular method";
        container dot1x {
          description
            "dot1x result";
          uses class-map-match-result-type-grouping;
        }
        container mab {
          description
            "mab result";
          uses class-map-match-result-type-grouping;
        }
        container webauth {
          description
            "webauth result";
          uses class-map-match-result-type-grouping;
        }
      }
      uses class-map-match-result-type-grouping;
    }
  }

  grouping class-map-match-grouping {
    container current-method-priority {
      description
        "match the priority against the current method's priority";
      leaf eq {
        description
          "equal to";
        type uint8 {
          range "1..254";
        }
      }
      leaf gt {
        description
          "greater than";
        type uint8 {
          range "1..254";
        }
      }
      leaf lt {
        description
          "less than";
        type uint8 {
          range "1..254";
        }
      }
    }
    container application {
      description
        "Application to match";
      container application-group {
        description
          "Application Group to match";
        leaf telepresence-group {
          description
            "Telepresence Group";
          type empty;
        }
        leaf vmware-group {
          description
            "VMWARE Group";
          type empty;
        }
        leaf webex-group {
          description
            "WebEx Group";
          type empty;
        }
      }
      container attribute {
        description
          "Application attribute to match";
        leaf media-type {
          description
            "Media type attribute to match";
          type enumeration {
            enum "audio";
            enum "audio-video";
            enum "control";
            enum "data";
            enum "video";
          }
        }
      }
    }
    container access-group {
      description
        "Access group";
      leaf index {
        type uint32 {
          range "1..2699";
        }
      }
      leaf-list name {
        description
          "Named Access List";
        type string;
      }
    }
    leaf any {
      description
        "Any packets";
      type empty;
    }
    leaf-list class-map {
      description
        "Class map";
      type string;
    }
    leaf-list cos {
      description
        "IEEE 802.1Q/ISL class of service/user priority values";
      type uint8 {
        range "0..7";
      }
    }
    container destination-address {
      description
        "Destination address";
      leaf-list mac {
        description
          "MAC address";
        type yang:mac-address;
      }
    }
    leaf-list discard-class {
      description
        "Discard behavior identifier";
      type uint8 {
        range "0..7";
      }
    }
    leaf-list dscp {
      description
        "Match DSCP in IP(v4) and IPv6 packets";
      type ios-types:dscp-type;
    }
    leaf fr-de {
      description
        "Match on Frame-relay DE bit";
      type empty;
    }
    leaf-list fr-dlci {
      description
        "Match on fr-dlci";
      type uint16 {
        range "16..1007";
      }
    }
    container group-object {
      description
        "Match object-group";
      container security {
        description
          "Match object-group security";
        leaf-list source {
          description
            "Match source object-group security";
          type string;
        }
        leaf-list destination {
          description
            "Match destination object-group security";
          type string;
        }
      }
    }
    leaf-list input-interface {
      description
        "Select an input interface to match";
      type string;
    }
    container ip {
      description
        "IP specific values";
      leaf-list dscp {
        description
          "Match IP DSCP (DiffServ CodePoints)";
        type ios-types:dscp-type;
      }
      leaf-list precedence {
        description
          "Match IP precedence";
        type ios-types:precedence-type;
      }
      list rtp {
        description
          "Match RTP port nos";
        key "port1 port2";
        leaf port1 {
          type uint16 {
            range "2000..65535";
          }
        }
        leaf port2 {
          type uint16 {
            range "0..16383";
          }
        }
      }
    }
    leaf non-client-nrt {
      type empty;
    }
    container mpls {
      description
        "Multi Protocol Label Switching specific values";
      container experimental {
        description
          "Match MPLS experimental";
        leaf-list topmost {
          description
            "Match MPLS experimental value on topmost label";
          type uint8 {
            range "0..7";
          }
        }
      }
    }
    container packet {
      description
        "Layer 3 Packet length";
      container length {
        description
          "Layer 3 Packet length";
        leaf max {
          description
            "Maximum length of packet";
          type uint16 {
            range "1..2000";
          }
        }
        leaf min {
          description
            "Minimum length of packet";
          type uint16 {
            range "1..2000";
          }
        }
      }
    }
    leaf-list precedence {
      description
        "Match Precedence in IP(v4) and IPv6 packets";
      type ios-types:precedence-type;
    }
    container protocol {
      description
        "Protocol";
      leaf protocols {
        type enumeration {
          enum "x802-11-iapp";
          enum "ace-svr";
          enum "aol";
          enum "appleqtc";
          enum "biff";
          enum "bittorrent";
          enum "bootpc";
          enum "bootps";
          enum "cddbp";
          enum "cifs";
          enum "cisco-fna";
          enum "cisco-net-mgmt";
          enum "cisco-svcs";
          enum "cisco-sys";
          enum "cisco-tdp";
          enum "cisco-tna";
          enum "citriximaclient";
          enum "clp";
          enum "creativepartnr";
          enum "creativeserver";
          enum "daytime";
          enum "dbase";
          enum "dbcontrol_agent";
          enum "ddns-v3";
          enum "dhcp-failover";
          enum "directconnect";
          enum "discard";
          enum "dnsix";
          enum "echo";
          enum "entrust-svc-hdlr";
          enum "entrust-svcs";
          enum "exec";
          enum "fcip-port";
          enum "ftps";
          enum "gdoi";
          enum "giop";
          enum "gtpv0";
          enum "gtpv1";
          enum "h225ras";
          enum "h323callsigalt";
          enum "hp-alarm-mgr";
          enum "hp-collector";
          enum "hp-managed-node";
          enum "hsrp";
          enum "https";
          enum "ica";
          enum "icabrowser";
          enum "ident";
          enum "igmpv3lite";
          enum "imap3";
          enum "imaps";
          enum "ipass";
          enum "ipsec-msft";
          enum "irc-serv";
          enum "ircs";
          enum "ircu";
          enum "isakmp";
          enum "iscsi";
          enum "iscsi-target";
          enum "kermit";
          enum "ldap-admin";
          enum "ldaps";
          enum "login";
          enum "lotusmtap";
          enum "lotusnote";
          enum "mapi";
          enum "ms-ad-rep";
          enum "ms-exch-nspi";
          enum "ms-frs";
          enum "ms-frsapi";
          enum "ms-rfr";
          enum "msn-messenger";
          enum "netlogon";
          enum "microsoft-ds";
          enum "ms-cluster-net";
          enum "ms-dotnetster";
          enum "ms-sna";
          enum "ms-sql";
          enum "ms-sql-m";
          enum "msexch-routing";
          enum "msnmsgr";
          enum "msrpc";
          enum "mysql";
          enum "n2h2server";
          enum "ncp";
          enum "net8-cman";
          enum "netbios-dgm";
          enum "netbios-ns";
          enum "netbios-ssn";
          enum "netstat";
          enum "oem-agent";
          enum "oracle";
          enum "oracle-em-vp";
          enum "oraclenames";
          enum "orasrv";
          enum "pcanywheredata";
          enum "pcanywherestat";
          enum "pop3s";
          enum "pwdgen";
          enum "qmtp";
          enum "r-winsock";
          enum "radius";
          enum "rdb-dbs-disp";
          enum "realmedia";
          enum "realsecure";
          enum "router";
          enum "rsvp-encap";
          enum "rsvp_tunnel";
          enum "rtc-pm-port";
          enum "rtelnet";
          enum "send";
          enum "shell";
          enum "sip-tls";
          enum "sms";
          enum "smtp";
          enum "snmptrap";
          enum "sql-net";
          enum "sqlserv";
          enum "sqlsrv";
          enum "sshell";
          enum "ssp";
          enum "syslog-conn";
          enum "tacacs";
          enum "tacacs-ds";
          enum "tarantella";
          enum "tcp";
          enum "telnets";
          enum "time";
          enum "timed";
          enum "tr-rsrb";
          enum "ttc";
          enum "udp";
          enum "uucp";
          enum "vqp";
          enum "webster";
          enum "who";
          enum "wins";
          enum "x11";
          enum "xdmcp";
          enum "ymsgr";
          enum "aarp";
          enum "appletalk";
          enum "arp";
          enum "bgp";
          enum "bridge";
          enum "bstun";
          enum "cdp";
        }
      }
      container citrix {
        description
          "Citrix Systems ICA protocol";
        presence "enable citrix system protocol matching";
        leaf ica-tag {
          description
            "Citrix ICA tag 0-high 1-medium 2-low 3-background";
          type string;
        }
      }
      leaf clns {
        description
          "ISO CLNS";
        type empty;
      }
      leaf clns_es {
        description
          "ISO CLNS End System";
        type empty;
      }
      leaf clns_is {
        description
          "ISO CLNS Intermediate System";
        type empty;
      }
      leaf cmns {
        description
          "ISO CMNS";
        type empty;
      }
      leaf compressedtcp {
        description
          "Compressed TCP (VJ";
        type empty;
      }
      leaf cuseeme {
        description
          "CU-SeeMe desktop video conference";
        type empty;
      }
      leaf decnet {
        description
          "DECnet";
        type empty;
      }
      leaf decnet_node {
        description
          "DECnet Node";
        type empty;
      }
      leaf decnet_router-l1 {
        description
          "DECnet Router L1";
        type empty;
      }
      leaf decnet_router-l2 {
        description
          "DECnet Router L2";
        type empty;
      }
      leaf dhcp {
        description
          "Dynamic Host Configuration";
        type empty;
      }
      leaf dlsw {
        type empty;
      }
      leaf dns {
        type empty;
      }
      leaf edonkey {
        type empty;
      }
      leaf egp {
        type empty;
      }
      leaf eigrp {
        type empty;
      }
      leaf exchange {
        type empty;
      }
      container fasttrack {
        description
          "FastTrack Traffic - KaZaA, Morpheus, Grokster";
        presence "enable fasttrack matching";
        leaf file-transfer {
          description
            "File transfer stream";
          type string;
        }
      }
      leaf finger {
        type empty;
      }
      leaf ftp {
        type empty;
      }
      container gnutella {
        description
          "Gnutella Version2 Traffic - BearShare, Shareeza, Morpheus";
        presence "enable gnutella matching";
        leaf file-transfer {
          description
            "File transfer stream";
          type string;
        }
      }
      leaf gopher {
        type empty;
      }
      leaf gre {
        type empty;
      }
      leaf h323 {
        type empty;
      }
      container http {
        description
          "World Wide Web traffic";
        presence "enable http traffic matching";
        leaf c-header-field {
          description
            "Client general Header Field";
          type string;
        }
        leaf host {
          description
            "Server Host Name";
          type string;
        }
        leaf mime {
          description
            "Match MIME Type";
          type string;
        }
        leaf s-header-field {
          description
            "Server general Header Field";
          type string;
        }
        leaf url {
          description
            "Match URL String";
          type string;
        }
      }
      leaf icmp {
        description
          "Internet Control Message";
        type empty;
      }
      leaf imap {
        description
          "Internet Message Access Protocol";
        type empty;
      }
      leaf ip {
        description
          "IP";
        type empty;
      }
      leaf ipinip {
        description
          "IP in IP (encapsulation";
        type empty;
      }
      leaf ipsec {
        description
          "IP Security Protocol (ESP/AH";
        type empty;
      }
      leaf ipv6 {
        description
          "IPV6";
        type empty;
      }
      leaf ipx {
        description
          "Novell IPX";
        type empty;
      }
      leaf irc {
        type empty;
        description
          "Internet Relay Chat";
      }
      container kazaa2 {
        description
          "Kazaa Version 2";
        presence "enable kazaa version 2 matching";
        leaf file-transfer {
          description
            "File transfer stream";
          type string;
        }
      }
      leaf kerberos {
        description
          "Kerberos";
        type empty;
      }
      leaf l2tp {
        description
          "L2F/L2TP tunnel";
        type empty;
      }
      leaf ldap {
        description
          "Lightweight Directory Access Protocol";
        type empty;
      }
      leaf llc2 {
        description
          "llc2";
        type empty;
      }
      leaf mgcp {
        description
          "Media Gateway Control Protocol";
        type empty;
      }
      container napster {
        description
          "Napster Traffic";
        presence "enable napster matching";
        leaf non-std {
          description
            "Non-standard port advertizements";
          type empty;
        }
      }
      leaf netbios {
        description
          "NetBIOS";
        type empty;
      }
      leaf netshow {
        description
          "Microsoft Netshow";
        type empty;
      }
      leaf nfs {
        description
          "Network File System";
        type empty;
      }
      leaf nntp {
        description
          "Network News Transfer Protocol";
        type empty;
      }
      leaf notes {
        description
          "Lotus Notes(R";
        type empty;
      }
      leaf novadigm {
        description
          "Novadigm EDM";
        type empty;
      }
      leaf ntp {
        description
          "Network Time Protocol";
        type empty;
      }
      leaf ospf {
        description
          "Open Shortest Path First";
        type empty;
      }
      leaf pad {
        description
          "PAD links";
        type empty;
      }
      leaf pcanywhere {
        description
          "Symantec pcANYWHERE";
        type empty;
      }
      leaf pop3 {
        description
          "Post Office Protocol";
        type empty;
      }
      leaf pppoe {
        description
          "PPP over Ethernet";
        type empty;
      }
      leaf pptp {
        description
          "Point-to-Point Tunneling Protocol";
        type empty;
      }
      leaf printer {
        description
          "print spooler/lpd";
        type empty;
      }
      leaf qllc {
        description
          "qllc protocol";
        type empty;
      }
      leaf rcmd {
        description
          "BSD r-commands (rsh, rlogin, rexec";
        type empty;
      }
      leaf rip {
        description
          "Routing Information Protocol";
        type empty;
      }
      leaf rsrb {
        description
          "Remote Source-Route Bridging";
        type empty;
      }
      leaf rsvp {
        description
          "Resource Reservation Protocol";
        type empty;
      }
      leaf rtcp {
        description
          "Real Time Control Protocol";
        type empty;
      }
      container rtp {
        description
          "Real Time Protocol";
        presence "enable rtp matching";
        leaf audio {
          description
            "Match voice packets";
          type empty;
        }
        leaf payload-type {
          description
            "Match an explicit PT";
          type string;
        }
        leaf video {
          description
            "Match video packets";
          type empty;
        }
      }
      leaf rtsp {
        description
          "Real Time Streaming Protocol";
        type empty;
      }
      leaf secure-ftp {
        description
          "FTP over TLS/SSL";
        type empty;
      }
      leaf secure-http {
        description
          "Secured HTTP";
        type empty;
      }
      leaf secure-imap {
        description
          "Internet Message Access Protocol over TLS/SSL";
        type empty;
      }
      leaf secure-irc {
        description
          "Internet Relay Chat over TLS/SSL";
        type empty;
      }
      leaf secure-ldap {
        description
          "Lightweight Directory Access Protocol over TLS/SSL";
        type empty;
      }
      leaf secure-nntp {
        description
          "Network News Transfer Protocol over TLS/SSL";
        type empty;
      }
      leaf secure-pop3 {
        description
          "Post Office Protocol over TLS/SSL";
        type empty;
      }
      leaf secure-telnet {
        description
          "Telnet over TLS/SSL";
        type empty;
      }
      leaf sip {
        description
          "Session Initiation Protocol";
        type empty;
      }
      leaf skinny {
        description
          "Skinny Protocol";
        type empty;
      }
      container smtp {
        description
          "Simple Mail Transfer Protocol";
        presence "true";
        leaf extended {
          type empty;
        }
      }
      leaf snapshot {
        description
          "Snapshot routing support";
        type empty;
      }
      leaf snmp {
        description
          "Simple Network Management Protocol";
        type empty;
      }
      leaf socks {
        description
          "SOCKS";
        type empty;
      }
      leaf sqlnet {
        description
          "SQL*NET for Oracle";
        type empty;
      }
      leaf sqlserver {
        description
          "MS SQL Server";
        type empty;
      }
      leaf ssh {
        description
          "Secured Shell";
        type empty;
      }
      leaf streamwork {
        description
          "Xing Technology StreamWorks player";
        type empty;
      }
      leaf stun {
        description
          "Serial Tunnel";
        type empty;
      }
      leaf sunrpc {
        description
          "Sun RPC";
        type empty;
      }
      leaf syslog {
        description
          "System Logging Utility";
        type empty;
      }
      leaf telnet {
        description
          "Telnet";
        type empty;
      }
      leaf tftp {
        description
          "Trivial File Transfer Protocol";
        type empty;
      }
      leaf vdolive {
        description
          "VDOLive streaming video";
        type empty;
      }
      leaf vofr {
        description
          "voice over Frame Relay packets";
        type empty;
      }
      leaf winmx {
        description
          "WinMx file-sharing application";
        type empty;
      }
      leaf xwindows {
        description
          "X-Windows remote access";
        type empty;
      }
      container attribute {
        description
          "Attribute based protocol match";
        container business-relevance {
          description
            "Application business-relevance";
          leaf business-irrelevant {
            description
              "Undesirable business traffic";
            type empty;
          }
          leaf business-relevant {
            description
              "Business critical applications";
            type empty;
          }
          leaf default {
            description
              "Related business applications";
            type empty;
          }
        }
        container traffic-class {
          description
            "SRND class";
          leaf broadcast-video {
            description
              "Broadcast TV, live events, video surveillance";
            type empty;
          }
          leaf bulk-data {
            description
              "Non-interactive data applications";
            type empty;
          }
          leaf multimedia-conferencing {
            description
              "Desktop software multimedia collaboration applications";
            type empty;
          }
          leaf multimedia-streaming {
            description
              "Video-on-Demand (VoD) streaming video";
            type empty;
          }
          leaf network-control {
            description
              "Network control plane traffic";
            type empty;
          }
          leaf ops-admin-mgmt {
            description
              "Network operations, administration, and management traffic";
            type empty;
          }
          leaf real-time-interactive {
            description
              "High-definition interactive video applications";
            type empty;
          }
          leaf signaling {
            description
              "Signaling traffic that supports IP voice and video telephony";
            type empty;
          }
          leaf transactional-data {
            description
              "Interactive data applications";
            type empty;
          }
          leaf voip-telephony {
            description
              "VoIP telephony (bearer-only) traffic";
            type empty;
          }
        }
      }
    }
    leaf-list qos-group {
      description
        "Qos-group";
      type uint16 {
        range "0..99";
      }
    }
    container security-group {
      description
        "Security group";
      container destination {
        description
          "Destination security group";
        leaf tag {
          description
            "Security group tag";
          type uint16;
        }
      }
      container source {
        description
          "Source security group";
        leaf tag {
          description
            "Security group tag";
          type uint16;
        }
      }
    }
    container source-address {
      description
        "Source address";
      leaf-list mac {
        description
          "MAC address";
        type yang:mac-address;
      }
    }
    container vlan {
      description
        "VLANs to match";
      leaf-list inner {
        description
          "Inner tag to match";
        type union {
          type uint16 {
            range "1..4094";
          }
          type string;
        }
      }
      leaf-list value {
        type union {
          type uint16 {
            range "1..4094";
          }
          type string;
        }
      }
    }
  }

  grouping class-map-appnav-match-grouping {
    leaf peer {
      description
        "APPNAV Peer Filter";
      when "../../type = 'appnav'" {
        tailf:xpath-root 3;
      }
      type string;
    }
  }

  grouping class-map-appnav-not-match-grouping {
    leaf peer {
      description
        "APPNAV Peer Filter";
      when "../../../type = 'appnav'" {
        tailf:xpath-root 3;
      }
      type string;
    }
  }

  grouping config-class-map-grouping {
    list class-map {
      description
        "configure qos class map";
      key "name";
      leaf name {
        type string;
      }
      leaf type {
        description
          "type of the class-map";
        type enumeration {
          enum "access-control";
          enum "appnav";
          enum "control";
          enum "inspect";
          enum "multicast-flows";
          enum "stack";
          enum "traffic";
        }
      }
      leaf subscriber {
        type empty;
      }
      leaf protocol {
        when "../type = 'inspect'" {
          tailf:xpath-root 3;
        }
        type enumeration {
          enum "aol";
          enum "edonkey";
          enum "fasttrack";
          enum "gnutella";
          enum "http";
          enum "imap";
          enum "kazaa2";
          enum "msnmsgr";
          enum "pop3";
          enum "smtp";
          enum "sunrpc";
          enum "ymsgr";
        }
      }
      leaf prematch {
        type enumeration {
          enum "match-all";
          enum "match-any";
          enum "match-none";
        }
        mandatory true;
      }
      leaf description {
        description
          "Class-Map description";
        type string;
      }
      container match {
        description
          "classification criteria";
        uses class-map-match-grouping;
        uses class-map-appnav-match-grouping;
        uses class-map-control-filter-grouping;
        container not {
          description
            "Negate this match result";
          uses class-map-match-grouping;
          uses class-map-appnav-not-match-grouping;
        }
      }
      container no-match {
        description
          "no-match filter";
        uses class-map-control-filter-grouping;
      }
    }
  }

  grouping config-parameter-map-grouping {
    container timeout {
      description
        "timeout for the webauth session";
      when "/ios:native/ios:parameter-map/ios:type = 'webauth'" {
        tailf:xpath-root 3;
      }
      container init-state {
        description
          "init-state timeout";
        presence "true";
        leaf sec {
          description
            "WEBAUTH Timeout in Seconds";
          type uint32 {
            range "60..3932100";
          }
        }
      }
      container fin-wait {
        description
          "fin-wait timeout";
        leaf msec {
          description
            "WEBAUTH Timeout in milliseconds";
          type uint32 {
            range "1..2147483647";
          }
        }
      }
    }
    container watch-list {
      description
        "Watch List of webauth clients";
      when "/ios:native/ios:parameter-map/ios:type = 'webauth'" {
        tailf:xpath-root 3;
      }
      leaf enabled {
        description
          "Enable Watchlist";
        type empty;
      }
      leaf dynamic-expiry-timeout {
        description
          "dynamic_expiry_timeout";
        type uint32 {
          range "0..2147483";
        }
      }
      container add-item {
        description
          "Add item to Watch-list";
        leaf ipv4 {
          description
            "IPv4 Watch List Entry";
          type inet:ipv4-address;
        }
        leaf ipv6 {
          description
            "IPv6 Watch List Entry";
          type inet:ipv6-address;
        }
      }
    }
    container aggressive-aging {
      description
        "Aggressive Aging parameters";
      when "/ios:native/ios:parameter-map/ios:type = 'inspect-global'" {
        tailf:xpath-root 3;
      }
      container high {
        description
          "Specify the high watermark for aggressive-aging";
        choice absolute-percent {
          case absolute-case {
            container absolute {
              leaf value {
                type uint64 {
                  range "1..4294967295";
                }
              }
              leaf low {
                description
                  "Specify the low watermark for aggressive-aging";
                type uint64 {
                  range "1..4294967295";
                }
              }
            }
          }
          case percent-case {
            container percent {
              description
                "high watermark in percentage of max-incomplete value";
              leaf value {
                type uint8 {
                  range "1..100";
                }
              }
              leaf low_percent {
                description
                  "Specify the low watermark for aggressive-aging in percents";
                type uint8 {
                  range "1..100";
                }
              }
            }
          }
        }
      }
    }
    leaf alert {
      description
        "Turn on/off alert";
      type enumeration {
        enum "off";
        enum "on";
      }
    }
    leaf application-inspect {
      description
        "Turn on application inspection";
      type enumeration {
        enum "all";
        enum "dns";
        enum "exec";
        enum "ftp";
        enum "gtp";
        enum "h323";
        enum "http";
        enum "imap";
        enum "login";
        enum "msrpc";
        enum "netbios";
        enum "pop3";
        enum "rtsp";
        enum "shell";
        enum "sip";
        enum "skinny";
        enum "smtp";
        enum "sunrpc";
        enum "tftp";
      }
    }
    leaf audit-trail {
      description
        "Turn on/off audit trail";
      when "/ios:native/ios:parameter-map/ios:type = 'inspect'" {
        tailf:xpath-root 3;
      }
      type enumeration {
        enum "off";
        enum "on";
      }
    }
    leaf dns-timeout {
      description
        "Specify timeout for DNS";
      when "/ios:native/ios:parameter-map/ios:type = 'inspect'" {
        tailf:xpath-root 3;
      }
      type uint32 {
        range "1..2147483";
      }
    }
    container global {
      description
        "cws_tunnel global parameter-map";
      leaf fail-open {
        description
          "Allow traffic to go in clear if CWS Towers are unreachable";
        when "/ios:native/ios:parameter-map/ios:type = 'cws-tunnel'" {
          tailf:xpath-root 3;
        }
        type empty;
      }
      container license {
        description
          "License Key";
        when "/ios:native/ios:parameter-map/ios:type = 'cws-tunnel'" {
          tailf:xpath-root 3;
        }
        container Unencypted {
          description
            "Unencrypted License";
          leaf Hex-string {
            description
              "32 char non encrypted hex key";
            type string;
          }
        }
        container Encrypted {
          description
            "Encrypted License";
          leaf Hex-string {
            description
              "66 char encrypted hex key";
            type string;
          }
        }
      }
      leaf logging {
        description
          "CWS syslogs";
        type empty;
      }
      container primary {
        description
          "Primary tower";
        when "/ios:native/ios:parameter-map/ios:type = 'cws-tunnel'" {
          tailf:xpath-root 3;
        }
        presence "true";
        container tower {
          description
            "Tower configuration for CWS";
          leaf ipv4 {
            description
              "IPv4 address of the tower";
            type inet:ipv4-address;
          }
          leaf name {
            description
              "Fully Qualified Domain Name of tower";
            type string;
          }
        }
      }
      leaf redirect-list {
        description
          "Set access-list for reverse route from CWS Tower
           Standard IP access-list number <1-199>
           Standard IP access-list number (expanded range) <1300-2699>";
        when "/ios:native/ios:parameter-map/ios:type = 'cws-tunnel'" {
          tailf:xpath-root 3;
        }
        type union {
          type uint16 {
            range "1..199";
          }
          type uint16 {
            range "1300..2699";
          }
        }
      }
      container secondary {
        description
          "Secondary tower";
        when "/ios:native/ios:parameter-map/ios:type = 'cws-tunnel'" {
          tailf:xpath-root 3;
        }
        presence "true";
        container tower {
          description
            "Tower configuration for CWS";
          leaf ipv4 {
            description
              "IPv4 address of the tower";
            type inet:ipv4-address;
          }
          leaf name {
            description
              "Fully Qualified Domain Name of tower";
            type string;
          }
        }
      }
      container whitelist {
        description
          "Disable redirection to CWS
           Access list (standard) <1-199>
           Access list (extended) <1300-2699>
           Access list name";
        presence "true";
        container acl {
          description
            "Access list";
          leaf acl-number {
            type union {
              type uint16 {
                range "1..199";
              }
              type uint16 {
                range "1300..2699";
              }
            }
          }
          leaf name {
            description
              "Access list name";
            type string;
          }
        }
        container domain-name {
          description
            "Domain name based Whitelist";
          leaf regex {
            description
              "Domain name regex parameter map";
            type string;
          }
        }
        container download {
          description
            "whitelist download command";
          presence "true";
          leaf interval {
            description
              "Download interval in minutes";
            type uint16 {
              range "5..10080";
            }
          }
        }
      }
    }
    container icmp {
      description
        "Config timeout values for icmp";
      when "/ios:native/ios:parameter-map/ios:type = 'inspect'" {
        tailf:xpath-root 3;
      }
      leaf idle-time {
        description
          "Specify timeout for icmp";
        type uint32 {
          range "1..2147483";
        }
      }
    }
    container lisp {
      description
        "Turn on LISP options";
      leaf inner-packet-inspection {
        description
          "inner-packet-inspection";
        type empty;
      }
    }
    container log {
      description
        "Configure inspect logging parameters";
      leaf dropped-packets {
        description
          "Log dropped packets";
        type empty;
      }
      container flow-export {
        description
          "Configure inspect external logging parameters";
        container template {
          description
            "Configure record template parameters";
          leaf timeout-rate {
            description
              "Rate to resend the template in seconds";
            type uint32 {
              range "0..65535";
            }
          }
        }
        container v9 {
          description
            "Netflow version 9";
          container udp {
            description
              "Use UDP to export records";
            container destination {
              description
                "Specify the flow-export destination";
              leaf dst-ip {
                type inet:ipv4-address;
              }
              leaf dst-port {
                type uint16;
              }
            }
          }
        }
      }
    }
    leaf max-destination {
      description
        "config maximum destination";
      when "/ios:native/ios:parameter-map/ios:type = 'inspect-zone'" {
        tailf:xpath-root 3;
      }
      type uint32 {
        range "1..4294967295";
      }
    }
    container max-incomplete {
      description
        "Specify maximum number of incomplete connections before clamping";
      leaf high {
        description
          "Specify high-watermark for clamping";
        type uint32 {
          range "1..2147483647";
        }
      }
      leaf low {
        description
          "Specify low-watermark for clamping";
        type uint32 {
          range "1..2147483647";
        }
      }
    }
    container one-minute {
      description
        "Specify one-minute-sample watermarks for clamping";
      when "/ios:native/ios:parameter-map/ios:type = 'inspect'" {
        tailf:xpath-root 3;
      }
      leaf high {
        description
          "Specify high-watermark for clamping";
        type uint32 {
          range "1..2147483647";
        }
      }
      leaf low {
        description
          "Specify low-watermark for clamping";
        type uint32 {
          range "1..2147483647";
        }
      }
    }
    container sessions {
      description
        "Maximum number of inspect sessions";
      when "/ios:native/ios:parameter-map/ios:type = 'inspect'" {
        tailf:xpath-root 3;
      }
      leaf maximum {
        description
          "Maximum sessions";
        type uint32 {
          range "1..2147483647";
        }
      }
      container queue {
        description
          "queue";
        leaf max-threshold {
          type uint16 {
            range "0..65535";
          }
        }
        leaf min-threshold {
          type uint16 {
            range "0..65535";
          }
        }
      }
    }
    choice tcp-ins {
      container tcp-inspect {
        when "/ios:native/ios:parameter-map/ios:type = 'inspect'" {
          tailf:xpath-root 3;
        }
        container tcp {
          description
            "Config timeout values for tcp connections";
          when "/ios:native/ios:parameter-map/ios:type = 'inspect'" {
            tailf:xpath-root 3;
          }
          leaf finwait-time {
            description
              "Specify timeout for TCP connections after a FIN";
            type uint32 {
              range "1..2147483";
            }
          }
          leaf idle-time {
            description
              "Specify idle timeout for tcp connections";
            type uint32 {
              range "1..2147483";
            }
          }
          container max-incomplete {
            description
              "Specify max half-open connection per host";
            leaf host {
              description
                "Specify max half-open connection per host";
              type uint32 {
                range "1..4294967295";
              }
            }
          }
          leaf synwait-time {
            description
              "Specify timeout for TCP connections after a SYN and no";
            type uint32 {
              range "1..2147483";
            }
          }
        }
      }
      container tcp-inspect-zone {
        when "/ios:native/ios:parameter-map/ios:type = 'inspect-zone'" {
          tailf:xpath-root 3;
        }
        container tcp {
          description
            "Configure tcp syn-flood per-destination rate";
          container syn-flood {
            description
              "maximum syn packet";
            container rate {
              description
                "maximum syn packet rate";
              leaf per-destination {
                description
                  "per destination
                   maximum rate of TCP SYN packets";
                type uint32 {
                  range "1..1000000000";
                }
              }
            }
          }
        }
      }
    }
    container threat-detection {
      description
        "Configure Threat Detection";
      when "/ios:native/ios:parameter-map/ios:type = 'inspect-zone'" {
        tailf:xpath-root 3;
      }
      leaf basic-threat {
        description
          "Enable Threat Detection";
        type empty;
      }
      container rate {
        description
          "Configure Threat Detection rate";
        container fw-drop {
          description
            "Configure Threat Detection rate for firewall drop events";
          leaf average-time-frame {
            description
              "Configure Threat Detection average time frame";
            type uint32 {
              range "600..3600";
            }
          }
          leaf average-threshold {
            description
              "Configure Threat Detection average threshold";
            type uint64 {
              range "1..4294967295";
            }
          }
          leaf burst-threshold {
            description
              " Configure Threat Detection burst threshold";
            type uint64 {
              range "1..1000000000";
            }
          }
        }
        container inspect-drop {
          description
            "Configure Threat Detection rate for firewall inspection based drop events";
          leaf average-time-frame {
            description
              "Configure Threat Detection average time frame";
            type uint32 {
              range "600..3600";
            }
          }
          leaf average-threshold {
            description
              "Configure Threat Detection average threshold";
            type uint64 {
              range "1..4294967295";
            }
          }
          leaf burst-threshold {
            description
              " Configure Threat Detection burst threshold";
            type uint64 {
              range "1..1000000000";
            }
          }
        }
        container syn-attack {
          description
            "Configure Threat Detection rate for syn attack events";
          leaf average-time-frame {
            description
              "Configure Threat Detection average time frame";
            type uint32 {
              range "600..3600";
            }
          }
          leaf average-threshold {
            description
              "Configure Threat Detection average threshold";
            type uint64 {
              range "1..4294967295";
            }
          }
          leaf burst-threshold {
            description
              " Configure Threat Detection burst threshold";
            type uint64 {
              range "1..1000000000";
            }
          }
        }
      }
    }
    container udp {
      description
        "Config timeout values for udp flows";
      when "/ios:native/ios:parameter-map/ios:type = 'inspect'" {
        tailf:xpath-root 3;
      }
      leaf idle-time {
        description
          "Specify idle timeout for udp";
        type uint32 {
          range "1..2147483";
        }
      }
    }
    container vrf {
      description
        "vrf binding with parameter map";
      leaf name {
        type string;
      }
      leaf inspect {
        description
          "vrf binding with parameter map";
        type string;
      }
    }
    leaf zone-mismatch {
      description
        "Config zone-mismatch option";
      type enumeration {
        enum "drop";
      }
    }
  }

  grouping config-service-policy-direction-grouping {
    leaf input {
      description
        "Assign policy-map to the input of an interface";
      type string;
    }
    leaf output {
      description
        "Assign policy-map to the output of an interface";
      type string;
    }
  }

  grouping config-service-policy-grouping {
    container service-policy {
      uses config-service-policy-direction-grouping;
    }
  }

  grouping config-interface-service-policy-grouping {
    container service-policy {
      description
        "Configure QoS Service Policy";
      leaf history {
        description
          "Keep history of QoS metrics";
        type empty;
      }
      uses config-service-policy-direction-grouping;
      container type {
        description
          "Configure CPL Service Policy";
        container control {
          leaf subscriber {
            type string;
          }
        }
        container performance-monitor {
          description
            "Configure media monitor service-policy type";
          leaf direction {
            type enumeration {
              enum "input";
              enum "output";
            }
          }
          leaf name {
            type string;
          }
        }
        container service-chain {
          description
            "Configure Service-chain Service Policy";
          container input {
            description
              "Assign policy-map to the input of an interface";
            leaf name {
              type string;
            }
          }
          container output {
            description
              "Assign policy-map to the output of an interface";
            leaf name {
              type string;
            }
          }
        }
      }
    }
  }

  augment "/ncs:devices/ncs:template/ncs:config/ios:native/ios:policy" {
    uses ncs_template_config-class-map-grouping;
    uses ncs_template_config-policy-map-grouping;
  }
  augment "/ncs:devices/ncs:device/ncs:live-status/ios:native/ios:policy" {
    uses live_ncs_config-class-map-grouping {
      refine class-map {
        tailf:ncs-device-type "netconf";
        tailf:display-when "not(../../../ncs:module) or ../../../ncs:module[ncs:name='Cisco-IOS-XE-policy'] or (../../../ncs:live-status-protocol[not(ncs:capability)]) or (../../../ncs:live-status-protocol/ncs:capability/ncs:module[.='Cisco-IOS-XE-policy'])";
      }
    }
    uses live_ncs_config-policy-map-grouping {
      refine policy-map {
        tailf:ncs-device-type "netconf";
        tailf:display-when "not(../../../ncs:module) or ../../../ncs:module[ncs:name='Cisco-IOS-XE-policy'] or (../../../ncs:live-status-protocol[not(ncs:capability)]) or (../../../ncs:live-status-protocol/ncs:capability/ncs:module[.='Cisco-IOS-XE-policy'])";
      }
    }
  }
  augment "/ncs:devices/ncs:device/ncs:config/ios:native/ios:policy" {
    uses config-class-map-grouping {
      refine class-map {
        tailf:ncs-device-type "netconf";
        tailf:display-when "not(../../../ncs:module) or ../../../ncs:module[ncs:name='Cisco-IOS-XE-policy']";
      }
    }
    uses config-policy-map-grouping {
      refine policy-map {
        tailf:ncs-device-type "netconf";
        tailf:display-when "not(../../../ncs:module) or ../../../ncs:module[ncs:name='Cisco-IOS-XE-policy']";
      }
    }
  }
  augment "/ncs:devices/ncs:template/ncs:config/ios:native/ios:parameter-map" {
    uses ncs_template_config-parameter-map-grouping {
      // NCS drop if-feature statement
    }
  }
  augment "/ncs:devices/ncs:device/ncs:live-status/ios:native/ios:parameter-map" {
    uses live_ncs_config-parameter-map-grouping {
      refine zone-mismatch {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine vrf {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine udp {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine threat-detection {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine tcp-ins;
      refine sessions {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine one-minute {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine max-incomplete {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine max-destination {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine log {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine lisp {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine icmp {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine global {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine dns-timeout {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine audit-trail {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine application-inspect {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine alert {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine aggressive-aging {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine watch-list {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      refine timeout {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
      // NCS drop if-feature statement
    }
  }
  augment "/ncs:devices/ncs:device/ncs:config/ios:native/ios:parameter-map" {
    uses config-parameter-map-grouping {
      refine zone-mismatch {
        tailf:ncs-device-type "netconf";
        tailf:display-when "not(../../../../ncs:module) or ../../../../ncs:module[ncs:name='Cisco-IOS-XE-policy']";
      }
      refine vrf {
        tailf:ncs-device-type "netconf";
        tailf:display-when "not(../../../../ncs:module) or ../../../../ncs:module[ncs:name='Cisco-IOS-XE-policy']";
      }
      refine udp {
        tailf:ncs-device-type "netconf";
        tailf:display-when "not(../../../../ncs:module) or ../../../../ncs:module[ncs:name='Cisco-IOS-XE-policy']";
      }
      refine threat-detection {
        tailf:ncs-device-type "netconf";
        tailf:display-when "not(../../../../ncs:module) or ../../../../ncs:module[ncs:name='Cisco-IOS-XE-policy']";
      }
      refine tcp-ins;
      refine sessions {
        tailf:ncs-device-type "netconf";
        tailf:display-when "not(../../../../ncs:module) or ../../../../ncs:module[ncs:name='Cisco-IOS-XE-policy']";
      }
      refine one-minute {
        tailf:ncs-device-type "netconf";
        tailf:display-when "not(../../../../ncs:module) or ../../../../ncs:module[ncs:name='Cisco-IOS-XE-policy']";
      }
      refine max-incomplete {
        tailf:ncs-device-type "netconf";
        tailf:display-when "not(../../../../ncs:module) or ../../../../ncs:module[ncs:name='Cisco-IOS-XE-policy']";
      }
      refine max-destination {
        tailf:ncs-device-type "netconf";
        tailf:display-when "not(../../../../ncs:module) or ../../../../ncs:module[ncs:name='Cisco-IOS-XE-policy']";
      }
      refine log {
        tailf:ncs-device-type "netconf";
        tailf:display-when "not(../../../../ncs:module) or ../../../../ncs:module[ncs:name='Cisco-IOS-XE-policy']";
      }
      refine lisp {
        tailf:ncs-device-type "netconf";
        tailf:display-when "not(../../../../ncs:module) or ../../../../ncs:module[ncs:name='Cisco-IOS-XE-policy']";
      }
      refine icmp {
        tailf:ncs-device-type "netconf";
        tailf:display-when "not(../../../../ncs:module) or ../../../../ncs:module[ncs:name='Cisco-IOS-XE-policy']";
      }
      refine global {
        tailf:ncs-device-type "netconf";
        tailf:display-when "not(../../../../ncs:module) or ../../../../ncs:module[ncs:name='Cisco-IOS-XE-policy']";
      }
      refine dns-timeout {
        tailf:ncs-device-type "netconf";
        tailf:display-when "not(../../../../ncs:module) or ../../../../ncs:module[ncs:name='Cisco-IOS-XE-policy']";
      }
      refine audit-trail {
        tailf:ncs-device-type "netconf";
        tailf:display-when "not(../../../../ncs:module) or ../../../../ncs:module[ncs:name='Cisco-IOS-XE-policy']";
      }
      refine application-inspect {
        tailf:ncs-device-type "netconf";
        tailf:display-when "not(../../../../ncs:module) or ../../../../ncs:module[ncs:name='Cisco-IOS-XE-policy']";
      }
      refine alert {
        tailf:ncs-device-type "netconf";
        tailf:display-when "not(../../../../ncs:module) or ../../../../ncs:module[ncs:name='Cisco-IOS-XE-policy']";
      }
      refine aggressive-aging {
        tailf:ncs-device-type "netconf";
        tailf:display-when "not(../../../../ncs:module) or ../../../../ncs:module[ncs:name='Cisco-IOS-XE-policy']";
      }
      refine watch-list {
        tailf:ncs-device-type "netconf";
        tailf:display-when "not(../../../../ncs:module) or ../../../../ncs:module[ncs:name='Cisco-IOS-XE-policy']";
      }
      refine timeout {
        tailf:ncs-device-type "netconf";
        tailf:display-when "not(../../../../ncs:module) or ../../../../ncs:module[ncs:name='Cisco-IOS-XE-policy']";
      }
      // NCS drop if-feature statement
    }
  }
  augment "/ncs:devices/ncs:template/ncs:config/ios:native/ios:control-plane" {
    uses ncs_template_config-service-policy-grouping;
  }
  augment "/ncs:devices/ncs:device/ncs:live-status/ios:native/ios:control-plane" {
    uses live_ncs_config-service-policy-grouping {
      refine service-policy {
        tailf:ncs-device-type "netconf";
        tailf:display-when "not(../../../../ncs:module) or ../../../../ncs:module[ncs:name='Cisco-IOS-XE-policy'] or (../../../../ncs:live-status-protocol[not(ncs:capability)]) or (../../../../ncs:live-status-protocol/ncs:capability/ncs:module[.='Cisco-IOS-XE-policy'])";
      }
    }
  }
  augment "/ncs:devices/ncs:device/ncs:config/ios:native/ios:control-plane" {
    uses config-service-policy-grouping {
      refine service-policy {
        tailf:ncs-device-type "netconf";
        tailf:display-when "not(../../../../ncs:module) or ../../../../ncs:module[ncs:name='Cisco-IOS-XE-policy']";
      }
    }
  }
  augment "/ncs:devices/ncs:template/ncs:config/ios:native/ios:interface/ios:FastEthernet" {
    uses ncs_template_config-interface-service-policy-grouping;
  }
  augment "/ncs:devices/ncs:device/ncs:live-status/ios:native/ios:interface/ios:FastEthernet" {
    uses live_ncs_config-interface-service-policy-grouping {
      refine service-policy {
        tailf:ncs-device-type "netconf";
        tailf:display-when "not(../../../../../ncs:module) or ../../../../../ncs:module[ncs:name='Cisco-IOS-XE-policy'] or (../../../../../ncs:live-status-protocol[not(ncs:capability)]) or (../../../../../ncs:live-status-protocol/ncs:capability/ncs:module[.='Cisco-IOS-XE-policy'])";
      }
    }
  }
  augment "/ncs:devices/ncs:device/ncs:config/ios:native/ios:interface/ios:FastEthernet" {
    uses config-interface-service-policy-grouping {
      refine service-policy {
        tailf:ncs-device-type "netconf";
        tailf:display-when "not(../../../../../ncs:module) or ../../../../../ncs:module[ncs:name='Cisco-IOS-XE-policy']";
      }
    }
  }
  augment "/ncs:devices/ncs:template/ncs:config/ios:native/ios:interface/ios:GigabitEthernet" {
    uses ncs_template_config-interface-service-policy-grouping;
  }
  augment "/ncs:devices/ncs:device/ncs:live-status/ios:native/ios:interface/ios:GigabitEthernet" {
    uses live_ncs_config-interface-service-policy-grouping {
      refine service-policy {
        tailf:ncs-device-type "netconf";
        tailf:display-when "not(../../../../../ncs:module) or ../../../../../ncs:module[ncs:name='Cisco-IOS-XE-policy'] or (../../../../../ncs:live-status-protocol[not(ncs:capability)]) or (../../../../../ncs:live-status-protocol/ncs:capability/ncs:module[.='Cisco-IOS-XE-policy'])";
      }
    }
  }
  augment "/ncs:devices/ncs:device/ncs:config/ios:native/ios:interface/ios:GigabitEthernet" {
    uses config-interface-service-policy-grouping {
      refine service-policy {
        tailf:ncs-device-type "netconf";
        tailf:display-when "not(../../../../../ncs:module) or ../../../../../ncs:module[ncs:name='Cisco-IOS-XE-policy']";
      }
    }
  }
  augment "/ncs:devices/ncs:template/ncs:config/ios:native/ios:interface/ios:TenGigabitEthernet" {
    uses ncs_template_config-interface-service-policy-grouping;
  }
  augment "/ncs:devices/ncs:device/ncs:live-status/ios:native/ios:interface/ios:TenGigabitEthernet" {
    uses live_ncs_config-interface-service-policy-grouping {
      refine service-policy {
        tailf:ncs-device-type "netconf";
        tailf:display-when "not(../../../../../ncs:module) or ../../../../../ncs:module[ncs:name='Cisco-IOS-XE-policy'] or (../../../../../ncs:live-status-protocol[not(ncs:capability)]) or (../../../../../ncs:live-status-protocol/ncs:capability/ncs:module[.='Cisco-IOS-XE-policy'])";
      }
    }
  }
  augment "/ncs:devices/ncs:device/ncs:config/ios:native/ios:interface/ios:TenGigabitEthernet" {
    uses config-interface-service-policy-grouping {
      refine service-policy {
        tailf:ncs-device-type "netconf";
        tailf:display-when "not(../../../../../ncs:module) or ../../../../../ncs:module[ncs:name='Cisco-IOS-XE-policy']";
      }
    }
  }
  augment "/ncs:devices/ncs:template/ncs:config/ios:native/ios:interface/ios:Port-channel" {
    uses ncs_template_config-interface-service-policy-grouping;
  }
  augment "/ncs:devices/ncs:device/ncs:live-status/ios:native/ios:interface/ios:Port-channel" {
    uses live_ncs_config-interface-service-policy-grouping {
      refine service-policy {
        tailf:ncs-device-type "netconf";
        tailf:display-when "not(../../../../../ncs:module) or ../../../../../ncs:module[ncs:name='Cisco-IOS-XE-policy'] or (../../../../../ncs:live-status-protocol[not(ncs:capability)]) or (../../../../../ncs:live-status-protocol/ncs:capability/ncs:module[.='Cisco-IOS-XE-policy'])";
      }
    }
  }
  augment "/ncs:devices/ncs:device/ncs:config/ios:native/ios:interface/ios:Port-channel" {
    uses config-interface-service-policy-grouping {
      refine service-policy {
        tailf:ncs-device-type "netconf";
        tailf:display-when "not(../../../../../ncs:module) or ../../../../../ncs:module[ncs:name='Cisco-IOS-XE-policy']";
      }
    }
  }
  augment "/ncs:devices/ncs:template/ncs:config/ios:native/ios:interface/ios:Loopback" {
    uses ncs_template_config-interface-service-policy-grouping;
  }
  augment "/ncs:devices/ncs:device/ncs:live-status/ios:native/ios:interface/ios:Loopback" {
    uses live_ncs_config-interface-service-policy-grouping {
      refine service-policy {
        tailf:ncs-device-type "netconf";
        tailf:display-when "not(../../../../../ncs:module) or ../../../../../ncs:module[ncs:name='Cisco-IOS-XE-policy'] or (../../../../../ncs:live-status-protocol[not(ncs:capability)]) or (../../../../../ncs:live-status-protocol/ncs:capability/ncs:module[.='Cisco-IOS-XE-policy'])";
      }
    }
  }
  augment "/ncs:devices/ncs:device/ncs:config/ios:native/ios:interface/ios:Loopback" {
    uses config-interface-service-policy-grouping {
      refine service-policy {
        tailf:ncs-device-type "netconf";
        tailf:display-when "not(../../../../../ncs:module) or ../../../../../ncs:module[ncs:name='Cisco-IOS-XE-policy']";
      }
    }
  }
  augment "/ncs:devices/ncs:template/ncs:config/ios:native/ios:interface/ios:Tunnel" {
    uses ncs_template_config-interface-service-policy-grouping;
  }
  augment "/ncs:devices/ncs:device/ncs:live-status/ios:native/ios:interface/ios:Tunnel" {
    uses live_ncs_config-interface-service-policy-grouping {
      refine service-policy {
        tailf:ncs-device-type "netconf";
        tailf:display-when "not(../../../../../ncs:module) or ../../../../../ncs:module[ncs:name='Cisco-IOS-XE-policy'] or (../../../../../ncs:live-status-protocol[not(ncs:capability)]) or (../../../../../ncs:live-status-protocol/ncs:capability/ncs:module[.='Cisco-IOS-XE-policy'])";
      }
    }
  }
  augment "/ncs:devices/ncs:device/ncs:config/ios:native/ios:interface/ios:Tunnel" {
    uses config-interface-service-policy-grouping {
      refine service-policy {
        tailf:ncs-device-type "netconf";
        tailf:display-when "not(../../../../../ncs:module) or ../../../../../ncs:module[ncs:name='Cisco-IOS-XE-policy']";
      }
    }
  }
  augment "/ncs:devices/ncs:template/ncs:config/ios:native/ios:interface/ios:LISP" {
    uses ncs_template_config-interface-service-policy-grouping;
  }
  augment "/ncs:devices/ncs:device/ncs:live-status/ios:native/ios:interface/ios:LISP" {
    uses live_ncs_config-interface-service-policy-grouping {
      refine service-policy {
        tailf:ncs-device-type "netconf";
        tailf:display-when "not(../../../../../ncs:module) or ../../../../../ncs:module[ncs:name='Cisco-IOS-XE-policy'] or (../../../../../ncs:live-status-protocol[not(ncs:capability)]) or (../../../../../ncs:live-status-protocol/ncs:capability/ncs:module[.='Cisco-IOS-XE-policy'])";
      }
    }
  }
  augment "/ncs:devices/ncs:device/ncs:config/ios:native/ios:interface/ios:LISP" {
    uses config-interface-service-policy-grouping {
      refine service-policy {
        tailf:ncs-device-type "netconf";
        tailf:display-when "not(../../../../../ncs:module) or ../../../../../ncs:module[ncs:name='Cisco-IOS-XE-policy']";
      }
    }
  }
  augment "/ncs:devices/ncs:template/ncs:config/ios:native/ios:interface/ios:VirtualPortGroup" {
    uses ncs_template_config-interface-service-policy-grouping;
  }
  augment "/ncs:devices/ncs:device/ncs:live-status/ios:native/ios:interface/ios:VirtualPortGroup" {
    uses live_ncs_config-interface-service-policy-grouping {
      refine service-policy {
        tailf:ncs-device-type "netconf";
        tailf:display-when "not(../../../../../ncs:module) or ../../../../../ncs:module[ncs:name='Cisco-IOS-XE-policy'] or (../../../../../ncs:live-status-protocol[not(ncs:capability)]) or (../../../../../ncs:live-status-protocol/ncs:capability/ncs:module[.='Cisco-IOS-XE-policy'])";
      }
    }
  }
  augment "/ncs:devices/ncs:device/ncs:config/ios:native/ios:interface/ios:VirtualPortGroup" {
    uses config-interface-service-policy-grouping {
      refine service-policy {
        tailf:ncs-device-type "netconf";
        tailf:display-when "not(../../../../../ncs:module) or ../../../../../ncs:module[ncs:name='Cisco-IOS-XE-policy']";
      }
    }
  }
  augment "/ncs:devices/ncs:template/ncs:config/ios:native/ios:interface/ios:Virtual-Template" {
    uses ncs_template_config-interface-service-policy-grouping;
  }
  augment "/ncs:devices/ncs:device/ncs:live-status/ios:native/ios:interface/ios:Virtual-Template" {
    uses live_ncs_config-interface-service-policy-grouping {
      refine service-policy {
        tailf:ncs-device-type "netconf";
        tailf:display-when "not(../../../../../ncs:module) or ../../../../../ncs:module[ncs:name='Cisco-IOS-XE-policy'] or (../../../../../ncs:live-status-protocol[not(ncs:capability)]) or (../../../../../ncs:live-status-protocol/ncs:capability/ncs:module[.='Cisco-IOS-XE-policy'])";
      }
    }
  }
  augment "/ncs:devices/ncs:device/ncs:config/ios:native/ios:interface/ios:Virtual-Template" {
    uses config-interface-service-policy-grouping {
      refine service-policy {
        tailf:ncs-device-type "netconf";
        tailf:display-when "not(../../../../../ncs:module) or ../../../../../ncs:module[ncs:name='Cisco-IOS-XE-policy']";
      }
    }
  }
  augment "/ncs:devices/ncs:template/ncs:config/ios:native/ios:interface/ios:vasileft" {
    uses ncs_template_config-interface-service-policy-grouping;
  }
  augment "/ncs:devices/ncs:device/ncs:live-status/ios:native/ios:interface/ios:vasileft" {
    uses live_ncs_config-interface-service-policy-grouping {
      refine service-policy {
        tailf:ncs-device-type "netconf";
        tailf:display-when "not(../../../../../ncs:module) or ../../../../../ncs:module[ncs:name='Cisco-IOS-XE-policy'] or (../../../../../ncs:live-status-protocol[not(ncs:capability)]) or (../../../../../ncs:live-status-protocol/ncs:capability/ncs:module[.='Cisco-IOS-XE-policy'])";
      }
    }
  }
  augment "/ncs:devices/ncs:device/ncs:config/ios:native/ios:interface/ios:vasileft" {
    uses config-interface-service-policy-grouping {
      refine service-policy {
        tailf:ncs-device-type "netconf";
        tailf:display-when "not(../../../../../ncs:module) or ../../../../../ncs:module[ncs:name='Cisco-IOS-XE-policy']";
      }
    }
  }
  augment "/ncs:devices/ncs:template/ncs:config/ios:native/ios:interface/ios:vasiright" {
    uses ncs_template_config-interface-service-policy-grouping;
  }
  augment "/ncs:devices/ncs:device/ncs:live-status/ios:native/ios:interface/ios:vasiright" {
    uses live_ncs_config-interface-service-policy-grouping {
      refine service-policy {
        tailf:ncs-device-type "netconf";
        tailf:display-when "not(../../../../../ncs:module) or ../../../../../ncs:module[ncs:name='Cisco-IOS-XE-policy'] or (../../../../../ncs:live-status-protocol[not(ncs:capability)]) or (../../../../../ncs:live-status-protocol/ncs:capability/ncs:module[.='Cisco-IOS-XE-policy'])";
      }
    }
  }
  augment "/ncs:devices/ncs:device/ncs:config/ios:native/ios:interface/ios:vasiright" {
    uses config-interface-service-policy-grouping {
      refine service-policy {
        tailf:ncs-device-type "netconf";
        tailf:display-when "not(../../../../../ncs:module) or ../../../../../ncs:module[ncs:name='Cisco-IOS-XE-policy']";
      }
    }
  }
  augment "/ncs:devices/ncs:template/ncs:config/ios:native/ios:interface/ios:Vlan" {
    uses ncs_template_config-interface-service-policy-grouping;
  }
  augment "/ncs:devices/ncs:device/ncs:live-status/ios:native/ios:interface/ios:Vlan" {
    uses live_ncs_config-interface-service-policy-grouping {
      refine service-policy {
        tailf:ncs-device-type "netconf";
        tailf:display-when "not(../../../../../ncs:module) or ../../../../../ncs:module[ncs:name='Cisco-IOS-XE-policy'] or (../../../../../ncs:live-status-protocol[not(ncs:capability)]) or (../../../../../ncs:live-status-protocol/ncs:capability/ncs:module[.='Cisco-IOS-XE-policy'])";
      }
    }
  }
  augment "/ncs:devices/ncs:device/ncs:config/ios:native/ios:interface/ios:Vlan" {
    uses config-interface-service-policy-grouping {
      refine service-policy {
        tailf:ncs-device-type "netconf";
        tailf:display-when "not(../../../../../ncs:module) or ../../../../../ncs:module[ncs:name='Cisco-IOS-XE-policy']";
      }
    }
  }
  augment "/ncs:devices/ncs:template/ncs:config/ios:native/ios:interface/ios:BDI" {
    uses ncs_template_config-interface-service-policy-grouping;
  }
  augment "/ncs:devices/ncs:device/ncs:live-status/ios:native/ios:interface/ios:BDI" {
    uses live_ncs_config-interface-service-policy-grouping {
      refine service-policy {
        tailf:ncs-device-type "netconf";
        tailf:display-when "not(../../../../../ncs:module) or ../../../../../ncs:module[ncs:name='Cisco-IOS-XE-policy'] or (../../../../../ncs:live-status-protocol[not(ncs:capability)]) or (../../../../../ncs:live-status-protocol/ncs:capability/ncs:module[.='Cisco-IOS-XE-policy'])";
      }
    }
  }
  augment "/ncs:devices/ncs:device/ncs:config/ios:native/ios:interface/ios:BDI" {
    uses config-interface-service-policy-grouping {
      refine service-policy {
        tailf:ncs-device-type "netconf";
        tailf:display-when "not(../../../../../ncs:module) or ../../../../../ncs:module[ncs:name='Cisco-IOS-XE-policy']";
      }
    }
  }
}
