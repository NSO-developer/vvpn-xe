module Cisco-IOS-XE-ppp {
  // Generated by yanger -t ncs
  tailf:ncs-device-type "netconf";

  namespace "http://cisco.com/ns/yang/Cisco-IOS-XE-ppp";
  prefix ios-ppp;

  import ietf-inet-types {
    prefix inet;
  }
  import Cisco-IOS-XE-native {
    prefix ios;
  }
  import Cisco-IOS-XE-features {
    prefix ios-features;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Point-to-Point Protocol (PPP) Yang model.
     Copyright (c) 2016 by Cisco Systems, Inc.
     All rights reserved.";

  revision 2017-02-07 {
    description
      "Initial revision";
  }

  grouping ncs_template_config-ppp-grouping {
    container packet {
      description
        "Configure control packet rate throttling";
      leaf throttle {
        description
          "Configure control packet rate throttling";
        type string;
      }
      leaf allow_time {
        type string;
      }
      leaf block_time {
        type string;
      }
    }
  }

  grouping ncs_template_config-multilink-grouping {
    leaf bundle-name {
      description
        "Select method for naming multilink bundles";
      type string;
    }
    leaf virtual-template {
      description
        "virtual-template interface";
      type string;
    }
  }

  grouping ncs_template_config-interface-p2p-grouping {
    container ppp {
      description
        "Point-to-Point Protocol";
      leaf accounting {
        description
          "Set PPP network accounting method";
        type string;
      }
      container chap {
        description
          "Set CHAP authentication parameters";
        leaf hostname {
          description
            "Set alternate CHAP hostname";
          type string;
        }
        leaf challenge-length {
          description
            "Challenge Length for CHAP";
          type string;
        }
      }
      container authentication {
        description
          "Set PPP link authentication method";
        leaf method {
          type string;
        }
        leaf list-name {
          type string;
        }
        leaf chap {
          // NCS drop when statement
          type empty;
        }
        leaf callback {
          description
            "Authenticate remote on callback only";
          type empty;
        }
        leaf callin {
          description
            "Authenticate remote on incoming call only";
          type empty;
        }
        leaf callout {
          description
            "Authenticate remote on outgoing call only";
          type empty;
        }
        leaf default {
          description
            "Use the default authentication list";
          type empty;
        }
        leaf eap {
          description
            "Extensible Authentication Protocol (EAP)";
          // NCS drop when statement
          type empty;
        }
        leaf ms-chap {
          description
            "Microsoft Challenge Handshake Authentication Protocol (MS-CHAP)";
          // NCS drop when statement
          type empty;
        }
        leaf ms-chap-v2 {
          description
            "Microsoft CHAP Version 2 (MS-CHAP-V2)";
          // NCS drop when statement
          type empty;
        }
        leaf one-time {
          description
            "Allow use of username*OTP for one-time passwords";
          type empty;
        }
        leaf optional {
          description
            "Allow peer to refuse to authenticate";
          type empty;
        }
        leaf pap {
          description
            "Password Authentication Protocol (PAP)";
          // NCS drop when statement
          type empty;
        }
      }
      leaf authorization {
        description
          "Set PPP network authorization method";
        type string;
      }
      container ipcp {
        description
          "Set IPCP negotiation options";
        container dns {
          description
            "Specify DNS negotiation options";
          leaf primary {
            type string;
          }
        }
      }
      container multilink {
        description
          "Make interface multilink capable";
        presence "true";
        container links {
          description
            "Specify the limits on the number of links in a bundle";
          container minimum {
            description
              "Minimum number of links desired in the bundle";
            leaf minimum-value {
              type string;
            }
            leaf mandatory {
              description
                "Disable network layer until minimum number of links is reach";
              type empty;
            }
          }
        }
        leaf group {
          description
            "Put interface in a multilink bundle";
          type string;
        }
        container endpoint {
          description
            "Configure the local Endpoint Discriminator";
          leaf string {
            description
              "Use specified string";
            type string;
          }
        }
        container fragment {
          description
            "Specify fragmentation parameters";
          container delay {
            description
              "Specify the maximum delay for each fragment";
            leaf delay-value {
              type string;
            }
            leaf additional-delay-value {
              type string;
            }
          }
        }
      }
    }
  }

  grouping ncs_rpc_notif_config-ppp-grouping {
    container packet {
      description
        "Configure control packet rate throttling";
      leaf throttle {
        description
          "Configure control packet rate throttling";
        type uint32 {
          range "1..100000";
        }
      }
      leaf allow_time {
        type uint32 {
          range "1..3600";
        }
      }
      leaf block_time {
        type uint32 {
          range "2..3600";
        }
      }
    }
  }

  grouping ncs_rpc_notif_config-multilink-grouping {
    leaf bundle-name {
      description
        "Select method for naming multilink bundles";
      type enumeration {
        enum "authenticated";
        enum "both";
        enum "endpoint";
        enum "rfc";
      }
    }
    leaf virtual-template {
      description
        "virtual-template interface";
      type uint16 {
        range "1..4095";
      }
    }
  }

  grouping ncs_rpc_notif_config-interface-p2p-grouping {
    container ppp {
      description
        "Point-to-Point Protocol";
      leaf accounting {
        description
          "Set PPP network accounting method";
        type union {
          type string;
          type enumeration {
            enum "default";
          }
        }
      }
      container chap {
        description
          "Set CHAP authentication parameters";
        leaf hostname {
          description
            "Set alternate CHAP hostname";
          type string;
        }
        leaf challenge-length {
          description
            "Challenge Length for CHAP";
          type uint8 {
            range "16..63";
          }
        }
      }
      container authentication {
        description
          "Set PPP link authentication method";
        leaf method {
          type enumeration {
            enum "chap";
            enum "eap";
            enum "ms-chap";
            enum "ms-chap-v2";
            enum "pap";
          }
        }
        leaf list-name {
          type string;
        }
        leaf chap {
          when "not(../method = 'chap')" {
            tailf:xpath-root 3;
          }
          type empty;
        }
        leaf callback {
          description
            "Authenticate remote on callback only";
          type empty;
        }
        leaf callin {
          description
            "Authenticate remote on incoming call only";
          type empty;
        }
        leaf callout {
          description
            "Authenticate remote on outgoing call only";
          type empty;
        }
        leaf default {
          description
            "Use the default authentication list";
          type empty;
        }
        leaf eap {
          description
            "Extensible Authentication Protocol (EAP)";
          when "not(../method = 'eap')" {
            tailf:xpath-root 3;
          }
          type empty;
        }
        leaf ms-chap {
          description
            "Microsoft Challenge Handshake Authentication Protocol (MS-CHAP)";
          when "not(../method = 'ms-chap')" {
            tailf:xpath-root 3;
          }
          type empty;
        }
        leaf ms-chap-v2 {
          description
            "Microsoft CHAP Version 2 (MS-CHAP-V2)";
          when "not(../method = 'ms-chap-v2')" {
            tailf:xpath-root 3;
          }
          type empty;
        }
        leaf one-time {
          description
            "Allow use of username*OTP for one-time passwords";
          type empty;
        }
        leaf optional {
          description
            "Allow peer to refuse to authenticate";
          type empty;
        }
        leaf pap {
          description
            "Password Authentication Protocol (PAP)";
          when "not(../method = 'pap')" {
            tailf:xpath-root 3;
          }
          type empty;
        }
      }
      leaf authorization {
        description
          "Set PPP network authorization method";
        type union {
          type string;
          type enumeration {
            enum "default";
          }
        }
      }
      container ipcp {
        description
          "Set IPCP negotiation options";
        container dns {
          description
            "Specify DNS negotiation options";
          leaf primary {
            type inet:ipv4-address;
          }
        }
      }
      container multilink {
        description
          "Make interface multilink capable";
        presence "true";
        container links {
          description
            "Specify the limits on the number of links in a bundle";
          container minimum {
            description
              "Minimum number of links desired in the bundle";
            leaf minimum-value {
              type uint8;
            }
            leaf mandatory {
              description
                "Disable network layer until minimum number of links is reach";
              type empty;
            }
          }
        }
        leaf group {
          description
            "Put interface in a multilink bundle";
          type uint32 {
            range "1..2147483647";
          }
        }
        container endpoint {
          description
            "Configure the local Endpoint Discriminator";
          leaf string {
            description
              "Use specified string";
            type string;
          }
        }
        container fragment {
          description
            "Specify fragmentation parameters";
          container delay {
            description
              "Specify the maximum delay for each fragment";
            leaf delay-value {
              type uint16 {
                range "0..1000";
              }
            }
            leaf additional-delay-value {
              type uint16 {
                range "1..999";
              }
            }
          }
        }
      }
    }
  }

  grouping live_ncs_config-ppp-grouping {
    container packet {
      description
        "Configure control packet rate throttling";
      leaf throttle {
        description
          "Configure control packet rate throttling";
        type uint32 {
          range "1..100000";
        }
      }
      leaf allow_time {
        type uint32 {
          range "1..3600";
        }
      }
      leaf block_time {
        type uint32 {
          range "2..3600";
        }
      }
    }
  }

  grouping live_ncs_config-multilink-grouping {
    leaf bundle-name {
      description
        "Select method for naming multilink bundles";
      type enumeration {
        enum "authenticated";
        enum "both";
        enum "endpoint";
        enum "rfc";
      }
    }
    leaf virtual-template {
      description
        "virtual-template interface";
      type uint16 {
        range "1..4095";
      }
    }
  }

  grouping live_ncs_config-interface-p2p-grouping {
    container ppp {
      description
        "Point-to-Point Protocol";
      leaf accounting {
        description
          "Set PPP network accounting method";
        type union {
          type string;
          type enumeration {
            enum "default";
          }
        }
      }
      container chap {
        description
          "Set CHAP authentication parameters";
        leaf hostname {
          description
            "Set alternate CHAP hostname";
          type string;
        }
        leaf challenge-length {
          description
            "Challenge Length for CHAP";
          type uint8 {
            range "16..63";
          }
        }
      }
      container authentication {
        description
          "Set PPP link authentication method";
        leaf method {
          type enumeration {
            enum "chap";
            enum "eap";
            enum "ms-chap";
            enum "ms-chap-v2";
            enum "pap";
          }
        }
        leaf list-name {
          type string;
        }
        leaf chap {
          // NCS drop when statement
          type empty;
        }
        leaf callback {
          description
            "Authenticate remote on callback only";
          type empty;
        }
        leaf callin {
          description
            "Authenticate remote on incoming call only";
          type empty;
        }
        leaf callout {
          description
            "Authenticate remote on outgoing call only";
          type empty;
        }
        leaf default {
          description
            "Use the default authentication list";
          type empty;
        }
        leaf eap {
          description
            "Extensible Authentication Protocol (EAP)";
          // NCS drop when statement
          type empty;
        }
        leaf ms-chap {
          description
            "Microsoft Challenge Handshake Authentication Protocol (MS-CHAP)";
          // NCS drop when statement
          type empty;
        }
        leaf ms-chap-v2 {
          description
            "Microsoft CHAP Version 2 (MS-CHAP-V2)";
          // NCS drop when statement
          type empty;
        }
        leaf one-time {
          description
            "Allow use of username*OTP for one-time passwords";
          type empty;
        }
        leaf optional {
          description
            "Allow peer to refuse to authenticate";
          type empty;
        }
        leaf pap {
          description
            "Password Authentication Protocol (PAP)";
          // NCS drop when statement
          type empty;
        }
      }
      leaf authorization {
        description
          "Set PPP network authorization method";
        type union {
          type string;
          type enumeration {
            enum "default";
          }
        }
      }
      container ipcp {
        description
          "Set IPCP negotiation options";
        container dns {
          description
            "Specify DNS negotiation options";
          leaf primary {
            type inet:ipv4-address;
          }
        }
      }
      container multilink {
        description
          "Make interface multilink capable";
        presence "true";
        container links {
          description
            "Specify the limits on the number of links in a bundle";
          container minimum {
            description
              "Minimum number of links desired in the bundle";
            leaf minimum-value {
              type uint8;
            }
            leaf mandatory {
              description
                "Disable network layer until minimum number of links is reach";
              type empty;
            }
          }
        }
        leaf group {
          description
            "Put interface in a multilink bundle";
          type uint32 {
            range "1..2147483647";
          }
        }
        container endpoint {
          description
            "Configure the local Endpoint Discriminator";
          leaf string {
            description
              "Use specified string";
            type string;
          }
        }
        container fragment {
          description
            "Specify fragmentation parameters";
          container delay {
            description
              "Specify the maximum delay for each fragment";
            leaf delay-value {
              type uint16 {
                range "0..1000";
              }
            }
            leaf additional-delay-value {
              type uint16 {
                range "1..999";
              }
            }
          }
        }
      }
    }
  }

  grouping config-ppp-grouping {
    container packet {
      description
        "Configure control packet rate throttling";
      leaf throttle {
        description
          "Configure control packet rate throttling";
        type uint32 {
          range "1..100000";
        }
      }
      leaf allow_time {
        type uint32 {
          range "1..3600";
        }
      }
      leaf block_time {
        type uint32 {
          range "2..3600";
        }
      }
    }
  }

  grouping config-multilink-grouping {
    leaf bundle-name {
      description
        "Select method for naming multilink bundles";
      type enumeration {
        enum "authenticated";
        enum "both";
        enum "endpoint";
        enum "rfc";
      }
    }
    leaf virtual-template {
      description
        "virtual-template interface";
      type uint16 {
        range "1..4095";
      }
    }
  }

  grouping config-interface-p2p-grouping {
    container ppp {
      description
        "Point-to-Point Protocol";
      leaf accounting {
        description
          "Set PPP network accounting method";
        type union {
          type string;
          type enumeration {
            enum "default";
          }
        }
      }
      container chap {
        description
          "Set CHAP authentication parameters";
        leaf hostname {
          description
            "Set alternate CHAP hostname";
          type string;
        }
        leaf challenge-length {
          description
            "Challenge Length for CHAP";
          type uint8 {
            range "16..63";
          }
        }
      }
      container authentication {
        description
          "Set PPP link authentication method";
        leaf method {
          type enumeration {
            enum "chap";
            enum "eap";
            enum "ms-chap";
            enum "ms-chap-v2";
            enum "pap";
          }
        }
        leaf list-name {
          type string;
        }
        leaf chap {
          when "not(../method = 'chap')" {
            tailf:xpath-root 3;
          }
          type empty;
        }
        leaf callback {
          description
            "Authenticate remote on callback only";
          type empty;
        }
        leaf callin {
          description
            "Authenticate remote on incoming call only";
          type empty;
        }
        leaf callout {
          description
            "Authenticate remote on outgoing call only";
          type empty;
        }
        leaf default {
          description
            "Use the default authentication list";
          type empty;
        }
        leaf eap {
          description
            "Extensible Authentication Protocol (EAP)";
          when "not(../method = 'eap')" {
            tailf:xpath-root 3;
          }
          type empty;
        }
        leaf ms-chap {
          description
            "Microsoft Challenge Handshake Authentication Protocol (MS-CHAP)";
          when "not(../method = 'ms-chap')" {
            tailf:xpath-root 3;
          }
          type empty;
        }
        leaf ms-chap-v2 {
          description
            "Microsoft CHAP Version 2 (MS-CHAP-V2)";
          when "not(../method = 'ms-chap-v2')" {
            tailf:xpath-root 3;
          }
          type empty;
        }
        leaf one-time {
          description
            "Allow use of username*OTP for one-time passwords";
          type empty;
        }
        leaf optional {
          description
            "Allow peer to refuse to authenticate";
          type empty;
        }
        leaf pap {
          description
            "Password Authentication Protocol (PAP)";
          when "not(../method = 'pap')" {
            tailf:xpath-root 3;
          }
          type empty;
        }
      }
      leaf authorization {
        description
          "Set PPP network authorization method";
        type union {
          type string;
          type enumeration {
            enum "default";
          }
        }
      }
      container ipcp {
        description
          "Set IPCP negotiation options";
        container dns {
          description
            "Specify DNS negotiation options";
          leaf primary {
            type inet:ipv4-address;
          }
        }
      }
      container multilink {
        description
          "Make interface multilink capable";
        presence "true";
        container links {
          description
            "Specify the limits on the number of links in a bundle";
          container minimum {
            description
              "Minimum number of links desired in the bundle";
            leaf minimum-value {
              type uint8;
            }
            leaf mandatory {
              description
                "Disable network layer until minimum number of links is reach";
              type empty;
            }
          }
        }
        leaf group {
          description
            "Put interface in a multilink bundle";
          type uint32 {
            range "1..2147483647";
          }
        }
        container endpoint {
          description
            "Configure the local Endpoint Discriminator";
          leaf string {
            description
              "Use specified string";
            type string;
          }
        }
        container fragment {
          description
            "Specify fragmentation parameters";
          container delay {
            description
              "Specify the maximum delay for each fragment";
            leaf delay-value {
              type uint16 {
                range "0..1000";
              }
            }
            leaf additional-delay-value {
              type uint16 {
                range "1..999";
              }
            }
          }
        }
      }
    }
  }

  augment "/ncs:devices/ncs:template/ncs:config/ios:native/ios:ppp" {
    uses ncs_template_config-ppp-grouping;
  }
  augment "/ncs:devices/ncs:device/ncs:live-status/ios:native/ios:ppp" {
    uses live_ncs_config-ppp-grouping {
      refine packet {
        tailf:ncs-device-type "netconf";
        tailf:display-when "not(../../../../ncs:module) or ../../../../ncs:module[ncs:name='Cisco-IOS-XE-ppp'] or (../../../../ncs:live-status-protocol[not(ncs:capability)]) or (../../../../ncs:live-status-protocol/ncs:capability/ncs:module[.='Cisco-IOS-XE-ppp'])";
      }
    }
  }
  augment "/ncs:devices/ncs:device/ncs:config/ios:native/ios:ppp" {
    uses config-ppp-grouping {
      refine packet {
        tailf:ncs-device-type "netconf";
        tailf:display-when "not(../../../../ncs:module) or ../../../../ncs:module[ncs:name='Cisco-IOS-XE-ppp']";
      }
    }
  }
  augment "/ncs:devices/ncs:template/ncs:config/ios:native/ios:multilink" {
    uses ncs_template_config-multilink-grouping {
      // NCS drop if-feature statement
    }
  }
  augment "/ncs:devices/ncs:device/ncs:live-status/ios:native/ios:multilink" {
    uses live_ncs_config-multilink-grouping {
      refine virtual-template {
        tailf:ncs-device-type "netconf";
        tailf:display-when "not(../../../../ncs:module) or ../../../../ncs:module[ncs:name='Cisco-IOS-XE-ppp'] or (../../../../ncs:live-status-protocol[not(ncs:capability)]) or (../../../../ncs:live-status-protocol/ncs:capability/ncs:module[.='Cisco-IOS-XE-ppp'])";
      }
      refine bundle-name {
        tailf:ncs-device-type "netconf";
        tailf:display-when "not(../../../../ncs:module) or ../../../../ncs:module[ncs:name='Cisco-IOS-XE-ppp'] or (../../../../ncs:live-status-protocol[not(ncs:capability)]) or (../../../../ncs:live-status-protocol/ncs:capability/ncs:module[.='Cisco-IOS-XE-ppp'])";
      }
      // NCS drop if-feature statement
    }
  }
  augment "/ncs:devices/ncs:device/ncs:config/ios:native/ios:multilink" {
    uses config-multilink-grouping {
      refine virtual-template {
        tailf:ncs-device-type "netconf";
        tailf:display-when "not(../../../../ncs:module) or ../../../../ncs:module[ncs:name='Cisco-IOS-XE-ppp']";
      }
      refine bundle-name {
        tailf:ncs-device-type "netconf";
        tailf:display-when "not(../../../../ncs:module) or ../../../../ncs:module[ncs:name='Cisco-IOS-XE-ppp']";
      }
      // NCS drop if-feature statement
    }
  }
  augment "/ncs:devices/ncs:template/ncs:config/ios:native/ios:interface/ios:Multilink" {
    uses ncs_template_config-interface-p2p-grouping {
      // NCS drop if-feature statement
    }
  }
  augment "/ncs:devices/ncs:device/ncs:live-status/ios:native/ios:interface/ios:Multilink" {
    uses live_ncs_config-interface-p2p-grouping {
      refine ppp {
        tailf:ncs-device-type "netconf";
        tailf:display-when "not(../../../../../ncs:module) or ../../../../../ncs:module[ncs:name='Cisco-IOS-XE-ppp'] or (../../../../../ncs:live-status-protocol[not(ncs:capability)]) or (../../../../../ncs:live-status-protocol/ncs:capability/ncs:module[.='Cisco-IOS-XE-ppp'])";
      }
      // NCS drop if-feature statement
    }
  }
  augment "/ncs:devices/ncs:device/ncs:config/ios:native/ios:interface/ios:Multilink" {
    uses config-interface-p2p-grouping {
      refine ppp {
        tailf:ncs-device-type "netconf";
        tailf:display-when "not(../../../../../ncs:module) or ../../../../../ncs:module[ncs:name='Cisco-IOS-XE-ppp']";
      }
      // NCS drop if-feature statement
    }
  }
  augment "/ncs:devices/ncs:template/ncs:config/ios:native/ios:interface/ios:Serial" {
    uses ncs_template_config-interface-p2p-grouping {
      // NCS drop if-feature statement
    }
  }
  augment "/ncs:devices/ncs:device/ncs:live-status/ios:native/ios:interface/ios:Serial" {
    uses live_ncs_config-interface-p2p-grouping {
      refine ppp {
        tailf:ncs-device-type "netconf";
        tailf:display-when "not(../../../../../ncs:module) or ../../../../../ncs:module[ncs:name='Cisco-IOS-XE-ppp'] or (../../../../../ncs:live-status-protocol[not(ncs:capability)]) or (../../../../../ncs:live-status-protocol/ncs:capability/ncs:module[.='Cisco-IOS-XE-ppp'])";
      }
      // NCS drop if-feature statement
    }
  }
  augment "/ncs:devices/ncs:device/ncs:config/ios:native/ios:interface/ios:Serial" {
    uses config-interface-p2p-grouping {
      refine ppp {
        tailf:ncs-device-type "netconf";
        tailf:display-when "not(../../../../../ncs:module) or ../../../../../ncs:module[ncs:name='Cisco-IOS-XE-ppp']";
      }
      // NCS drop if-feature statement
    }
  }
  augment "/ncs:devices/ncs:template/ncs:config/ios:native/ios:interface/ios:Virtual-Template" {
    uses ncs_template_config-interface-p2p-grouping {
      // NCS drop if-feature statement
    }
  }
  augment "/ncs:devices/ncs:device/ncs:live-status/ios:native/ios:interface/ios:Virtual-Template" {
    uses live_ncs_config-interface-p2p-grouping {
      refine ppp {
        tailf:ncs-device-type "netconf";
        tailf:display-when "not(../../../../../ncs:module) or ../../../../../ncs:module[ncs:name='Cisco-IOS-XE-ppp'] or (../../../../../ncs:live-status-protocol[not(ncs:capability)]) or (../../../../../ncs:live-status-protocol/ncs:capability/ncs:module[.='Cisco-IOS-XE-ppp'])";
      }
      // NCS drop if-feature statement
    }
  }
  augment "/ncs:devices/ncs:device/ncs:config/ios:native/ios:interface/ios:Virtual-Template" {
    uses config-interface-p2p-grouping {
      refine ppp {
        tailf:ncs-device-type "netconf";
        tailf:display-when "not(../../../../../ncs:module) or ../../../../../ncs:module[ncs:name='Cisco-IOS-XE-ppp']";
      }
      // NCS drop if-feature statement
    }
  }
}
