module Cisco-IOS-XE-service-routing {
  // Generated by yanger -t ncs
  tailf:ncs-device-type "netconf";

  namespace "http://cisco.com/ns/yang/Cisco-IOS-XE-service-routing";
  prefix ios-sr;

  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Service Routing Yang model.
     Copyright (c) 2016 by Cisco Systems, Inc.
     All rights reserved.";

  revision 2017-05-09 {
    description
      "add service-routing mdns-sd support";
  }
  revision 2017-02-07 {
    description
      "Initial revision";
  }

  grouping ncs_template_config-service-routing-grouping {
    container service-routing {
      description
        "Configure service-routing";
      leaf capabilities-manager {
        description
          "Service-Routing Capabilities Manager configuration";
        type string;
      }
      leaf mdns-sd {
        description
          "Service-Routing MDNS configuration";
        type empty;
      }
    }
  }

  grouping ncs_rpc_notif_config-service-routing-grouping {
    container service-routing {
      description
        "Configure service-routing";
      leaf capabilities-manager {
        description
          "Service-Routing Capabilities Manager configuration";
        type boolean;
      }
      leaf mdns-sd {
        description
          "Service-Routing MDNS configuration";
        type empty;
      }
    }
  }

  grouping live_ncs_config-service-routing-grouping {
    container service-routing {
      description
        "Configure service-routing";
      leaf capabilities-manager {
        description
          "Service-Routing Capabilities Manager configuration";
        type boolean;
      }
      leaf mdns-sd {
        description
          "Service-Routing MDNS configuration";
        type empty;
      }
    }
  }

  grouping config-service-routing-grouping {
    container service-routing {
      description
        "Configure service-routing";
      leaf capabilities-manager {
        description
          "Service-Routing Capabilities Manager configuration";
        type boolean;
      }
      leaf mdns-sd {
        description
          "Service-Routing MDNS configuration";
        type empty;
      }
    }
  }

  augment "/ncs:devices/ncs:template/ncs:config/ios:native" {
    uses ncs_template_config-service-routing-grouping;
  }
  augment "/ncs:devices/ncs:device/ncs:live-status/ios:native" {
    uses live_ncs_config-service-routing-grouping {
      refine service-routing {
        tailf:ncs-device-type "netconf";
        tailf:display-when "not(../../../ncs:module) or ../../../ncs:module[ncs:name='Cisco-IOS-XE-service-routing'] or (../../../ncs:live-status-protocol[not(ncs:capability)]) or (../../../ncs:live-status-protocol/ncs:capability/ncs:module[.='Cisco-IOS-XE-service-routing'])";
      }
    }
  }
  augment "/ncs:devices/ncs:device/ncs:config/ios:native" {
    uses config-service-routing-grouping {
      refine service-routing {
        tailf:ncs-device-type "netconf";
        tailf:display-when "not(../../../ncs:module) or ../../../ncs:module[ncs:name='Cisco-IOS-XE-service-routing']";
      }
    }
  }
}
