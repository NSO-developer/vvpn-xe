module Cisco-IOS-XE-spanning-tree {
  // Generated by yanger -t ncs
  tailf:ncs-device-type "netconf";

  namespace "http://cisco.com/ns/yang/Cisco-IOS-XE-spanning-tree";
  prefix ios-stp;

  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Spanning Tree (stp) Yang Model.
     Copyright (c) 2016 by Cisco Systems, Inc.
     All rights reserved.";

  revision 2017-02-07 {
    description
      "Initial revision";
  }

  grouping ncs_template_config-spanning-tree-grouping {
    leaf backbonefast {
      description
        "Enable BackboneFast Feature";
      type empty;
    }
    container bridge {
      leaf priority {
        type string;
      }
      leaf ID {
        type string;
      }
    }
    container etherchannel {
      description
        "Spanning tree etherchannel specific configuration";
      container guard {
        description
          "Configure guard features for etherchannel";
        leaf misconfig {
          description
            "Enable guard to protect against etherchannel misconfiguration";
          type empty;
        }
      }
    }
    container extend {
      description
        "Spanning Tree 802.1t extensions";
      leaf system-id {
        description
          "Extend system-id into priority portion of the bridge id (PVST & Rapid PVST only)";
        type empty;
      }
    }
    leaf logging {
      description
        "Enable Spanning tree logging";
      type empty;
    }
    container loopguard {
      description
        "Spanning tree loopguard options";
      leaf default {
        description
          "Enable loopguard by default on all ports";
        type empty;
      }
    }
    container mst {
      description
        "Multiple spanning tree configuration";
      list instance-range {
        // NCS patched for predictable order
        ordered-by user;
        key "id";
        leaf id {
          type string;
        }
        leaf priority {
          description
            "Set the bridge priority for the spanning tree";
          type string;
        }
        leaf root {
          description
            "Configure switch as root";
          type string;
        }
      }
      container configuration {
        description
          "Enter MST configuration submode";
        leaf name {
          description
            "Set configuration name";
          type string;
        }
        list instance {
          // NCS patched for predictable order
          ordered-by user;
          description
            "Map vlans to an MST instance";
          key "id";
          leaf id {
            type string;
          }
          leaf-list vlan {
            // NCS patched for predictable order
            ordered-by user;
            description
              "Range of vlans to add to the instance mapping";
            type string;
          }
        }
        container private-vlan {
          description
            "Set private-vlan synchronization";
          leaf synchronize {
            description
              "Synchronize vlans";
            type empty;
          }
        }
        leaf revision {
          description
            "Set configuration revision number";
          type string;
        }
      }
      leaf forward-time {
        description
          "number of seconds for the forward delay timer";
        type string;
      }
      leaf hello-time {
        description
          "number of seconds between generation of config BPDUs";
        type string;
      }
      leaf max-age {
        description
          "maximum number of seconds the information in a BPDU is valid";
        type string;
      }
      leaf max-hops {
        description
          "maximum number of hops a BPDU is valid";
        type string;
      }
    }
    container optimize {
      container bpdu {
        leaf transmission {
          type string;
        }
      }
    }
    container pathcost {
      description
        "Spanning tree pathcost options";
      container method {
        description
          "Method to calculate default port path cost";
        leaf long {
          description
            "Use 32 bit based values for default port path costs";
          type empty;
        }
        leaf short {
          type empty;
        }
      }
    }
    container portfast {
      description
        "Spanning tree portfast options";
      leaf bdpu {
        type string;
      }
      leaf default {
        description
          "Enable portfast by default on all access ports";
        type empty;
      }
    }
    container transmit {
      description
        "STP transmit parameters";
      leaf hold-count {
        description
          "Value for txholdcount parameter";
        type string;
      }
    }
    container uplinkfast {
      description
        "Enable UplinkFast Feature";
      presence "true";
      leaf max-update-rate {
        description
          "Rate at which station address updates are sent";
        type string;
      }
    }
    leaf mode {
      description
        "Spanning tree operating mode";
      type string;
    }
    list vlan {
      // NCS patched for predictable order
      ordered-by user;
      description
        "VLAN Switch Spanning Tree";
      key "id";
      leaf id {
        type string;
      }
      leaf max-age {
        description
          "Set the max age interval for the spanning tree";
        type string;
      }
      leaf forward-time {
        description
          "Set the forward delay for the spanning tree";
        type string;
      }
      leaf hello-time {
        description
          "Set the hello interval for the spanning tree";
        type string;
      }
      leaf priority {
        description
          "Set the bridge priority for the spanning tree";
        type string;
      }
      container root {
        description
          "Configure switch as root";
        container primary {
          description
            "Configure this switch as primary root for this spanning tree";
          leaf diameter {
            description
              "Network diameter of this spanning tree";
            type string;
          }
          leaf hello-time {
            description
              "Hello interval for this spanning tree";
            type string;
          }
        }
        container secondary {
          description
            "Configure switch as secondary root";
          leaf diameter {
            description
              "Network diameter of this spanning tree";
            type string;
          }
          leaf hello-time {
            description
              "Hello interval for this spanning tree";
            type string;
          }
        }
      }
    }
  }

  grouping ncs_template_config-interface-spanning-tree {
    container spanning-tree {
      description
        "Spanning Tree Subsystem";
      leaf bpdufilter {
        description
          "Don't send or receive BPDUs on this interface";
        type string;
      }
      container bpduguard {
        description
          "Don't accept BPDUs on this interface";
        choice bpduguard-choice {
          leaf disable {
            description
              "Disable BPDU guard for this interface";
            type empty;
          }
          leaf enable {
            type empty;
            description
              "Enable BPDU guard for this interface";
          }
        }
      }
      leaf cost {
        description
          "To set the path cost of the interface";
        type string;
      }
      leaf guard {
        description
          "Change an interface's spanning tree guard mode";
        type string;
      }
      leaf link-type {
        description
          "Specify a link type for spanning tree tree protocol use";
        type string;
      }
      container portfast {
        description
          "Spanning tree portfast options";
        presence "true";
        leaf disable {
          description
            "Disable portfast for this interface";
          type empty;
        }
        leaf trunk {
          description
            "Enable portfast on the interface even in trunk mode";
          type empty;
        }
        leaf edge {
          description
            "Enable portfast edge on the interface";
          type empty;
        }
      }
      leaf port-priority {
        description
          "Spanning tree port-priority options";
        type string;
      }
      container vlan {
        description
          "VLAN Switch Spanning Tree";
        leaf-list vlan-ids {
          // NCS patched for predictable order
          ordered-by user;
          description
            "vlan range, example: 1,3-5,7,9-11";
          type string;
        }
        leaf cost {
          description
            "<1-200000000> Spanning-tree cost";
          type string;
        }
        leaf port-priority {
          description
            "<0-240> port priority in increments of 16";
          type string;
        }
      }
      container loopguard {
        description
          "Spanning tree loopguard options";
        leaf default {
          description
            "Enable loopguard by default on all ports";
          type empty;
        }
      }
      container mst {
        description
          "Per interface MST configurations";
        leaf instance {
          description
            "MST instance list, example 0,2-4,6,8-12";
          type string;
        }
        leaf cost {
          description
            "<1-200000000> Spanning-tree cost";
          type string;
        }
        leaf port-priority {
          description
            "<0-240> port priority in increments of 16";
          type string;
        }
        leaf pre-standard {
          description
            "Force pre-standard MST BPDU transmission on port";
          type empty;
        }
      }
    }
  }

  grouping ncs_rpc_notif_config-spanning-tree-grouping {
    leaf backbonefast {
      description
        "Enable BackboneFast Feature";
      type empty;
    }
    container bridge {
      leaf priority {
        type uint8;
      }
      leaf ID {
        type string;
      }
    }
    container etherchannel {
      description
        "Spanning tree etherchannel specific configuration";
      container guard {
        description
          "Configure guard features for etherchannel";
        leaf misconfig {
          description
            "Enable guard to protect against etherchannel misconfiguration";
          type empty;
        }
      }
    }
    container extend {
      description
        "Spanning Tree 802.1t extensions";
      leaf system-id {
        description
          "Extend system-id into priority portion of the bridge id (PVST & Rapid PVST only)";
        type empty;
      }
    }
    leaf logging {
      description
        "Enable Spanning tree logging";
      type empty;
    }
    container loopguard {
      description
        "Spanning tree loopguard options";
      leaf default {
        description
          "Enable loopguard by default on all ports";
        type empty;
      }
    }
    container mst {
      description
        "Multiple spanning tree configuration";
      list instance-range {
        key "id";
        leaf id {
          type union {
            type uint16;
            type string;
          }
        }
        leaf priority {
          description
            "Set the bridge priority for the spanning tree";
          type uint16 {
            range "0..61440";
          }
        }
        leaf root {
          description
            "Configure switch as root";
          type enumeration {
            enum "primary";
            enum "secondary";
          }
        }
      }
      container configuration {
        description
          "Enter MST configuration submode";
        leaf name {
          description
            "Set configuration name";
          type string;
        }
        list instance {
          description
            "Map vlans to an MST instance";
          key "id";
          leaf id {
            type uint16 {
              range "0..4094";
            }
          }
          leaf-list vlan {
            description
              "Range of vlans to add to the instance mapping";
            type union {
              type uint16;
              type string;
            }
          }
        }
        container private-vlan {
          description
            "Set private-vlan synchronization";
          leaf synchronize {
            description
              "Synchronize vlans";
            type empty;
          }
        }
        leaf revision {
          description
            "Set configuration revision number";
          type uint16;
        }
      }
      leaf forward-time {
        description
          "number of seconds for the forward delay timer";
        type uint8 {
          range "4..30";
        }
      }
      leaf hello-time {
        description
          "number of seconds between generation of config BPDUs";
        type uint8 {
          range "1..10";
        }
      }
      leaf max-age {
        description
          "maximum number of seconds the information in a BPDU is valid";
        type uint8 {
          range "6..40";
        }
      }
      leaf max-hops {
        description
          "maximum number of hops a BPDU is valid";
        type uint8 {
          range "1..255";
        }
      }
    }
    container optimize {
      container bpdu {
        leaf transmission {
          type boolean;
        }
      }
    }
    container pathcost {
      description
        "Spanning tree pathcost options";
      container method {
        description
          "Method to calculate default port path cost";
        leaf long {
          description
            "Use 32 bit based values for default port path costs";
          type empty;
        }
        leaf short {
          type empty;
        }
      }
    }
    container portfast {
      description
        "Spanning tree portfast options";
      leaf bdpu {
        type enumeration {
          enum "bpdufilter";
          enum "bpduguard";
        }
      }
      leaf default {
        description
          "Enable portfast by default on all access ports";
        type empty;
      }
    }
    container transmit {
      description
        "STP transmit parameters";
      leaf hold-count {
        description
          "Value for txholdcount parameter";
        type uint8 {
          range "1..20";
        }
      }
    }
    container uplinkfast {
      description
        "Enable UplinkFast Feature";
      presence "true";
      leaf max-update-rate {
        description
          "Rate at which station address updates are sent";
        type uint32 {
          range "0..32000";
        }
      }
    }
    leaf mode {
      description
        "Spanning tree operating mode";
      type enumeration {
        enum "mst";
        enum "pvst";
        enum "rapid-pvst";
      }
    }
    list vlan {
      description
        "VLAN Switch Spanning Tree";
      key "id";
      leaf id {
        type string;
      }
      leaf max-age {
        description
          "Set the max age interval for the spanning tree";
        type uint8 {
          range "6..40";
        }
      }
      leaf forward-time {
        description
          "Set the forward delay for the spanning tree";
        type uint8 {
          range "4..30";
        }
      }
      leaf hello-time {
        description
          "Set the hello interval for the spanning tree";
        type uint8 {
          range "1..10";
        }
      }
      leaf priority {
        description
          "Set the bridge priority for the spanning tree";
        type uint16 {
          range "0..61440";
        }
      }
      container root {
        description
          "Configure switch as root";
        container primary {
          description
            "Configure this switch as primary root for this spanning tree";
          leaf diameter {
            description
              "Network diameter of this spanning tree";
            type uint8 {
              range "2..7";
            }
          }
          leaf hello-time {
            description
              "Hello interval for this spanning tree";
            type uint8 {
              range "1..10";
            }
          }
        }
        container secondary {
          description
            "Configure switch as secondary root";
          leaf diameter {
            description
              "Network diameter of this spanning tree";
            type uint8 {
              range "2..7";
            }
          }
          leaf hello-time {
            description
              "Hello interval for this spanning tree";
            type uint8 {
              range "1..10";
            }
          }
        }
      }
    }
  }

  grouping ncs_rpc_notif_config-interface-spanning-tree {
    container spanning-tree {
      description
        "Spanning Tree Subsystem";
      leaf bpdufilter {
        description
          "Don't send or receive BPDUs on this interface";
        type enumeration {
          enum "disable";
          enum "enable";
        }
      }
      container bpduguard {
        description
          "Don't accept BPDUs on this interface";
        choice bpduguard-choice {
          leaf disable {
            description
              "Disable BPDU guard for this interface";
            type empty;
          }
          leaf enable {
            type empty;
            description
              "Enable BPDU guard for this interface";
          }
        }
      }
      leaf cost {
        description
          "To set the path cost of the interface";
        type uint32 {
          range "1..200000000";
        }
      }
      leaf guard {
        description
          "Change an interface's spanning tree guard mode";
        type enumeration {
          enum "loop";
          enum "none";
          enum "root";
        }
      }
      leaf link-type {
        description
          "Specify a link type for spanning tree tree protocol use";
        type enumeration {
          enum "auto";
          enum "none";
          enum "point-to-point";
          enum "root";
          enum "shared";
        }
      }
      container portfast {
        description
          "Spanning tree portfast options";
        presence "true";
        leaf disable {
          description
            "Disable portfast for this interface";
          type empty;
        }
        leaf trunk {
          description
            "Enable portfast on the interface even in trunk mode";
          type empty;
        }
        leaf edge {
          description
            "Enable portfast edge on the interface";
          type empty;
        }
      }
      leaf port-priority {
        description
          "Spanning tree port-priority options";
        type uint8 {
          range "0..240";
        }
      }
      container vlan {
        description
          "VLAN Switch Spanning Tree";
        leaf-list vlan-ids {
          description
            "vlan range, example: 1,3-5,7,9-11";
          type union {
            type uint16 {
              range "1..4095";
            }
            type string;
          }
        }
        leaf cost {
          description
            "<1-200000000> Spanning-tree cost";
          type uint32 {
            range "1..200000000";
          }
        }
        leaf port-priority {
          description
            "<0-240> port priority in increments of 16";
          type uint16 {
            range "0..240";
          }
        }
      }
      container loopguard {
        description
          "Spanning tree loopguard options";
        leaf default {
          description
            "Enable loopguard by default on all ports";
          type empty;
        }
      }
      container mst {
        description
          "Per interface MST configurations";
        leaf instance {
          description
            "MST instance list, example 0,2-4,6,8-12";
          type string;
        }
        leaf cost {
          description
            "<1-200000000> Spanning-tree cost";
          type uint32 {
            range "1..200000000";
          }
        }
        leaf port-priority {
          description
            "<0-240> port priority in increments of 16";
          type uint16 {
            range "0..240";
          }
        }
        leaf pre-standard {
          description
            "Force pre-standard MST BPDU transmission on port";
          type empty;
        }
      }
    }
  }

  grouping live_ncs_config-spanning-tree-grouping {
    leaf backbonefast {
      description
        "Enable BackboneFast Feature";
      type empty;
    }
    container bridge {
      leaf priority {
        type uint8;
      }
      leaf ID {
        type string;
      }
    }
    container etherchannel {
      description
        "Spanning tree etherchannel specific configuration";
      container guard {
        description
          "Configure guard features for etherchannel";
        leaf misconfig {
          description
            "Enable guard to protect against etherchannel misconfiguration";
          type empty;
        }
      }
    }
    container extend {
      description
        "Spanning Tree 802.1t extensions";
      leaf system-id {
        description
          "Extend system-id into priority portion of the bridge id (PVST & Rapid PVST only)";
        type empty;
      }
    }
    leaf logging {
      description
        "Enable Spanning tree logging";
      type empty;
    }
    container loopguard {
      description
        "Spanning tree loopguard options";
      leaf default {
        description
          "Enable loopguard by default on all ports";
        type empty;
      }
    }
    container mst {
      description
        "Multiple spanning tree configuration";
      list instance-range {
        key "id";
        leaf id {
          type union {
            type uint16;
            type string;
          }
        }
        leaf priority {
          description
            "Set the bridge priority for the spanning tree";
          type uint16 {
            range "0..61440";
          }
        }
        leaf root {
          description
            "Configure switch as root";
          type enumeration {
            enum "primary";
            enum "secondary";
          }
        }
      }
      container configuration {
        description
          "Enter MST configuration submode";
        leaf name {
          description
            "Set configuration name";
          type string;
        }
        list instance {
          description
            "Map vlans to an MST instance";
          key "id";
          leaf id {
            type uint16 {
              range "0..4094";
            }
          }
          leaf-list vlan {
            description
              "Range of vlans to add to the instance mapping";
            type union {
              type uint16;
              type string;
            }
          }
        }
        container private-vlan {
          description
            "Set private-vlan synchronization";
          leaf synchronize {
            description
              "Synchronize vlans";
            type empty;
          }
        }
        leaf revision {
          description
            "Set configuration revision number";
          type uint16;
        }
      }
      leaf forward-time {
        description
          "number of seconds for the forward delay timer";
        type uint8 {
          range "4..30";
        }
      }
      leaf hello-time {
        description
          "number of seconds between generation of config BPDUs";
        type uint8 {
          range "1..10";
        }
      }
      leaf max-age {
        description
          "maximum number of seconds the information in a BPDU is valid";
        type uint8 {
          range "6..40";
        }
      }
      leaf max-hops {
        description
          "maximum number of hops a BPDU is valid";
        type uint8 {
          range "1..255";
        }
      }
    }
    container optimize {
      container bpdu {
        leaf transmission {
          type boolean;
        }
      }
    }
    container pathcost {
      description
        "Spanning tree pathcost options";
      container method {
        description
          "Method to calculate default port path cost";
        leaf long {
          description
            "Use 32 bit based values for default port path costs";
          type empty;
        }
        leaf short {
          type empty;
        }
      }
    }
    container portfast {
      description
        "Spanning tree portfast options";
      leaf bdpu {
        type enumeration {
          enum "bpdufilter";
          enum "bpduguard";
        }
      }
      leaf default {
        description
          "Enable portfast by default on all access ports";
        type empty;
      }
    }
    container transmit {
      description
        "STP transmit parameters";
      leaf hold-count {
        description
          "Value for txholdcount parameter";
        type uint8 {
          range "1..20";
        }
      }
    }
    container uplinkfast {
      description
        "Enable UplinkFast Feature";
      presence "true";
      leaf max-update-rate {
        description
          "Rate at which station address updates are sent";
        type uint32 {
          range "0..32000";
        }
      }
    }
    leaf mode {
      description
        "Spanning tree operating mode";
      type enumeration {
        enum "mst";
        enum "pvst";
        enum "rapid-pvst";
      }
    }
    list vlan {
      description
        "VLAN Switch Spanning Tree";
      key "id";
      leaf id {
        type string;
      }
      leaf max-age {
        description
          "Set the max age interval for the spanning tree";
        type uint8 {
          range "6..40";
        }
      }
      leaf forward-time {
        description
          "Set the forward delay for the spanning tree";
        type uint8 {
          range "4..30";
        }
      }
      leaf hello-time {
        description
          "Set the hello interval for the spanning tree";
        type uint8 {
          range "1..10";
        }
      }
      leaf priority {
        description
          "Set the bridge priority for the spanning tree";
        type uint16 {
          range "0..61440";
        }
      }
      container root {
        description
          "Configure switch as root";
        container primary {
          description
            "Configure this switch as primary root for this spanning tree";
          leaf diameter {
            description
              "Network diameter of this spanning tree";
            type uint8 {
              range "2..7";
            }
          }
          leaf hello-time {
            description
              "Hello interval for this spanning tree";
            type uint8 {
              range "1..10";
            }
          }
        }
        container secondary {
          description
            "Configure switch as secondary root";
          leaf diameter {
            description
              "Network diameter of this spanning tree";
            type uint8 {
              range "2..7";
            }
          }
          leaf hello-time {
            description
              "Hello interval for this spanning tree";
            type uint8 {
              range "1..10";
            }
          }
        }
      }
    }
  }

  grouping live_ncs_config-interface-spanning-tree {
    container spanning-tree {
      description
        "Spanning Tree Subsystem";
      leaf bpdufilter {
        description
          "Don't send or receive BPDUs on this interface";
        type enumeration {
          enum "disable";
          enum "enable";
        }
      }
      container bpduguard {
        description
          "Don't accept BPDUs on this interface";
        choice bpduguard-choice {
          leaf disable {
            description
              "Disable BPDU guard for this interface";
            type empty;
          }
          leaf enable {
            type empty;
            description
              "Enable BPDU guard for this interface";
          }
        }
      }
      leaf cost {
        description
          "To set the path cost of the interface";
        type uint32 {
          range "1..200000000";
        }
      }
      leaf guard {
        description
          "Change an interface's spanning tree guard mode";
        type enumeration {
          enum "loop";
          enum "none";
          enum "root";
        }
      }
      leaf link-type {
        description
          "Specify a link type for spanning tree tree protocol use";
        type enumeration {
          enum "auto";
          enum "none";
          enum "point-to-point";
          enum "root";
          enum "shared";
        }
      }
      container portfast {
        description
          "Spanning tree portfast options";
        presence "true";
        leaf disable {
          description
            "Disable portfast for this interface";
          type empty;
        }
        leaf trunk {
          description
            "Enable portfast on the interface even in trunk mode";
          type empty;
        }
        leaf edge {
          description
            "Enable portfast edge on the interface";
          type empty;
        }
      }
      leaf port-priority {
        description
          "Spanning tree port-priority options";
        type uint8 {
          range "0..240";
        }
      }
      container vlan {
        description
          "VLAN Switch Spanning Tree";
        leaf-list vlan-ids {
          description
            "vlan range, example: 1,3-5,7,9-11";
          type union {
            type uint16 {
              range "1..4095";
            }
            type string;
          }
        }
        leaf cost {
          description
            "<1-200000000> Spanning-tree cost";
          type uint32 {
            range "1..200000000";
          }
        }
        leaf port-priority {
          description
            "<0-240> port priority in increments of 16";
          type uint16 {
            range "0..240";
          }
        }
      }
      container loopguard {
        description
          "Spanning tree loopguard options";
        leaf default {
          description
            "Enable loopguard by default on all ports";
          type empty;
        }
      }
      container mst {
        description
          "Per interface MST configurations";
        leaf instance {
          description
            "MST instance list, example 0,2-4,6,8-12";
          type string;
        }
        leaf cost {
          description
            "<1-200000000> Spanning-tree cost";
          type uint32 {
            range "1..200000000";
          }
        }
        leaf port-priority {
          description
            "<0-240> port priority in increments of 16";
          type uint16 {
            range "0..240";
          }
        }
        leaf pre-standard {
          description
            "Force pre-standard MST BPDU transmission on port";
          type empty;
        }
      }
    }
  }

  grouping config-spanning-tree-grouping {
    leaf backbonefast {
      description
        "Enable BackboneFast Feature";
      type empty;
    }
    container bridge {
      leaf priority {
        type uint8;
      }
      leaf ID {
        type string;
      }
    }
    container etherchannel {
      description
        "Spanning tree etherchannel specific configuration";
      container guard {
        description
          "Configure guard features for etherchannel";
        leaf misconfig {
          description
            "Enable guard to protect against etherchannel misconfiguration";
          type empty;
        }
      }
    }
    container extend {
      description
        "Spanning Tree 802.1t extensions";
      leaf system-id {
        description
          "Extend system-id into priority portion of the bridge id (PVST & Rapid PVST only)";
        type empty;
      }
    }
    leaf logging {
      description
        "Enable Spanning tree logging";
      type empty;
    }
    container loopguard {
      description
        "Spanning tree loopguard options";
      leaf default {
        description
          "Enable loopguard by default on all ports";
        type empty;
      }
    }
    container mst {
      description
        "Multiple spanning tree configuration";
      list instance-range {
        key "id";
        leaf id {
          type union {
            type uint16;
            type string;
          }
        }
        leaf priority {
          description
            "Set the bridge priority for the spanning tree";
          type uint16 {
            range "0..61440";
          }
        }
        leaf root {
          description
            "Configure switch as root";
          type enumeration {
            enum "primary";
            enum "secondary";
          }
        }
      }
      container configuration {
        description
          "Enter MST configuration submode";
        leaf name {
          description
            "Set configuration name";
          type string;
        }
        list instance {
          description
            "Map vlans to an MST instance";
          key "id";
          leaf id {
            type uint16 {
              range "0..4094";
            }
          }
          leaf-list vlan {
            description
              "Range of vlans to add to the instance mapping";
            type union {
              type uint16;
              type string;
            }
          }
        }
        container private-vlan {
          description
            "Set private-vlan synchronization";
          leaf synchronize {
            description
              "Synchronize vlans";
            type empty;
          }
        }
        leaf revision {
          description
            "Set configuration revision number";
          type uint16;
        }
      }
      leaf forward-time {
        description
          "number of seconds for the forward delay timer";
        type uint8 {
          range "4..30";
        }
      }
      leaf hello-time {
        description
          "number of seconds between generation of config BPDUs";
        type uint8 {
          range "1..10";
        }
      }
      leaf max-age {
        description
          "maximum number of seconds the information in a BPDU is valid";
        type uint8 {
          range "6..40";
        }
      }
      leaf max-hops {
        description
          "maximum number of hops a BPDU is valid";
        type uint8 {
          range "1..255";
        }
      }
    }
    container optimize {
      container bpdu {
        leaf transmission {
          type boolean;
        }
      }
    }
    container pathcost {
      description
        "Spanning tree pathcost options";
      container method {
        description
          "Method to calculate default port path cost";
        leaf long {
          description
            "Use 32 bit based values for default port path costs";
          type empty;
        }
        leaf short {
          type empty;
        }
      }
    }
    container portfast {
      description
        "Spanning tree portfast options";
      leaf bdpu {
        type enumeration {
          enum "bpdufilter";
          enum "bpduguard";
        }
      }
      leaf default {
        description
          "Enable portfast by default on all access ports";
        type empty;
      }
    }
    container transmit {
      description
        "STP transmit parameters";
      leaf hold-count {
        description
          "Value for txholdcount parameter";
        type uint8 {
          range "1..20";
        }
      }
    }
    container uplinkfast {
      description
        "Enable UplinkFast Feature";
      presence "true";
      leaf max-update-rate {
        description
          "Rate at which station address updates are sent";
        type uint32 {
          range "0..32000";
        }
      }
    }
    leaf mode {
      description
        "Spanning tree operating mode";
      type enumeration {
        enum "mst";
        enum "pvst";
        enum "rapid-pvst";
      }
    }
    list vlan {
      description
        "VLAN Switch Spanning Tree";
      key "id";
      leaf id {
        type string;
      }
      leaf max-age {
        description
          "Set the max age interval for the spanning tree";
        type uint8 {
          range "6..40";
        }
      }
      leaf forward-time {
        description
          "Set the forward delay for the spanning tree";
        type uint8 {
          range "4..30";
        }
      }
      leaf hello-time {
        description
          "Set the hello interval for the spanning tree";
        type uint8 {
          range "1..10";
        }
      }
      leaf priority {
        description
          "Set the bridge priority for the spanning tree";
        type uint16 {
          range "0..61440";
        }
      }
      container root {
        description
          "Configure switch as root";
        container primary {
          description
            "Configure this switch as primary root for this spanning tree";
          leaf diameter {
            description
              "Network diameter of this spanning tree";
            type uint8 {
              range "2..7";
            }
          }
          leaf hello-time {
            description
              "Hello interval for this spanning tree";
            type uint8 {
              range "1..10";
            }
          }
        }
        container secondary {
          description
            "Configure switch as secondary root";
          leaf diameter {
            description
              "Network diameter of this spanning tree";
            type uint8 {
              range "2..7";
            }
          }
          leaf hello-time {
            description
              "Hello interval for this spanning tree";
            type uint8 {
              range "1..10";
            }
          }
        }
      }
    }
  }

  grouping config-interface-spanning-tree {
    container spanning-tree {
      description
        "Spanning Tree Subsystem";
      leaf bpdufilter {
        description
          "Don't send or receive BPDUs on this interface";
        type enumeration {
          enum "disable";
          enum "enable";
        }
      }
      container bpduguard {
        description
          "Don't accept BPDUs on this interface";
        choice bpduguard-choice {
          leaf disable {
            description
              "Disable BPDU guard for this interface";
            type empty;
          }
          leaf enable {
            type empty;
            description
              "Enable BPDU guard for this interface";
          }
        }
      }
      leaf cost {
        description
          "To set the path cost of the interface";
        type uint32 {
          range "1..200000000";
        }
      }
      leaf guard {
        description
          "Change an interface's spanning tree guard mode";
        type enumeration {
          enum "loop";
          enum "none";
          enum "root";
        }
      }
      leaf link-type {
        description
          "Specify a link type for spanning tree tree protocol use";
        type enumeration {
          enum "auto";
          enum "none";
          enum "point-to-point";
          enum "root";
          enum "shared";
        }
      }
      container portfast {
        description
          "Spanning tree portfast options";
        presence "true";
        leaf disable {
          description
            "Disable portfast for this interface";
          type empty;
        }
        leaf trunk {
          description
            "Enable portfast on the interface even in trunk mode";
          type empty;
        }
        leaf edge {
          description
            "Enable portfast edge on the interface";
          type empty;
        }
      }
      leaf port-priority {
        description
          "Spanning tree port-priority options";
        type uint8 {
          range "0..240";
        }
      }
      container vlan {
        description
          "VLAN Switch Spanning Tree";
        leaf-list vlan-ids {
          description
            "vlan range, example: 1,3-5,7,9-11";
          type union {
            type uint16 {
              range "1..4095";
            }
            type string;
          }
        }
        leaf cost {
          description
            "<1-200000000> Spanning-tree cost";
          type uint32 {
            range "1..200000000";
          }
        }
        leaf port-priority {
          description
            "<0-240> port priority in increments of 16";
          type uint16 {
            range "0..240";
          }
        }
      }
      container loopguard {
        description
          "Spanning tree loopguard options";
        leaf default {
          description
            "Enable loopguard by default on all ports";
          type empty;
        }
      }
      container mst {
        description
          "Per interface MST configurations";
        leaf instance {
          description
            "MST instance list, example 0,2-4,6,8-12";
          type string;
        }
        leaf cost {
          description
            "<1-200000000> Spanning-tree cost";
          type uint32 {
            range "1..200000000";
          }
        }
        leaf port-priority {
          description
            "<0-240> port priority in increments of 16";
          type uint16 {
            range "0..240";
          }
        }
        leaf pre-standard {
          description
            "Force pre-standard MST BPDU transmission on port";
          type empty;
        }
      }
    }
  }

  augment "/ncs:devices/ncs:template/ncs:config/ios:native/ios:spanning-tree" {
    uses ncs_template_config-spanning-tree-grouping;
  }
  augment "/ncs:devices/ncs:device/ncs:live-status/ios:native/ios:spanning-tree" {
    uses live_ncs_config-spanning-tree-grouping {
      refine vlan {
        tailf:ncs-device-type "netconf";
        tailf:display-when "not(../../../ncs:module) or ../../../ncs:module[ncs:name='Cisco-IOS-XE-spanning-tree'] or (../../../ncs:live-status-protocol[not(ncs:capability)]) or (../../../ncs:live-status-protocol/ncs:capability/ncs:module[.='Cisco-IOS-XE-spanning-tree'])";
      }
      refine mode {
        tailf:ncs-device-type "netconf";
        tailf:display-when "not(../../../../ncs:module) or ../../../../ncs:module[ncs:name='Cisco-IOS-XE-spanning-tree'] or (../../../../ncs:live-status-protocol[not(ncs:capability)]) or (../../../../ncs:live-status-protocol/ncs:capability/ncs:module[.='Cisco-IOS-XE-spanning-tree'])";
      }
      refine uplinkfast {
        tailf:ncs-device-type "netconf";
        tailf:display-when "not(../../../../ncs:module) or ../../../../ncs:module[ncs:name='Cisco-IOS-XE-spanning-tree'] or (../../../../ncs:live-status-protocol[not(ncs:capability)]) or (../../../../ncs:live-status-protocol/ncs:capability/ncs:module[.='Cisco-IOS-XE-spanning-tree'])";
      }
      refine transmit {
        tailf:ncs-device-type "netconf";
        tailf:display-when "not(../../../../ncs:module) or ../../../../ncs:module[ncs:name='Cisco-IOS-XE-spanning-tree'] or (../../../../ncs:live-status-protocol[not(ncs:capability)]) or (../../../../ncs:live-status-protocol/ncs:capability/ncs:module[.='Cisco-IOS-XE-spanning-tree'])";
      }
      refine portfast {
        tailf:ncs-device-type "netconf";
        tailf:display-when "not(../../../../ncs:module) or ../../../../ncs:module[ncs:name='Cisco-IOS-XE-spanning-tree'] or (../../../../ncs:live-status-protocol[not(ncs:capability)]) or (../../../../ncs:live-status-protocol/ncs:capability/ncs:module[.='Cisco-IOS-XE-spanning-tree'])";
      }
      refine pathcost {
        tailf:ncs-device-type "netconf";
        tailf:display-when "not(../../../../ncs:module) or ../../../../ncs:module[ncs:name='Cisco-IOS-XE-spanning-tree'] or (../../../../ncs:live-status-protocol[not(ncs:capability)]) or (../../../../ncs:live-status-protocol/ncs:capability/ncs:module[.='Cisco-IOS-XE-spanning-tree'])";
      }
      refine optimize {
        tailf:ncs-device-type "netconf";
        tailf:display-when "not(../../../../ncs:module) or ../../../../ncs:module[ncs:name='Cisco-IOS-XE-spanning-tree'] or (../../../../ncs:live-status-protocol[not(ncs:capability)]) or (../../../../ncs:live-status-protocol/ncs:capability/ncs:module[.='Cisco-IOS-XE-spanning-tree'])";
      }
      refine mst {
        tailf:ncs-device-type "netconf";
        tailf:display-when "not(../../../../ncs:module) or ../../../../ncs:module[ncs:name='Cisco-IOS-XE-spanning-tree'] or (../../../../ncs:live-status-protocol[not(ncs:capability)]) or (../../../../ncs:live-status-protocol/ncs:capability/ncs:module[.='Cisco-IOS-XE-spanning-tree'])";
      }
      refine loopguard {
        tailf:ncs-device-type "netconf";
        tailf:display-when "not(../../../../ncs:module) or ../../../../ncs:module[ncs:name='Cisco-IOS-XE-spanning-tree'] or (../../../../ncs:live-status-protocol[not(ncs:capability)]) or (../../../../ncs:live-status-protocol/ncs:capability/ncs:module[.='Cisco-IOS-XE-spanning-tree'])";
      }
      refine logging {
        tailf:ncs-device-type "netconf";
        tailf:display-when "not(../../../../ncs:module) or ../../../../ncs:module[ncs:name='Cisco-IOS-XE-spanning-tree'] or (../../../../ncs:live-status-protocol[not(ncs:capability)]) or (../../../../ncs:live-status-protocol/ncs:capability/ncs:module[.='Cisco-IOS-XE-spanning-tree'])";
      }
      refine extend {
        tailf:ncs-device-type "netconf";
        tailf:display-when "not(../../../../ncs:module) or ../../../../ncs:module[ncs:name='Cisco-IOS-XE-spanning-tree'] or (../../../../ncs:live-status-protocol[not(ncs:capability)]) or (../../../../ncs:live-status-protocol/ncs:capability/ncs:module[.='Cisco-IOS-XE-spanning-tree'])";
      }
      refine etherchannel {
        tailf:ncs-device-type "netconf";
        tailf:display-when "not(../../../../ncs:module) or ../../../../ncs:module[ncs:name='Cisco-IOS-XE-spanning-tree'] or (../../../../ncs:live-status-protocol[not(ncs:capability)]) or (../../../../ncs:live-status-protocol/ncs:capability/ncs:module[.='Cisco-IOS-XE-spanning-tree'])";
      }
      refine bridge {
        tailf:ncs-device-type "netconf";
        tailf:display-when "not(../../../../ncs:module) or ../../../../ncs:module[ncs:name='Cisco-IOS-XE-spanning-tree'] or (../../../../ncs:live-status-protocol[not(ncs:capability)]) or (../../../../ncs:live-status-protocol/ncs:capability/ncs:module[.='Cisco-IOS-XE-spanning-tree'])";
      }
      refine backbonefast {
        tailf:ncs-device-type "netconf";
        tailf:display-when "not(../../../../ncs:module) or ../../../../ncs:module[ncs:name='Cisco-IOS-XE-spanning-tree'] or (../../../../ncs:live-status-protocol[not(ncs:capability)]) or (../../../../ncs:live-status-protocol/ncs:capability/ncs:module[.='Cisco-IOS-XE-spanning-tree'])";
      }
    }
  }
  augment "/ncs:devices/ncs:device/ncs:config/ios:native/ios:spanning-tree" {
    uses config-spanning-tree-grouping {
      refine vlan {
        tailf:ncs-device-type "netconf";
        tailf:display-when "not(../../../ncs:module) or ../../../ncs:module[ncs:name='Cisco-IOS-XE-spanning-tree']";
      }
      refine mode {
        tailf:ncs-device-type "netconf";
        tailf:display-when "not(../../../../ncs:module) or ../../../../ncs:module[ncs:name='Cisco-IOS-XE-spanning-tree']";
      }
      refine uplinkfast {
        tailf:ncs-device-type "netconf";
        tailf:display-when "not(../../../../ncs:module) or ../../../../ncs:module[ncs:name='Cisco-IOS-XE-spanning-tree']";
      }
      refine transmit {
        tailf:ncs-device-type "netconf";
        tailf:display-when "not(../../../../ncs:module) or ../../../../ncs:module[ncs:name='Cisco-IOS-XE-spanning-tree']";
      }
      refine portfast {
        tailf:ncs-device-type "netconf";
        tailf:display-when "not(../../../../ncs:module) or ../../../../ncs:module[ncs:name='Cisco-IOS-XE-spanning-tree']";
      }
      refine pathcost {
        tailf:ncs-device-type "netconf";
        tailf:display-when "not(../../../../ncs:module) or ../../../../ncs:module[ncs:name='Cisco-IOS-XE-spanning-tree']";
      }
      refine optimize {
        tailf:ncs-device-type "netconf";
        tailf:display-when "not(../../../../ncs:module) or ../../../../ncs:module[ncs:name='Cisco-IOS-XE-spanning-tree']";
      }
      refine mst {
        tailf:ncs-device-type "netconf";
        tailf:display-when "not(../../../../ncs:module) or ../../../../ncs:module[ncs:name='Cisco-IOS-XE-spanning-tree']";
      }
      refine loopguard {
        tailf:ncs-device-type "netconf";
        tailf:display-when "not(../../../../ncs:module) or ../../../../ncs:module[ncs:name='Cisco-IOS-XE-spanning-tree']";
      }
      refine logging {
        tailf:ncs-device-type "netconf";
        tailf:display-when "not(../../../../ncs:module) or ../../../../ncs:module[ncs:name='Cisco-IOS-XE-spanning-tree']";
      }
      refine extend {
        tailf:ncs-device-type "netconf";
        tailf:display-when "not(../../../../ncs:module) or ../../../../ncs:module[ncs:name='Cisco-IOS-XE-spanning-tree']";
      }
      refine etherchannel {
        tailf:ncs-device-type "netconf";
        tailf:display-when "not(../../../../ncs:module) or ../../../../ncs:module[ncs:name='Cisco-IOS-XE-spanning-tree']";
      }
      refine bridge {
        tailf:ncs-device-type "netconf";
        tailf:display-when "not(../../../../ncs:module) or ../../../../ncs:module[ncs:name='Cisco-IOS-XE-spanning-tree']";
      }
      refine backbonefast {
        tailf:ncs-device-type "netconf";
        tailf:display-when "not(../../../../ncs:module) or ../../../../ncs:module[ncs:name='Cisco-IOS-XE-spanning-tree']";
      }
    }
  }
  augment "/ncs:devices/ncs:template/ncs:config/ios:native/ios:interface/ios:FastEthernet" {
    uses ncs_template_config-interface-spanning-tree;
  }
  augment "/ncs:devices/ncs:device/ncs:live-status/ios:native/ios:interface/ios:FastEthernet" {
    uses live_ncs_config-interface-spanning-tree {
      refine spanning-tree {
        tailf:ncs-device-type "netconf";
        tailf:display-when "not(../../../../../ncs:module) or ../../../../../ncs:module[ncs:name='Cisco-IOS-XE-spanning-tree'] or (../../../../../ncs:live-status-protocol[not(ncs:capability)]) or (../../../../../ncs:live-status-protocol/ncs:capability/ncs:module[.='Cisco-IOS-XE-spanning-tree'])";
      }
    }
  }
  augment "/ncs:devices/ncs:device/ncs:config/ios:native/ios:interface/ios:FastEthernet" {
    uses config-interface-spanning-tree {
      refine spanning-tree {
        tailf:ncs-device-type "netconf";
        tailf:display-when "not(../../../../../ncs:module) or ../../../../../ncs:module[ncs:name='Cisco-IOS-XE-spanning-tree']";
      }
    }
  }
  augment "/ncs:devices/ncs:template/ncs:config/ios:native/ios:interface/ios:GigabitEthernet" {
    uses ncs_template_config-interface-spanning-tree;
  }
  augment "/ncs:devices/ncs:device/ncs:live-status/ios:native/ios:interface/ios:GigabitEthernet" {
    uses live_ncs_config-interface-spanning-tree {
      refine spanning-tree {
        tailf:ncs-device-type "netconf";
        tailf:display-when "not(../../../../../ncs:module) or ../../../../../ncs:module[ncs:name='Cisco-IOS-XE-spanning-tree'] or (../../../../../ncs:live-status-protocol[not(ncs:capability)]) or (../../../../../ncs:live-status-protocol/ncs:capability/ncs:module[.='Cisco-IOS-XE-spanning-tree'])";
      }
    }
  }
  augment "/ncs:devices/ncs:device/ncs:config/ios:native/ios:interface/ios:GigabitEthernet" {
    uses config-interface-spanning-tree {
      refine spanning-tree {
        tailf:ncs-device-type "netconf";
        tailf:display-when "not(../../../../../ncs:module) or ../../../../../ncs:module[ncs:name='Cisco-IOS-XE-spanning-tree']";
      }
    }
  }
  augment "/ncs:devices/ncs:template/ncs:config/ios:native/ios:interface/ios:TenGigabitEthernet" {
    uses ncs_template_config-interface-spanning-tree;
  }
  augment "/ncs:devices/ncs:device/ncs:live-status/ios:native/ios:interface/ios:TenGigabitEthernet" {
    uses live_ncs_config-interface-spanning-tree {
      refine spanning-tree {
        tailf:ncs-device-type "netconf";
        tailf:display-when "not(../../../../../ncs:module) or ../../../../../ncs:module[ncs:name='Cisco-IOS-XE-spanning-tree'] or (../../../../../ncs:live-status-protocol[not(ncs:capability)]) or (../../../../../ncs:live-status-protocol/ncs:capability/ncs:module[.='Cisco-IOS-XE-spanning-tree'])";
      }
    }
  }
  augment "/ncs:devices/ncs:device/ncs:config/ios:native/ios:interface/ios:TenGigabitEthernet" {
    uses config-interface-spanning-tree {
      refine spanning-tree {
        tailf:ncs-device-type "netconf";
        tailf:display-when "not(../../../../../ncs:module) or ../../../../../ncs:module[ncs:name='Cisco-IOS-XE-spanning-tree']";
      }
    }
  }
  augment "/ncs:devices/ncs:template/ncs:config/ios:native/ios:interface/ios:Port-channel" {
    uses ncs_template_config-interface-spanning-tree;
  }
  augment "/ncs:devices/ncs:device/ncs:live-status/ios:native/ios:interface/ios:Port-channel" {
    uses live_ncs_config-interface-spanning-tree {
      refine spanning-tree {
        tailf:ncs-device-type "netconf";
        tailf:display-when "not(../../../../../ncs:module) or ../../../../../ncs:module[ncs:name='Cisco-IOS-XE-spanning-tree'] or (../../../../../ncs:live-status-protocol[not(ncs:capability)]) or (../../../../../ncs:live-status-protocol/ncs:capability/ncs:module[.='Cisco-IOS-XE-spanning-tree'])";
      }
    }
  }
  augment "/ncs:devices/ncs:device/ncs:config/ios:native/ios:interface/ios:Port-channel" {
    uses config-interface-spanning-tree {
      refine spanning-tree {
        tailf:ncs-device-type "netconf";
        tailf:display-when "not(../../../../../ncs:module) or ../../../../../ncs:module[ncs:name='Cisco-IOS-XE-spanning-tree']";
      }
    }
  }
}
