module Cisco-IOS-XE-voice {
  // Generated by yanger -t ncs
  tailf:ncs-device-type "netconf";

  namespace "http://cisco.com/ns/yang/Cisco-IOS-XE-voice";
  prefix ios-voice;

  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Voice Yang model.
     Copyright (c) 2016 by Cisco Systems, Inc.
     All rights reserved.";

  revision 2017-02-07 {
    description
      "Initial revision";
  }

  grouping ncs_template_config-voice-grouping {
    container voice {
      description
        "Global voice configuration";
      list service {
        // NCS patched for predictable order
        ordered-by user;
        description
          "Global packet telephony service commands";
        key "type";
        leaf type {
          type string;
        }
        container fax {
          description
            "Global fax commands";
          leaf protocol {
            description
              "The system-wide fax protocol type";
            type string;
          }
          leaf fallback {
            description
              "fax transport to use if T.38 unsupported on far end";
            // NCS drop when statement
            type string;
          }
          leaf codec {
            // NCS drop when statement
            type string;
          }
          leaf ls-redundancy {
            description
              "t38 low speed redundancy";
            // NCS drop when statement
            type string;
          }
          leaf hs-redundancy {
            description
              "t38 high speed redundancy";
            // NCS drop when statement
            type string;
          }
          leaf version {
            description
              "t38 fax version";
            // NCS drop when statement
            type string;
          }
        }
      }
    }
  }

  grouping ncs_template_config-voice-card-grouping {
    list voice-card {
      // NCS patched for predictable order
      ordered-by user;
      description
        "Configure a specific voice-card";
      key "slot";
      leaf slot {
        type string;
      }
    }
  }

  grouping ncs_rpc_notif_config-voice-grouping {
    container voice {
      description
        "Global voice configuration";
      list service {
        description
          "Global packet telephony service commands";
        key "type";
        leaf type {
          type enumeration {
            enum "pots";
            enum "saf";
            enum "voatm";
            enum "vofr";
            enum "voip";
          }
        }
        container fax {
          description
            "Global fax commands";
          leaf protocol {
            description
              "The system-wide fax protocol type";
            type enumeration {
              enum "cisco";
              enum "none";
              enum "pass-through";
              enum "t38";
            }
          }
          leaf fallback {
            description
              "fax transport to use if T.38 unsupported on far end";
            when "../protocol = 't38'" {
              tailf:xpath-root 3;
            }
            type enumeration {
              enum "cisco";
              enum "none";
              enum "pass-through";
            }
          }
          leaf codec {
            when "../protocol = 'pass-through' or ../fallback = 'pass-through'" {
              tailf:xpath-root 3;
            }
            type enumeration {
              enum "g711alaw";
              enum "g711ulaw";
            }
          }
          leaf ls-redundancy {
            description
              "t38 low speed redundancy";
            when "../protocol = 't38'" {
              tailf:xpath-root 3;
            }
            type uint8 {
              range "0..5";
            }
          }
          leaf hs-redundancy {
            description
              "t38 high speed redundancy";
            when "../protocol = 't38'" {
              tailf:xpath-root 3;
            }
            type uint8 {
              range "0..2";
            }
          }
          leaf version {
            description
              "t38 fax version";
            when "../protocol = 't38'" {
              tailf:xpath-root 3;
            }
            type enumeration {
              enum "0";
              enum "3";
            }
          }
        }
      }
    }
  }

  grouping ncs_rpc_notif_config-voice-card-grouping {
    list voice-card {
      description
        "Configure a specific voice-card";
      key "slot";
      leaf slot {
        type uint8 {
          range "0..2";
        }
      }
    }
  }

  grouping live_ncs_config-voice-grouping {
    container voice {
      description
        "Global voice configuration";
      list service {
        description
          "Global packet telephony service commands";
        key "type";
        leaf type {
          type enumeration {
            enum "pots";
            enum "saf";
            enum "voatm";
            enum "vofr";
            enum "voip";
          }
        }
        container fax {
          description
            "Global fax commands";
          leaf protocol {
            description
              "The system-wide fax protocol type";
            type enumeration {
              enum "cisco";
              enum "none";
              enum "pass-through";
              enum "t38";
            }
          }
          leaf fallback {
            description
              "fax transport to use if T.38 unsupported on far end";
            // NCS drop when statement
            type enumeration {
              enum "cisco";
              enum "none";
              enum "pass-through";
            }
          }
          leaf codec {
            // NCS drop when statement
            type enumeration {
              enum "g711alaw";
              enum "g711ulaw";
            }
          }
          leaf ls-redundancy {
            description
              "t38 low speed redundancy";
            // NCS drop when statement
            type uint8 {
              range "0..5";
            }
          }
          leaf hs-redundancy {
            description
              "t38 high speed redundancy";
            // NCS drop when statement
            type uint8 {
              range "0..2";
            }
          }
          leaf version {
            description
              "t38 fax version";
            // NCS drop when statement
            type enumeration {
              enum "0";
              enum "3";
            }
          }
        }
      }
    }
  }

  grouping live_ncs_config-voice-card-grouping {
    list voice-card {
      description
        "Configure a specific voice-card";
      key "slot";
      leaf slot {
        type uint8 {
          range "0..2";
        }
      }
    }
  }

  grouping config-voice-grouping {
    container voice {
      description
        "Global voice configuration";
      list service {
        description
          "Global packet telephony service commands";
        key "type";
        leaf type {
          type enumeration {
            enum "pots";
            enum "saf";
            enum "voatm";
            enum "vofr";
            enum "voip";
          }
        }
        container fax {
          description
            "Global fax commands";
          leaf protocol {
            description
              "The system-wide fax protocol type";
            type enumeration {
              enum "cisco";
              enum "none";
              enum "pass-through";
              enum "t38";
            }
          }
          leaf fallback {
            description
              "fax transport to use if T.38 unsupported on far end";
            when "../protocol = 't38'" {
              tailf:xpath-root 3;
            }
            type enumeration {
              enum "cisco";
              enum "none";
              enum "pass-through";
            }
          }
          leaf codec {
            when "../protocol = 'pass-through' or ../fallback = 'pass-through'" {
              tailf:xpath-root 3;
            }
            type enumeration {
              enum "g711alaw";
              enum "g711ulaw";
            }
          }
          leaf ls-redundancy {
            description
              "t38 low speed redundancy";
            when "../protocol = 't38'" {
              tailf:xpath-root 3;
            }
            type uint8 {
              range "0..5";
            }
          }
          leaf hs-redundancy {
            description
              "t38 high speed redundancy";
            when "../protocol = 't38'" {
              tailf:xpath-root 3;
            }
            type uint8 {
              range "0..2";
            }
          }
          leaf version {
            description
              "t38 fax version";
            when "../protocol = 't38'" {
              tailf:xpath-root 3;
            }
            type enumeration {
              enum "0";
              enum "3";
            }
          }
        }
      }
    }
  }

  grouping config-voice-card-grouping {
    list voice-card {
      description
        "Configure a specific voice-card";
      key "slot";
      leaf slot {
        type uint8 {
          range "0..2";
        }
      }
    }
  }

  augment "/ncs:devices/ncs:template/ncs:config/ios:native" {
    uses ncs_template_config-voice-grouping;
    uses ncs_template_config-voice-card-grouping;
  }
  augment "/ncs:devices/ncs:device/ncs:live-status/ios:native" {
    uses live_ncs_config-voice-grouping {
      refine voice {
        tailf:ncs-device-type "netconf";
        tailf:display-when "not(../../../ncs:module) or ../../../ncs:module[ncs:name='Cisco-IOS-XE-voice'] or (../../../ncs:live-status-protocol[not(ncs:capability)]) or (../../../ncs:live-status-protocol/ncs:capability/ncs:module[.='Cisco-IOS-XE-voice'])";
      }
    }
    uses live_ncs_config-voice-card-grouping {
      refine voice-card {
        tailf:ncs-device-type "netconf";
        tailf:display-when "not(../../ncs:module) or ../../ncs:module[ncs:name='Cisco-IOS-XE-voice'] or (../../ncs:live-status-protocol[not(ncs:capability)]) or (../../ncs:live-status-protocol/ncs:capability/ncs:module[.='Cisco-IOS-XE-voice'])";
      }
    }
  }
  augment "/ncs:devices/ncs:device/ncs:config/ios:native" {
    uses config-voice-grouping {
      refine voice {
        tailf:ncs-device-type "netconf";
        tailf:display-when "not(../../../ncs:module) or ../../../ncs:module[ncs:name='Cisco-IOS-XE-voice']";
      }
    }
    uses config-voice-card-grouping {
      refine voice-card {
        tailf:ncs-device-type "netconf";
        tailf:display-when "not(../../ncs:module) or ../../ncs:module[ncs:name='Cisco-IOS-XE-voice']";
      }
    }
  }
}
