module Cisco-IOS-XE-vtp {
  // Generated by yanger -t ncs
  tailf:ncs-device-type "netconf";

  namespace "http://cisco.com/ns/yang/Cisco-IOS-XE-vtp";
  prefix ios-vtp;

  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native VLAN Trunk Protocol (VTP) Yang model.
     Copyright (c) 2016 by Cisco Systems, Inc.
     All rights reserved.";

  revision 2017-02-07 {
    description
      "Initial revision";
  }

  grouping ncs_template_device-modes {
    leaf mst {
      description
        "Set the mode for MST VTP instance";
      type empty;
    }
    leaf unknown {
      description
        "Set the mode for unknown VTP instances";
      type empty;
    }
    leaf vlan {
      description
        "Set the mode for VLAN VTP instance";
      type empty;
    }
  }

  grouping ncs_template_config-vtp-grouping {
    leaf file {
      description
        "Configure IFS filesystem file where VTP configuration is stored.";
      type string;
    }
    container interface {
      description
        "Configure Interface as the preferred source for the VTP IP updater address";
      leaf interface-name {
        description
          "The name of the interface providing the VTP updater ID for this device";
        type string;
      }
      leaf only {
        description
          "Use only this interface's IP address as the VTP IP updater address";
        type empty;
      }
    }
    container password {
      description
        "Set the password for the VTP administrative domain";
      leaf password {
        description
          "The ascii password for the VTP administrative domain";
        type string;
      }
      leaf hidden {
        description
          "Set the VTP password hidden option";
        type empty;
      }
      leaf secret {
        description
          "Specify the vtp password in encrypted form";
        type empty;
      }
    }
    leaf pruning {
      description
        "Set the adminstrative domain to permit pruning";
      type empty;
    }
    leaf version {
      description
        "Set the adminstrative domain to VTP version";
      type string;
    }
    leaf domain {
      description
        "Set the name of the VTP administrative domain.";
      type string;
    }
    container mode {
      description
        "Configure VTP device mode";
      container client {
        description
          "Set the device to client mode";
        presence "true";
        uses ncs_template_device-modes;
      }
      container off {
        description
          "Set the device to off mode";
        presence "true";
        uses ncs_template_device-modes;
      }
      container server {
        description
          "Set the device to server mode";
        presence "true";
        uses ncs_template_device-modes;
      }
      container transparent {
        description
          "Set the device to transparent mode";
        presence "true";
        uses ncs_template_device-modes;
      }
    }
  }

  grouping ncs_rpc_notif_device-modes {
    leaf mst {
      description
        "Set the mode for MST VTP instance";
      type empty;
    }
    leaf unknown {
      description
        "Set the mode for unknown VTP instances";
      type empty;
    }
    leaf vlan {
      description
        "Set the mode for VLAN VTP instance";
      type empty;
    }
  }

  grouping ncs_rpc_notif_config-vtp-grouping {
    leaf file {
      description
        "Configure IFS filesystem file where VTP configuration is stored.";
      type string;
    }
    container interface {
      description
        "Configure Interface as the preferred source for the VTP IP updater address";
      leaf interface-name {
        description
          "The name of the interface providing the VTP updater ID for this device";
        type string;
      }
      leaf only {
        description
          "Use only this interface's IP address as the VTP IP updater address";
        type empty;
      }
    }
    container password {
      description
        "Set the password for the VTP administrative domain";
      leaf password {
        description
          "The ascii password for the VTP administrative domain";
        type string;
      }
      leaf hidden {
        description
          "Set the VTP password hidden option";
        type empty;
      }
      leaf secret {
        description
          "Specify the vtp password in encrypted form";
        type empty;
      }
    }
    leaf pruning {
      description
        "Set the adminstrative domain to permit pruning";
      type empty;
    }
    leaf version {
      description
        "Set the adminstrative domain to VTP version";
      type uint8 {
        range "1..3";
      }
    }
    leaf domain {
      description
        "Set the name of the VTP administrative domain.";
      type string;
    }
    container mode {
      description
        "Configure VTP device mode";
      container client {
        description
          "Set the device to client mode";
        presence "true";
        uses ncs_rpc_notif_device-modes;
      }
      container off {
        description
          "Set the device to off mode";
        presence "true";
        uses ncs_rpc_notif_device-modes;
      }
      container server {
        description
          "Set the device to server mode";
        presence "true";
        uses ncs_rpc_notif_device-modes;
      }
      container transparent {
        description
          "Set the device to transparent mode";
        presence "true";
        uses ncs_rpc_notif_device-modes;
      }
    }
  }

  grouping live_ncs_device-modes {
    leaf mst {
      description
        "Set the mode for MST VTP instance";
      type empty;
    }
    leaf unknown {
      description
        "Set the mode for unknown VTP instances";
      type empty;
    }
    leaf vlan {
      description
        "Set the mode for VLAN VTP instance";
      type empty;
    }
  }

  grouping live_ncs_config-vtp-grouping {
    leaf file {
      description
        "Configure IFS filesystem file where VTP configuration is stored.";
      type string;
    }
    container interface {
      description
        "Configure Interface as the preferred source for the VTP IP updater address";
      leaf interface-name {
        description
          "The name of the interface providing the VTP updater ID for this device";
        type string;
      }
      leaf only {
        description
          "Use only this interface's IP address as the VTP IP updater address";
        type empty;
      }
    }
    container password {
      description
        "Set the password for the VTP administrative domain";
      leaf password {
        description
          "The ascii password for the VTP administrative domain";
        type string;
      }
      leaf hidden {
        description
          "Set the VTP password hidden option";
        type empty;
      }
      leaf secret {
        description
          "Specify the vtp password in encrypted form";
        type empty;
      }
    }
    leaf pruning {
      description
        "Set the adminstrative domain to permit pruning";
      type empty;
    }
    leaf version {
      description
        "Set the adminstrative domain to VTP version";
      type uint8 {
        range "1..3";
      }
    }
    leaf domain {
      description
        "Set the name of the VTP administrative domain.";
      type string;
    }
    container mode {
      description
        "Configure VTP device mode";
      container client {
        description
          "Set the device to client mode";
        presence "true";
        uses live_ncs_device-modes;
      }
      container off {
        description
          "Set the device to off mode";
        presence "true";
        uses live_ncs_device-modes;
      }
      container server {
        description
          "Set the device to server mode";
        presence "true";
        uses live_ncs_device-modes;
      }
      container transparent {
        description
          "Set the device to transparent mode";
        presence "true";
        uses live_ncs_device-modes;
      }
    }
  }

  grouping device-modes {
    leaf mst {
      description
        "Set the mode for MST VTP instance";
      type empty;
    }
    leaf unknown {
      description
        "Set the mode for unknown VTP instances";
      type empty;
    }
    leaf vlan {
      description
        "Set the mode for VLAN VTP instance";
      type empty;
    }
  }

  grouping config-vtp-grouping {
    leaf file {
      description
        "Configure IFS filesystem file where VTP configuration is stored.";
      type string;
    }
    container interface {
      description
        "Configure Interface as the preferred source for the VTP IP updater address";
      leaf interface-name {
        description
          "The name of the interface providing the VTP updater ID for this device";
        type string;
      }
      leaf only {
        description
          "Use only this interface's IP address as the VTP IP updater address";
        type empty;
      }
    }
    container password {
      description
        "Set the password for the VTP administrative domain";
      leaf password {
        description
          "The ascii password for the VTP administrative domain";
        type string;
      }
      leaf hidden {
        description
          "Set the VTP password hidden option";
        type empty;
      }
      leaf secret {
        description
          "Specify the vtp password in encrypted form";
        type empty;
      }
    }
    leaf pruning {
      description
        "Set the adminstrative domain to permit pruning";
      type empty;
    }
    leaf version {
      description
        "Set the adminstrative domain to VTP version";
      type uint8 {
        range "1..3";
      }
    }
    leaf domain {
      description
        "Set the name of the VTP administrative domain.";
      type string;
    }
    container mode {
      description
        "Configure VTP device mode";
      container client {
        description
          "Set the device to client mode";
        presence "true";
        uses device-modes;
      }
      container off {
        description
          "Set the device to off mode";
        presence "true";
        uses device-modes;
      }
      container server {
        description
          "Set the device to server mode";
        presence "true";
        uses device-modes;
      }
      container transparent {
        description
          "Set the device to transparent mode";
        presence "true";
        uses device-modes;
      }
    }
  }

  augment "/ncs:devices/ncs:template/ncs:config/ios:native/ios:vtp" {
    uses ncs_template_config-vtp-grouping;
  }
  augment "/ncs:devices/ncs:device/ncs:live-status/ios:native/ios:vtp" {
    uses live_ncs_config-vtp-grouping {
      refine mode {
        tailf:ncs-device-type "netconf";
        tailf:display-when "not(../../../../ncs:module) or ../../../../ncs:module[ncs:name='Cisco-IOS-XE-vtp'] or (../../../../ncs:live-status-protocol[not(ncs:capability)]) or (../../../../ncs:live-status-protocol/ncs:capability/ncs:module[.='Cisco-IOS-XE-vtp'])";
      }
      refine domain {
        tailf:ncs-device-type "netconf";
        tailf:display-when "not(../../../../ncs:module) or ../../../../ncs:module[ncs:name='Cisco-IOS-XE-vtp'] or (../../../../ncs:live-status-protocol[not(ncs:capability)]) or (../../../../ncs:live-status-protocol/ncs:capability/ncs:module[.='Cisco-IOS-XE-vtp'])";
      }
      refine version {
        tailf:ncs-device-type "netconf";
        tailf:display-when "not(../../../../ncs:module) or ../../../../ncs:module[ncs:name='Cisco-IOS-XE-vtp'] or (../../../../ncs:live-status-protocol[not(ncs:capability)]) or (../../../../ncs:live-status-protocol/ncs:capability/ncs:module[.='Cisco-IOS-XE-vtp'])";
      }
      refine pruning {
        tailf:ncs-device-type "netconf";
        tailf:display-when "not(../../../../ncs:module) or ../../../../ncs:module[ncs:name='Cisco-IOS-XE-vtp'] or (../../../../ncs:live-status-protocol[not(ncs:capability)]) or (../../../../ncs:live-status-protocol/ncs:capability/ncs:module[.='Cisco-IOS-XE-vtp'])";
      }
      refine password {
        tailf:ncs-device-type "netconf";
        tailf:display-when "not(../../../../ncs:module) or ../../../../ncs:module[ncs:name='Cisco-IOS-XE-vtp'] or (../../../../ncs:live-status-protocol[not(ncs:capability)]) or (../../../../ncs:live-status-protocol/ncs:capability/ncs:module[.='Cisco-IOS-XE-vtp'])";
      }
      refine interface {
        tailf:ncs-device-type "netconf";
        tailf:display-when "not(../../../../ncs:module) or ../../../../ncs:module[ncs:name='Cisco-IOS-XE-vtp'] or (../../../../ncs:live-status-protocol[not(ncs:capability)]) or (../../../../ncs:live-status-protocol/ncs:capability/ncs:module[.='Cisco-IOS-XE-vtp'])";
      }
      refine file {
        tailf:ncs-device-type "netconf";
        tailf:display-when "not(../../../../ncs:module) or ../../../../ncs:module[ncs:name='Cisco-IOS-XE-vtp'] or (../../../../ncs:live-status-protocol[not(ncs:capability)]) or (../../../../ncs:live-status-protocol/ncs:capability/ncs:module[.='Cisco-IOS-XE-vtp'])";
      }
    }
  }
  augment "/ncs:devices/ncs:device/ncs:config/ios:native/ios:vtp" {
    uses config-vtp-grouping {
      refine mode {
        tailf:ncs-device-type "netconf";
        tailf:display-when "not(../../../../ncs:module) or ../../../../ncs:module[ncs:name='Cisco-IOS-XE-vtp']";
      }
      refine domain {
        tailf:ncs-device-type "netconf";
        tailf:display-when "not(../../../../ncs:module) or ../../../../ncs:module[ncs:name='Cisco-IOS-XE-vtp']";
      }
      refine version {
        tailf:ncs-device-type "netconf";
        tailf:display-when "not(../../../../ncs:module) or ../../../../ncs:module[ncs:name='Cisco-IOS-XE-vtp']";
      }
      refine pruning {
        tailf:ncs-device-type "netconf";
        tailf:display-when "not(../../../../ncs:module) or ../../../../ncs:module[ncs:name='Cisco-IOS-XE-vtp']";
      }
      refine password {
        tailf:ncs-device-type "netconf";
        tailf:display-when "not(../../../../ncs:module) or ../../../../ncs:module[ncs:name='Cisco-IOS-XE-vtp']";
      }
      refine interface {
        tailf:ncs-device-type "netconf";
        tailf:display-when "not(../../../../ncs:module) or ../../../../ncs:module[ncs:name='Cisco-IOS-XE-vtp']";
      }
      refine file {
        tailf:ncs-device-type "netconf";
        tailf:display-when "not(../../../../ncs:module) or ../../../../ncs:module[ncs:name='Cisco-IOS-XE-vtp']";
      }
    }
  }
}
