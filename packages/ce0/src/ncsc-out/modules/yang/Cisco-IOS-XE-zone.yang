module Cisco-IOS-XE-zone {
  // Generated by yanger -t ncs
  tailf:ncs-device-type "netconf";

  namespace "http://cisco.com/ns/yang/Cisco-IOS-XE-zone";
  prefix ios-zone;

  import Cisco-IOS-XE-native {
    prefix ios;
  }
  import tailf-ncs {
    prefix ncs;
  }
  import tailf-common {
    prefix tailf;
  }

  organization "Cisco Systems, Inc.";
  contact
    "Cisco Systems, Inc.
     Customer Service

     Postal: 170 W Tasman Drive
     San Jose, CA 95134

     Tel: +1 1800 553-NETS

     E-mail: cs-yang@cisco.com";
  description
    "Cisco XE Native Zone Interfaces Yang model.
     Copyright (c) 2016 by Cisco Systems, Inc.
     All rights reserved.";

  revision 2017-02-07 {
    description
      "Initial revision";
  }

  grouping ncs_template_config-interface-zone-member-grouping {
    container zone-member {
      description
        "Apply zone name";
      leaf security {
        description
          "Security zone";
        type string;
      }
    }
  }

  grouping ncs_template_config-zone-grouping {
    list security {
      // NCS patched for predictable order
      ordered-by user;
      description
        "Security zone";
      key "id";
      leaf id {
        type string;
      }
      leaf description {
        description
          "Zone description";
        type string;
      }
      leaf protection {
        description
          "config sync cookie protection against sync flood";
        type string;
      }
    }
  }

  grouping ncs_template_config-zone-pair-grouping {
    description
      "Zone pair command";
    list security {
      // NCS patched for predictable order
      ordered-by user;
      description
        "Zone-pair name";
      key "id";
      leaf id {
        type string;
      }
      leaf source {
        description
          "Source zone";
        type string;
      }
      leaf destination {
        description
          "Destination zone";
        type string;
      }
      leaf description {
        description
          "Zone description";
        type string;
      }
      container service-policy {
        description
          "Configure CBAC Service Policy";
        container type {
          description
            "Service Policy type";
          leaf inspect {
            description
              "Configure CBAC Service Policy type inspect";
            type string;
          }
        }
      }
    }
  }

  grouping ncs_rpc_notif_config-interface-zone-member-grouping {
    container zone-member {
      description
        "Apply zone name";
      leaf security {
        description
          "Security zone";
        type string;
      }
    }
  }

  grouping ncs_rpc_notif_config-zone-grouping {
    list security {
      description
        "Security zone";
      key "id";
      leaf id {
        type string;
      }
      leaf description {
        description
          "Zone description";
        type string;
      }
      leaf protection {
        description
          "config sync cookie protection against sync flood";
        type string;
      }
    }
  }

  grouping ncs_rpc_notif_config-zone-pair-grouping {
    description
      "Zone pair command";
    list security {
      description
        "Zone-pair name";
      key "id";
      leaf id {
        type string;
      }
      leaf source {
        description
          "Source zone";
        type string;
      }
      leaf destination {
        description
          "Destination zone";
        type string;
      }
      leaf description {
        description
          "Zone description";
        type string {
          length "1..200";
        }
      }
      container service-policy {
        description
          "Configure CBAC Service Policy";
        container type {
          description
            "Service Policy type";
          leaf inspect {
            description
              "Configure CBAC Service Policy type inspect";
            type string;
          }
        }
      }
    }
  }

  grouping live_ncs_config-interface-zone-member-grouping {
    container zone-member {
      description
        "Apply zone name";
      leaf security {
        description
          "Security zone";
        type string;
      }
    }
  }

  grouping live_ncs_config-zone-grouping {
    list security {
      description
        "Security zone";
      key "id";
      leaf id {
        type string;
      }
      leaf description {
        description
          "Zone description";
        type string;
      }
      leaf protection {
        description
          "config sync cookie protection against sync flood";
        type string;
      }
    }
  }

  grouping live_ncs_config-zone-pair-grouping {
    description
      "Zone pair command";
    list security {
      description
        "Zone-pair name";
      key "id";
      leaf id {
        type string;
      }
      leaf source {
        description
          "Source zone";
        type string;
      }
      leaf destination {
        description
          "Destination zone";
        type string;
      }
      leaf description {
        description
          "Zone description";
        type string {
          length "1..200";
        }
      }
      container service-policy {
        description
          "Configure CBAC Service Policy";
        container type {
          description
            "Service Policy type";
          leaf inspect {
            description
              "Configure CBAC Service Policy type inspect";
            type string;
          }
        }
      }
    }
  }

  grouping config-interface-zone-member-grouping {
    container zone-member {
      description
        "Apply zone name";
      leaf security {
        description
          "Security zone";
        type string;
      }
    }
  }

  grouping config-zone-grouping {
    list security {
      description
        "Security zone";
      key "id";
      leaf id {
        type string;
      }
      leaf description {
        description
          "Zone description";
        type string;
      }
      leaf protection {
        description
          "config sync cookie protection against sync flood";
        type string;
      }
    }
  }

  grouping config-zone-pair-grouping {
    description
      "Zone pair command";
    list security {
      description
        "Zone-pair name";
      key "id";
      leaf id {
        type string;
      }
      leaf source {
        description
          "Source zone";
        type string;
      }
      leaf destination {
        description
          "Destination zone";
        type string;
      }
      leaf description {
        description
          "Zone description";
        type string {
          length "1..200";
        }
      }
      container service-policy {
        description
          "Configure CBAC Service Policy";
        container type {
          description
            "Service Policy type";
          leaf inspect {
            description
              "Configure CBAC Service Policy type inspect";
            type string;
          }
        }
      }
    }
  }

  augment "/ncs:devices/ncs:template/ncs:config/ios:native/ios:zone" {
    uses ncs_template_config-zone-grouping;
  }
  augment "/ncs:devices/ncs:device/ncs:live-status/ios:native/ios:zone" {
    uses live_ncs_config-zone-grouping {
      refine security {
        tailf:ncs-device-type "netconf";
        tailf:display-when "not(../../../ncs:module) or ../../../ncs:module[ncs:name='Cisco-IOS-XE-zone'] or (../../../ncs:live-status-protocol[not(ncs:capability)]) or (../../../ncs:live-status-protocol/ncs:capability/ncs:module[.='Cisco-IOS-XE-zone'])";
      }
    }
  }
  augment "/ncs:devices/ncs:device/ncs:config/ios:native/ios:zone" {
    uses config-zone-grouping {
      refine security {
        tailf:ncs-device-type "netconf";
        tailf:display-when "not(../../../ncs:module) or ../../../ncs:module[ncs:name='Cisco-IOS-XE-zone']";
      }
    }
  }
  augment "/ncs:devices/ncs:template/ncs:config/ios:native/ios:zone-pair" {
    uses ncs_template_config-zone-pair-grouping;
  }
  augment "/ncs:devices/ncs:device/ncs:live-status/ios:native/ios:zone-pair" {
    uses live_ncs_config-zone-pair-grouping {
      refine security {
        tailf:ncs-device-type "netconf";
        tailf:display-when "not(../../../ncs:module) or ../../../ncs:module[ncs:name='Cisco-IOS-XE-zone'] or (../../../ncs:live-status-protocol[not(ncs:capability)]) or (../../../ncs:live-status-protocol/ncs:capability/ncs:module[.='Cisco-IOS-XE-zone'])";
      }
    }
  }
  augment "/ncs:devices/ncs:device/ncs:config/ios:native/ios:zone-pair" {
    uses config-zone-pair-grouping {
      refine security {
        tailf:ncs-device-type "netconf";
        tailf:display-when "not(../../../ncs:module) or ../../../ncs:module[ncs:name='Cisco-IOS-XE-zone']";
      }
    }
  }
  augment "/ncs:devices/ncs:template/ncs:config/ios:native/ios:interface/ios:FastEthernet" {
    uses ncs_template_config-interface-zone-member-grouping;
  }
  augment "/ncs:devices/ncs:device/ncs:live-status/ios:native/ios:interface/ios:FastEthernet" {
    uses live_ncs_config-interface-zone-member-grouping {
      refine zone-member {
        tailf:ncs-device-type "netconf";
        tailf:display-when "not(../../../../../ncs:module) or ../../../../../ncs:module[ncs:name='Cisco-IOS-XE-zone'] or (../../../../../ncs:live-status-protocol[not(ncs:capability)]) or (../../../../../ncs:live-status-protocol/ncs:capability/ncs:module[.='Cisco-IOS-XE-zone'])";
      }
    }
  }
  augment "/ncs:devices/ncs:device/ncs:config/ios:native/ios:interface/ios:FastEthernet" {
    uses config-interface-zone-member-grouping {
      refine zone-member {
        tailf:ncs-device-type "netconf";
        tailf:display-when "not(../../../../../ncs:module) or ../../../../../ncs:module[ncs:name='Cisco-IOS-XE-zone']";
      }
    }
  }
  augment "/ncs:devices/ncs:template/ncs:config/ios:native/ios:interface/ios:GigabitEthernet" {
    uses ncs_template_config-interface-zone-member-grouping;
  }
  augment "/ncs:devices/ncs:device/ncs:live-status/ios:native/ios:interface/ios:GigabitEthernet" {
    uses live_ncs_config-interface-zone-member-grouping {
      refine zone-member {
        tailf:ncs-device-type "netconf";
        tailf:display-when "not(../../../../../ncs:module) or ../../../../../ncs:module[ncs:name='Cisco-IOS-XE-zone'] or (../../../../../ncs:live-status-protocol[not(ncs:capability)]) or (../../../../../ncs:live-status-protocol/ncs:capability/ncs:module[.='Cisco-IOS-XE-zone'])";
      }
    }
  }
  augment "/ncs:devices/ncs:device/ncs:config/ios:native/ios:interface/ios:GigabitEthernet" {
    uses config-interface-zone-member-grouping {
      refine zone-member {
        tailf:ncs-device-type "netconf";
        tailf:display-when "not(../../../../../ncs:module) or ../../../../../ncs:module[ncs:name='Cisco-IOS-XE-zone']";
      }
    }
  }
  augment "/ncs:devices/ncs:template/ncs:config/ios:native/ios:interface/ios:TenGigabitEthernet" {
    uses ncs_template_config-interface-zone-member-grouping;
  }
  augment "/ncs:devices/ncs:device/ncs:live-status/ios:native/ios:interface/ios:TenGigabitEthernet" {
    uses live_ncs_config-interface-zone-member-grouping {
      refine zone-member {
        tailf:ncs-device-type "netconf";
        tailf:display-when "not(../../../../../ncs:module) or ../../../../../ncs:module[ncs:name='Cisco-IOS-XE-zone'] or (../../../../../ncs:live-status-protocol[not(ncs:capability)]) or (../../../../../ncs:live-status-protocol/ncs:capability/ncs:module[.='Cisco-IOS-XE-zone'])";
      }
    }
  }
  augment "/ncs:devices/ncs:device/ncs:config/ios:native/ios:interface/ios:TenGigabitEthernet" {
    uses config-interface-zone-member-grouping {
      refine zone-member {
        tailf:ncs-device-type "netconf";
        tailf:display-when "not(../../../../../ncs:module) or ../../../../../ncs:module[ncs:name='Cisco-IOS-XE-zone']";
      }
    }
  }
  augment "/ncs:devices/ncs:template/ncs:config/ios:native/ios:interface/ios:Loopback" {
    uses ncs_template_config-interface-zone-member-grouping;
  }
  augment "/ncs:devices/ncs:device/ncs:live-status/ios:native/ios:interface/ios:Loopback" {
    uses live_ncs_config-interface-zone-member-grouping {
      refine zone-member {
        tailf:ncs-device-type "netconf";
        tailf:display-when "not(../../../../../ncs:module) or ../../../../../ncs:module[ncs:name='Cisco-IOS-XE-zone'] or (../../../../../ncs:live-status-protocol[not(ncs:capability)]) or (../../../../../ncs:live-status-protocol/ncs:capability/ncs:module[.='Cisco-IOS-XE-zone'])";
      }
    }
  }
  augment "/ncs:devices/ncs:device/ncs:config/ios:native/ios:interface/ios:Loopback" {
    uses config-interface-zone-member-grouping {
      refine zone-member {
        tailf:ncs-device-type "netconf";
        tailf:display-when "not(../../../../../ncs:module) or ../../../../../ncs:module[ncs:name='Cisco-IOS-XE-zone']";
      }
    }
  }
  augment "/ncs:devices/ncs:template/ncs:config/ios:native/ios:interface/ios:Tunnel" {
    uses ncs_template_config-interface-zone-member-grouping;
  }
  augment "/ncs:devices/ncs:device/ncs:live-status/ios:native/ios:interface/ios:Tunnel" {
    uses live_ncs_config-interface-zone-member-grouping {
      refine zone-member {
        tailf:ncs-device-type "netconf";
        tailf:display-when "not(../../../../../ncs:module) or ../../../../../ncs:module[ncs:name='Cisco-IOS-XE-zone'] or (../../../../../ncs:live-status-protocol[not(ncs:capability)]) or (../../../../../ncs:live-status-protocol/ncs:capability/ncs:module[.='Cisco-IOS-XE-zone'])";
      }
    }
  }
  augment "/ncs:devices/ncs:device/ncs:config/ios:native/ios:interface/ios:Tunnel" {
    uses config-interface-zone-member-grouping {
      refine zone-member {
        tailf:ncs-device-type "netconf";
        tailf:display-when "not(../../../../../ncs:module) or ../../../../../ncs:module[ncs:name='Cisco-IOS-XE-zone']";
      }
    }
  }
  augment "/ncs:devices/ncs:template/ncs:config/ios:native/ios:interface/ios:Virtual-Template" {
    uses ncs_template_config-interface-zone-member-grouping;
  }
  augment "/ncs:devices/ncs:device/ncs:live-status/ios:native/ios:interface/ios:Virtual-Template" {
    uses live_ncs_config-interface-zone-member-grouping {
      refine zone-member {
        tailf:ncs-device-type "netconf";
        tailf:display-when "not(../../../../../ncs:module) or ../../../../../ncs:module[ncs:name='Cisco-IOS-XE-zone'] or (../../../../../ncs:live-status-protocol[not(ncs:capability)]) or (../../../../../ncs:live-status-protocol/ncs:capability/ncs:module[.='Cisco-IOS-XE-zone'])";
      }
    }
  }
  augment "/ncs:devices/ncs:device/ncs:config/ios:native/ios:interface/ios:Virtual-Template" {
    uses config-interface-zone-member-grouping {
      refine zone-member {
        tailf:ncs-device-type "netconf";
        tailf:display-when "not(../../../../../ncs:module) or ../../../../../ncs:module[ncs:name='Cisco-IOS-XE-zone']";
      }
    }
  }
  augment "/ncs:devices/ncs:template/ncs:config/ios:native/ios:interface/ios:Vlan" {
    uses ncs_template_config-interface-zone-member-grouping;
  }
  augment "/ncs:devices/ncs:device/ncs:live-status/ios:native/ios:interface/ios:Vlan" {
    uses live_ncs_config-interface-zone-member-grouping {
      refine zone-member {
        tailf:ncs-device-type "netconf";
        tailf:display-when "not(../../../../../ncs:module) or ../../../../../ncs:module[ncs:name='Cisco-IOS-XE-zone'] or (../../../../../ncs:live-status-protocol[not(ncs:capability)]) or (../../../../../ncs:live-status-protocol/ncs:capability/ncs:module[.='Cisco-IOS-XE-zone'])";
      }
    }
  }
  augment "/ncs:devices/ncs:device/ncs:config/ios:native/ios:interface/ios:Vlan" {
    uses config-interface-zone-member-grouping {
      refine zone-member {
        tailf:ncs-device-type "netconf";
        tailf:display-when "not(../../../../../ncs:module) or ../../../../../ncs:module[ncs:name='Cisco-IOS-XE-zone']";
      }
    }
  }
}
