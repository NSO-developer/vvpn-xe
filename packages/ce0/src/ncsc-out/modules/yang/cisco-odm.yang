module cisco-odm {
  // Generated by yanger -t ncs
  tailf:ncs-device-type "netconf";

  namespace "http://cisco.com/yang/cisco-odm";
  prefix codm;

  import cisco-self-mgmt {
    prefix cisco-sfm;
  }
  import tailf-common {
    prefix tailf;
  }
  import tailf-ncs {
    prefix ncs;
  }

  description
    "Copyright (c) 2016-2017 by Cisco Systems, Inc.All rights reserved.";

  revision 2017-04-25 {
    description
      "Marked BGP, FlowMonitor, PlatformSoftware obsolete";
  }
  revision 2017-01-25 {
    description
      "Added a missing default for polling-enable leaf";
  }
  revision 2016-12-20 {
    description
      "Added Diffserv parsername, removed TDL based parser names";
  }
  revision 2016-08-05 {
    description
      "Changed action names to be type identity. Obsoleted on-demand features.";
  }
  revision 2016-05-16 {
    description
      "Add augment statement";
  }
  revision 2016-05-04 {
    description
      "Add tail-f annotation to boolean leaves";
  }
  revision 2016-03-30 {
    description
      "Update description with copyright notice.";
  }
  revision 2015-06-19 {
    description
      "initial commit";
  }

  augment "/ncs:devices/ncs:template/ncs:config/cisco-sfm:netconf-yang" {
    container cisco-odm {
      leaf polling-enable {
        type string;
        // NCS drop default statement
      }
      leaf on-demand-default-time {
        status obsolete;
        type string;
        // NCS drop default statement
      }
      leaf on-demand-enable {
        status obsolete;
        type string;
        // NCS drop default statement
      }
      list actions {
        // NCS patched for predictable order
        ordered-by user;
        key "action-name";
        leaf action-name {
          type string;
        }
        leaf polling-interval {
          type string;
          // NCS drop default statement
        }
        leaf mode {
          type string;
          // NCS drop default statement
        }
        leaf cdb-xpath {
          type string;
        }
      }
    }
  }
  augment "/ncs:devices/ncs:device/ncs:live-status/cisco-sfm:netconf-yang" {
    container cisco-odm {
      tailf:ncs-device-type "netconf";
      tailf:display-when "not(../../../ncs:module) or ../../../ncs:module[ncs:name='cisco-odm'] or (../../../ncs:live-status-protocol[not(ncs:capability)]) or (../../../ncs:live-status-protocol/ncs:capability/ncs:module[.='cisco-odm'])";
      leaf polling-enable {
        // NCS drop tailf:cli-boolean-no
        type boolean;
        // NCS drop default statement
      }
      leaf on-demand-default-time {
        status obsolete;
        type uint32 {
          range "500..max";
        }
        // NCS drop default statement
      }
      leaf on-demand-enable {
        status obsolete;
        // NCS drop tailf:cli-boolean-no
        type boolean;
        // NCS drop default statement
      }
      list actions {
        key "action-name";
        leaf action-name {
          type identityref {
            base parsername;
          }
        }
        leaf polling-interval {
          type uint32 {
            range "1..max";
          }
          // NCS drop default statement
        }
        leaf mode {
          type enumeration {
            enum "poll";
            enum "on-demand";
            enum "none";
          }
          // NCS drop default statement
        }
        leaf cdb-xpath {
          type string;
        }
      }
    }
  }
  augment "/ncs:devices/ncs:device/ncs:config/cisco-sfm:netconf-yang" {
    container cisco-odm {
      tailf:ncs-device-type "netconf";
      tailf:display-when "not(../../../ncs:module) or ../../../ncs:module[ncs:name='cisco-odm']";
      leaf polling-enable {
        tailf:cli-boolean-no;
        type boolean;
        default "false";
      }
      leaf on-demand-default-time {
        status obsolete;
        type uint32 {
          range "500..max";
        }
        default "30000";
      }
      leaf on-demand-enable {
        status obsolete;
        tailf:cli-boolean-no;
        type boolean;
        default "false";
      }
      list actions {
        key "action-name";
        leaf action-name {
          type identityref {
            base parsername;
          }
        }
        leaf polling-interval {
          type uint32 {
            range "1..max";
          }
          default "120000";
        }
        leaf mode {
          type enumeration {
            enum "poll";
            enum "on-demand";
            enum "none";
          }
          default "poll";
        }
        leaf cdb-xpath {
          type string;
        }
      }
    }
  }

  identity EthernetCFMStats {
    description
      "show ethernet cfm statistics";
    base parsername;
  }

  identity OSPF {
    description
      "show ospf";
    base parsername;
  }

  identity MPLSForwardingTable {
    description
      "show mpls forwarding-table";
    base parsername;
  }

  identity MPLSStaticBinding {
    description
      "show mpls static binding";
    base parsername;
  }

  identity PlatformSoftware {
    status obsolete;
    description
      "show platform software";
    base parsername;
  }

  identity MPLSLDPNeighbors {
    description
      "show mpls ldp neighbor detail";
    base parsername;
  }

  identity VirtualService {
    description
      "show virtual-service";
    base parsername;
  }

  identity Diffserv {
    description
      "show policy-map interface";
    base parsername;
  }

  identity BridgeDomain {
    description
      "show bridge domain";
    base parsername;
  }

  identity BFDNeighbors {
    description
      "show bfd neighbors";
    base parsername;
  }

  identity FlowMonitor {
    status obsolete;
    description
      "show flow monitor";
    base parsername;
  }

  identity IPRoute {
    description
      "show ip route";
    base parsername;
  }

  identity BGP {
    status obsolete;
    description
      "show bgp";
    base parsername;
  }

  identity parsername {
    description
      " ODM parser names";
  }
}
