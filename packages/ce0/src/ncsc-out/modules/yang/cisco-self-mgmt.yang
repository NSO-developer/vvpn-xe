module cisco-self-mgmt {
  // Generated by yanger -t ncs
  tailf:ncs-device-type "netconf";

  namespace "http://cisco.com/yang/cisco-self-mgmt";
  prefix cisco-sfm;

  import tailf-ncs {
    prefix ncs;
  }
  import tailf-common {
    prefix tailf;
  }

  description
    "Copyright (c) 2016 by Cisco Systems, Inc.All rights reserved.";

  revision 2016-05-14 {
    description
      "Initial version with netconf-yang container";
  }

  augment "/ncs:devices/ncs:device/ncs:config" {
    container netconf-yang {
      tailf:ncs-device-type "netconf";
      tailf:display-when "not(../../ncs:module) or ../../ncs:module[ncs:name='cisco-self-mgmt']";
      description
        "Top level container shared by cisco-ia and cisco-odm models";
    }
  }
  augment "/ncs:devices/ncs:device/ncs:live-status" {
    container netconf-yang {
      tailf:ncs-device-type "netconf";
      tailf:display-when "not(../../ncs:module) or ../../ncs:module[ncs:name='cisco-self-mgmt'] or (../../ncs:live-status-protocol[not(ncs:capability)]) or (../../ncs:live-status-protocol/ncs:capability/ncs:module[.='cisco-self-mgmt'])";
      description
        "Top level container shared by cisco-ia and cisco-odm models";
    }
  }
  augment "/ncs:devices/ncs:template/ncs:config" {
    container netconf-yang {
      description
        "Top level container shared by cisco-ia and cisco-odm models";
    }
  }
}
